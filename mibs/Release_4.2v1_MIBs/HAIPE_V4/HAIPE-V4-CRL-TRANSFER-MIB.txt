--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-CRL-TRANSFER-MIB  DEFINITIONS  ::= BEGIN

IMPORTS
    hv4CRLTransfer                      FROM HAIPE-V4-FEATURE-HIERARCHY-MIB
    OBJECT-TYPE, MODULE-IDENTITY        FROM SNMPv2-SMI
    TruthValue                          FROM SNMPv2-TC;

haipev4CRLTransferMIB MODULE-IDENTITY
    LAST-UPDATED "201303292338Z"
    ORGANIZATION "HAIPE PO"
    CONTACT-INFO
        "(U//FOUO) Not Available"
    DESCRIPTION
        "(U//FOUO) This MIB defines the HAIPE Certificate Revocation List 
         Transfer objects.  Note that ALL objects within this module must not 
         exist if an implementation does not support the Certificate Revocation
         List Transfer Extension."
    REVISION     "201303292338Z"
    DESCRIPTION  "(U//FOUO) HAIPE MIB 4.1.2 Final"		 
    ::= { hv4CRLTransfer 1 }


-- **********************************************************************
-- CRL Transfer Information Segments
-- **********************************************************************
hCRLTransferControlObjects       OBJECT IDENTIFIER ::= { haipev4CRLTransferMIB 1 }
hCRLTransferScalars              OBJECT IDENTIFIER ::= { haipev4CRLTransferMIB 2 }
hCRLTransferNotifications        OBJECT IDENTIFIER ::= { haipev4CRLTransferMIB 3 }


-- **********************************************************************
-- CRL Transfer Control Objects
-- **********************************************************************
hCRLTransferEnable OBJECT-TYPE
    SYNTAX     TruthValue
    MAX-ACCESS read-write
    STATUS     current
    DESCRIPTION
        "(U//FOUO) This object enables/disables CRL Transfer functionality."
    DEFVAL { true }
    ::= { hCRLTransferControlObjects 1 }

hCRLTransferRequestMode OBJECT-TYPE
    SYNTAX     INTEGER { authenticationAssociatedCRL(1), allCRLs(2) }
    MAX-ACCESS read-write
    STATUS     current
    DESCRIPTION
        "(U//FOUO) This object sets the CRL Transfer Request Mode.  
        
         (U//FOUO) [authenticationAssociatedCRL] HAIPE will request the 
         associated CRL used in the authentication of the HAIPE IKEv2 exchange. 
         Note, the associated CRL is the CRL used to authenticate the HAIPE to  
         its peer.

         (U//FOUO) [allCRLs] HAIPE will request all CRLs for which it has a
         local CA."
    DEFVAL { authenticationAssociatedCRL }
    ::= { hCRLTransferControlObjects 2 }

hCRLEnblTrigCRLInfoTrans OBJECT-TYPE
    SYNTAX     TruthValue
    MAX-ACCESS read-write
    STATUS     current
    DESCRIPTION
        "(U//FOUO) This object enables/disables Triggered CRL Information 
         Transmission.  Note, if hCRLTransferEnable is set to false (i.e., CRL 
         Transfer is disabled), Triggered CRL Information Transmission is 
         effectively disabled."
    DEFVAL { false }
    ::= { hCRLTransferControlObjects 3 }


-- **********************************************************************
-- CRL Transfer Scalars 
-- **********************************************************************

                                     
-- **********************************************************************
-- CRL Transfer Notifications 
-- **********************************************************************


END
