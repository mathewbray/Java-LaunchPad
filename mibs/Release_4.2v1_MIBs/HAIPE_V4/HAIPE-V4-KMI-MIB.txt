--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-KMI-MIB  DEFINITIONS  ::= BEGIN

IMPORTS
    OBJECT-TYPE, Unsigned32,
    MODULE-IDENTITY                    FROM SNMPv2-SMI
    SnmpAdminString                    FROM SNMP-FRAMEWORK-MIB
    RowStatus, TimeStamp               FROM SNMPv2-TC
    hv4KMI                             FROM HAIPE-V4-FEATURE-HIERARCHY-MIB
    IPAddress, IPAddressType           FROM HAIPE-V4-TEXTUAL-CONVENTIONS-MIB;

haipeKMIMIB MODULE-IDENTITY
    LAST-UPDATED "197001010000Z"
    ORGANIZATION "HAIPE PO"
    CONTACT-INFO
         "(U//FOUO) Not Available"
    DESCRIPTION
        "(U//FOUO) This MIB defines KMI MIB objects necessary
         for a HAIPE to interface with KMI."
    REVISION     "197001010000Z"
    DESCRIPTION  "(U//FOUO) MIB 4.1.2 RC1"		 
    ::= { hv4KMI 1 }

-- **********************************************************************
-- Key Management Infrastructure [KMI] Information Segments
-- **********************************************************************

-- Define Product Delivery Enclave [PDE] information
hPDEInformation           OBJECT IDENTIFIER ::= { haipeKMIMIB 1 }

-- Define KMI Control Objects
hKMIControlObjects       OBJECT IDENTIFIER ::= { haipeKMIMIB 2 }

-- Define MGC Ethernet information
hMGCEnetInformation       OBJECT IDENTIFIER ::= { haipeKMIMIB 3 }

-- Define MGC Air Gap information
hMGCAirGapInformation     OBJECT IDENTIFIER ::= { haipeKMIMIB 4 }

-- **********************************************************************
-- Product Delivery Enclave [PDE] Scalars
-- **********************************************************************

hPDERetryDelay OBJECT-TYPE
    SYNTAX     Unsigned32
    MAX-ACCESS read-write
    STATUS     current
    DESCRIPTION
        "(U//FOUO) The amount of time (seconds) to wait after a Key Management 
         Infrastructure [KMI] product download fails before attempting to retry
         the operation.  Failures in these cases do not include Transport Layer
         Security [TLS].  When a failure occurs due to the TLS protocol, then
         the hTLSEstablishmentRetryDelay applies and not this hPDERetryDelay."
    ::= { hPDEInformation 1 }

hPDERetryMaxAttempts OBJECT-TYPE
    SYNTAX     Unsigned32
    MAX-ACCESS read-write
    STATUS     current
    DESCRIPTION
        "(U//FOUO) The amount of retries attempted before giving up on this 
         Product Delivery Enclave [PDE] or Over-the-Network Keying [OTNK] 
         Intermediary due to consecutive download failures.  Failures in these
         cases do not include TLS.  When a failure occurs due to the TLS 
         protocol, then the hTLSEstablishmentMaxAttempts applies and not this
         hPDERetryMaxAttempts."
    ::= { hPDEInformation 2 }

hPDETLSEstablishmentRetryDelay OBJECT-TYPE
    SYNTAX     Unsigned32
    MAX-ACCESS read-write
    STATUS     deprecated
    DESCRIPTION
        "(U//FOUO) This object has been deprecated and should not be
        implemented.

        (U//FOUO) The amount of time to wait before attempting to establish a 
        TLS connection with a PDE or OTNK Intermediary that supports TLS."
    ::= { hPDEInformation 3 }

hPDETLSEstablishmentMaxAttempts OBJECT-TYPE
    SYNTAX     Unsigned32
    MAX-ACCESS read-write
    STATUS     deprecated
    DESCRIPTION
        "(U//FOUO) This object has been deprecated and should not be
        implemented.

        (U//FOUO) The amount of retries attempted before giving up on this PDE
        or OTNK Intermediary due to consecutive failing attempts to try and 
        establish a TLS connection."
    ::= { hPDEInformation 4 }

-- **********************************************************************
-- Key Management Infrastructure [KMI] Control Objects
-- **********************************************************************

hKMIActiveIface OBJECT-TYPE
    SYNTAX     INTEGER { pde(1), mgc(2), fillPort(3), airGap(4) }
    MAX-ACCESS read-write
    STATUS     current
    DESCRIPTION
        "(U//FOUO) Establishes the current KMI active interface. The following 
        options are supported:

        (U//FOUO) [pde] - Product Delivery Enclave (HTTPS & HAIPE SA).
        (U//FOUO) [mgc] - Manager Client Node (HTTP)
        (U//FOUO) [fillPort] - Fill Port (DS-101).
        (U//FOUO) [airGap] - Air Gap Interface."
    ::= { hKMIControlObjects 1 }

    hKMIInitiatePALRetrieval OBJECT-TYPE
    SYNTAX     TruthValue
    MAX-ACCESS read-write
    STATUS     current
    DESCRIPTION
        "(U//FOUO) When set to [true], initiates the retrieval of the PAL from 
        the hKMIActiveIface. This may be used by the user to initiate the PAL 
        retrieval immediately, for instance in between the device's normally 
        scheduled PAL retrieval interval.  Note, this scalar is also used to 
        initiate PAL retrieval for non-PDE interface cases (e.g., when 
        hKMIActiveIface is set to 'mgc').

        (U//FOUO) When read, this object will always return [false]"
    ::= { hKMIControlObjects 2 } 

-- **********************************************************************
-- Manager Client Node [MGC] Ethernet Scalars
-- **********************************************************************

hMGCEnetIPAddressType OBJECT-TYPE
    SYNTAX     IPAddressType
    MAX-ACCESS read-write
    STATUS     current
    DESCRIPTION
        "(U//FOUO) The Internet Protocol Version, IPv4 or IPv6, of the IP 
        address of the Manager Client Node's Ethernet interface."
    ::= { hMGCEnetInformation 1 }

hMGCEnetIPAddress OBJECT-TYPE
    SYNTAX     IPAddress
    MAX-ACCESS read-write
    STATUS     current
    DESCRIPTION
        "(U//FOUO) The IP address of the MGC's Ethernet interface.  This object 
        is only required to be populated when the hKMIActiveIface is set to 
        [mgc]."
    ::= { hMGCEnetInformation 2 }

hMGCEnetHostname OBJECT-TYPE
    SYNTAX     OCTET STRING (SIZE(1..384))
    MAX-ACCESS read-write
    STATUS     current
    DESCRIPTION

        "(U//FOUO) The Fully Qualified Domain Name (FQDN) of the MGC."
    ::= { hMGCEnetInformation 3 }

-- **********************************************************************
-- Manager Client Node [MGC] AirGap Scalars
-- **********************************************************************

hMGCAGIPAddrType OBJECT-TYPE
    SYNTAX     IPAddressType
    MAX-ACCESS read-write
    STATUS     current
    DESCRIPTION
        "(U//FOUO) The Internet Protocol Version, IPv4 or IPv6, of the IP 
        address of the intermediary system's Air Gap interface."
    ::= { hMGCAirGapInformation 1 } 

hMGCAGIPAddress OBJECT-TYPE
    SYNTAX     IPAddress
    MAX-ACCESS read-write
    STATUS     current
    DESCRIPTION

        "(U//FOUO) The IP address of the intermediary system's Air Gap 
        interface.  This object is only required to be populated when the 
        hKMIActiveIface is set to [airGap]."
    ::= { hMGCAirGapInformation 2 } 

hMGCAGCurrentURI OBJECT-TYPE
    SYNTAX     OCTET STRING (SIZE(1..384))
    MAX-ACCESS read-write
    STATUS     current
    DESCRIPTION
        "(U//FOUO) This object contains the current URI (full path) of the file 
        to upload/download. For example, this may be a request which would be 
        uploaded to the URI or a PAL download where the ECU will retrieve the 
        data from the URI.

        (U//FOUO) The format of the URI will determine the Air Gap protocol.
        Note: not all protocols will be accepted by all ECUs. When an agent 
        receives a URI where the ECU does not support the protocol identified, 
        an SNMPv3 badValue exception will be sent.

        (U//FOUO) [tftp] - Trivial File Transfer Protocol (TFTP). For this 
        protocol, the URI hMGCAGCurrentURI/hMGCAGNextURI is of the form
        tftp://<hMGCAGIPAddress>/<location>, where <location> is the path
        of the file to upload/download.

        (U//FOUO) [http] - Hyper Text Transport Protocol (HTTP). For this 
        protocol, the URI hMGCAGCurrentURI/hMGCAGNextURI is of the form
        http://<hMGCAGIPAddress>/<location>, where <location> is the path 
        for the GET or POST operation.

        (U//FOUO) This object may be populated by a management station or 
        automatically by the agent.  For instance, the HAIPE's KMI process may 
        use the hMGCAGIPAddress and append a location in an automated fashion."
    ::= { hMGCAirGapInformation 3 }

hMGCAGNextURI OBJECT-TYPE
    SYNTAX     OCTET STRING (SIZE(1..384))
    MAX-ACCESS read-write
    STATUS     current
    DESCRIPTION
        "(U//FOUO) This object contains the next URI (full path) of the next 
        file to upload/download.  This path will be moved into the 
        hMGCAGCurrentURI when hMGCAGUpdateURI is triggered (i.e. set to 
        [true]).  When the URI is moved, the value of this object is cleared to 
        make ready for a new Next URI path if applicable.

        (U//FOUO) This object may be populated by a management station or 
        automatically by the agent.  For instance, the HAIPE's KMI process may 
        use the hMGCAGIPAddress and append a location in an automated fashion."
    ::= { hMGCAirGapInformation 4 }

hMGCAGUpdateURI OBJECT-TYPE
    SYNTAX     TruthValue
    MAX-ACCESS read-write
    STATUS     current
    DESCRIPTION
        "(U//FOUO) Updates the Air Gap URIs when set to [true].  The path 
        hMGCAGNextURI replaces the value in hMGCAGCurrentURI.  Additionally the 
        hMGCAGNextURI is cleared.

        (U//FOUO) File transfers may be triggered locally by an internal KMI 
        process; it is not required that the user actively set this object.
 
        (U//FOUO) When read, this object will always return [false]."
    ::= { hMGCAirGapInformation 5 }

hMGCAGTransfer OBJECT-TYPE
    SYNTAX     TruthValue
    MAX-ACCESS read-write
    STATUS     current
    DESCRIPTION
        "(U//FOUO) Initiates the Air Gap file transfer process when set to 
        [true].  This may be an upload, or a download of the object specfied at 
        hMGCAGCurrentURI. Initiation of hMGCAGTransfer may be done manually or 
        automatically in the course of ECU operations.

        (U//FOUO) When read, this object will always return [false]."
    ::= { hMGCAirGapInformation 6 }

hMGCAGTransferStatus OBJECT-TYPE
    SYNTAX     INTEGER { pending(1), complete(2), failed(3) }
    MAX-ACCESS read-only
    STATUS     current
    DESCRIPTION
        "(U//FOUO) Displays the status of the current or previous Air Gap file 
        transfer. The following status values are supported:

        (U//FOUO) [pending] - This status indicates that a file transfer is 
        slated to occur, but has yet to happen.

        (U//FOUO) [complete] - This status indicates that a file transfer has 
        completed.

        (U//FOUO) [failed] - This status indicates that the file transfer was 
        unsuccessful."
    ::= { hMGCAirGapInformation 7 }       

-- **********************************************************************
-- PDE Table
-- **********************************************************************
    
hPDETableCount OBJECT-TYPE
    SYNTAX     Unsigned32
    MAX-ACCESS read-only
    STATUS     current
    DESCRIPTION
        "(U//FOUO) The number of rows in the hPDETable."
    ::= { hPDEInformation 5 }

hPDETableLastChanged OBJECT-TYPE
    SYNTAX     TimeStamp
    MAX-ACCESS read-only
    STATUS     current
    DESCRIPTION
        "(U//FOUO) The value of sysUpTime the last time any entry in the
         hPDETable was modified, created, or deleted by either SNMP or other
         management method (e.g. via an HMI).

         (U//FOUO) Managers can use this object to ensure that no changes to
         configuration of this table have happened since the last time it
         examined the table.

         (U//FOUO) A value of 0 indicates that no entry has been changed since
         the agent initialized."
    ::= { hPDEInformation 6 }

hPDETable OBJECT-TYPE
    SYNTAX     SEQUENCE OF HPDETableEntry
    MAX-ACCESS not-accessible
    STATUS     current
    DESCRIPTION
        "(U//FOUO)  This table allows the manager to configure Product 
         Delivery Enclaves [PDEs] or Over-the-Network Keying [OTNK] 
         Intermediaries that the HAIPE will interface with in order to obtain
         Product Availability Lists [PALs] or other Key Management 
         Infrastructure [KMI] product.

         (U//FOUO)  Entries from downloaded PALs are used to dynamically 
         populate this table.  The manager will have the capability to choose
         which KMI product to download from the automatically populated rows
         in this table.

         (U//FOUO)  Once product is downloaded it will populate the appropriate
         MIB table.  If the hPDERequest column is configured for 
         'downloadAndInstall' then the destination is a MIB table that allows 
         local consumption of the KMI product.

         (U//FOUO)  When multiple PDEs or OTNK Intermediaries are available,
         the  Manager will determine priority by initiating the request with the
         PDE or OTNK Intermediary which it feels should have the highest
         priority.  If the Hypertext Transfer Protocol [HTTP] request fails 
         after it reaches the hPDERetryMaxAttempts, then the Manager will
         attempt an alternate PDE or OTNK Intermediary which it feels has the
         next highest priority."
    ::= { hPDEInformation 7 }

hPDETableEntry OBJECT-TYPE
    SYNTAX     HPDETableEntry
    MAX-ACCESS not-accessible
    STATUS     current
    DESCRIPTION
        "(U//FOUO)  A row in the hPDETable that provides access to download a 
	 KMI product."
    INDEX  { hPDEIndex }
    ::= { hPDETable 1 }

HPDETableEntry ::= SEQUENCE
{
       hPDEIndex                       Unsigned32,
       hPDEFromPAL                     Unsigned32,
       hPDEType                        INTEGER,
       hPDERequest                     INTEGER,
       hPDERequestStatus               INTEGER,
       hPDEURI                         OCTET STRING,
       hPDERowStatus                   RowStatus
}


hPDEIndex OBJECT-TYPE
    SYNTAX     Unsigned32
    MAX-ACCESS not-accessible
    STATUS     current
    DESCRIPTION
        "(U//FOUO) A unique numeric index that identifies a potential request to
         obtain KMI Product from a Product Delivery Enclave [PDE] or 
         Over-the-Network Keying [OTNK] Intermediary.  This column is the sole 
         index to the hPDETable."
    ::= { hPDETableEntry 1 }

hPDEFromPAL OBJECT-TYPE
    SYNTAX     Unsigned32
    MAX-ACCESS read-only
    STATUS     deprecated
    DESCRIPTION
        "(U//FOUO) This object has been deprecated and should not be
        implemented.

        (U//FOUO)  The hPDEIndex of the PAL which referenced the URI from
        which this row was created.  This allows tracking which entries in the
        hPDETable were dynamically created, and which PAL entry initiated the
        creation of the row.  For rows that are created by the manager, this
        column must not exist."
    ::= { hPDETableEntry 2 }

hPDEType OBJECT-TYPE
    SYNTAX     INTEGER { pal(1), ppk(2), appk(3), firefly(4), crl(5), pkc(6),
                         multiplePPK(7), multipleAPPK(8), multipleFFVS(9), 
                         iAIRekeyNotification(10), 
                         iAMRekeyNotification(11) }
    MAX-ACCESS read-create
    STATUS     current
    DESCRIPTION
        "(U//FOUO) The type of KMI product to be downloaded.  The type allows
         determination of the destination MIB table for the KMI product based 
         on the configured value of hPDERequest."
    ::= { hPDETableEntry 3 }

hPDERequest OBJECT-TYPE
    SYNTAX     INTEGER { downloadAndInstall(1), downloadAndStore(2), 
                         discardDownload(3) }
    MAX-ACCESS read-create
    STATUS     current
    DESCRIPTION
        "(U//FOUO)  This object signals the HAIPE to perform actions on the KMI
        product from the Product Delivery Enclave [PDE] or Over-the-Network 
	Keying [OTNK] Intermediary. The following types of actions are 
	supported:

        (U//FOUO) [downloadAndInstall] = Initiates an HTTP request to download
        the KMI product. After a successful download, the KMI product will be
        installed according to product type and format (ISSUE/FILL/etc.) and 
        an entry is to be configured in the appropriate MIB table if a 
        designated table exists based on hPDEType. For the following defined
        types the MIB destination is indicated, other actions/destinations may
        be appropriate for other products that become available from KMI:

        hPDEType           |  MIB Table Destination
        ---------------------------------------------
        (1) PAL            |  hPDETable  (this table)
        (2) PPK   (FILL)   |  hPrePlacedKeyTable 
        (2) PPK   (ISSUE)  |  hLoadedKeyTable         
        (3) APPK  (FILL)   |  hPrePlacedKeyTable 
        (3) APPK  (ISSUE)  |  hLoadedKeyTable 
        (4) FF    (FILL)   |  hFFTable
        (4) FF    (ISSUE)  |  hLoadedKeyTable          
        (5) CRL            |  hCRLTable
        (6) PKC            |  hPKCTable


        (U//FOUO) [downloadAndStore] = Optional for ECUs to support.  Initiates 
        an HTTP request to download the KMI product. After a successful 
        download, an entry is to be created in the appropriate MIB table. For 
        PPK/APPK/FFVS received in ISSUE format with hPDERequest set to 
        downloadAndStore the material is stored in the hLoadedKeyTable. For 
        PPK/APPK/FFVS received in FILL format the ECU copies the DS-100-1 tag 
        and duplicates it as an outer tag so the material can be stored in the 
        hLoadedKeyTable.

        (U//FOUO) [discardDownload] = Optional for ECUs to support.  Discards 
        the downloaded or downloading KMI product depending on the value of 
        hPDERequestStatus. If hPDERequestStatus is currently set at 'inProgress' 
        and hPDERequest is set to 'discardDownload', the KMI product will be 
        discarded when possible. A 'discardDownload' while hPDERequestStatus is 
        set  to 'controlError', 'downloadFailed', or 'installFailed' will cause 
        (1) the KMI product to be discarded if potentially downloaded and 
        (2) the hPDERequestStatus to revert to 'completeReady4Next'."
    ::= { hPDETableEntry 4 }

hPDERequestStatus OBJECT-TYPE
    SYNTAX     INTEGER { completeReady4Next(1), controlError(2), inProgress(3), 
	                 downloadFailed(4), installFailed(5), storeFailed(6) }
    MAX-ACCESS read-only
    STATUS     current
    DESCRIPTION
        "(U//FOUO) The status of the HTTP request operation. The following 
        status values are supported:

        (U//FOUO) [completeReady4Next] = This is the default state where the 
        HAIPE is ready to start a request for the KMI product. Between requests 
        this state can only be reached after successful operations or if 
        hPDERequest is set to 'discardDownload' during an operation.

        (U//FOUO) [controlError] - This state is reached when hPDERequest is set 
        to an invalid value. The *2 in the table below show the cases when this 
        state is reached based on the current hPDERequest and hPDERequestStatus 
        values.  To exit this state, hPDERequest would need to be configured to 
        'discardDownload' to guarantee that any ambiguous download is discarded 
        that could have occurred.

        (U//FOUO) [inProgress] - This state is reached when the device is either 
        currently performing an HTTP download of a KMI product or configuring 
        appropriate MIB tables conveying installation or storage (for key 
        transfer) of key material.

        (U//FOUO) [downloadFailed] - This state is reached after a failure 
        occurs during an HTTP download of a KMI product when hPDERequest was 
        configured to either 'downloadAndStore' or 'downloadAndInstall'. 

        (U//FOUO) [installFailed] - This state is reached after a failure occurs 
        during the install of the downloaded KMI product when hPDERequest was 
        configured to 'downloadAndInstall'. 

        (U//FOUO) [storeFailed] - This state is reached after a failure occurs 
        during the store (for key transfer) of the downloaded KMI product when 
        hPDERequest was configured to 'downloadAndStore'. This enumeration is 
        optional for ECUs to support.

        (U//FOUO)  The table below shows the possible next state for the 
        hPDERequestStatus column based on its current state and the 
        configuration of the hPDERequest column.

                                 |==========================|
                                 |         hPDERequest:     |
                                 |==========================|
                                 |download|download|        |
          ====================   |  And   |  And   |discard |
          |hPDERequestStatus:  \ |Install | Store  |Download|
          =======================+--------+--------+--------+
                                 | 3 -> 1 | 3 -> 1 |        |
          (1)completeReady4Next  | 3 -> 4 | 3 -> 4 | *2     |
                                 | 3 -> 5 | 3 -> 6 |        |
          -----------------------+--------+--------+--------+
          (2)controlError        | *2     | *2     |  1     |
          -----------------------+--------+--------+--------+
          (3)inProgress          | *2     | *2     |  1     |
          -----------------------+--------+--------+--------+
          (4)downloadFailed      | *2     | *2     |  1     |
          -----------------------+--------+--------+--------+
          (5)installFailed       | *2     | *2     |  1     |
          -----------------------+--------+--------+--------+
          (6)storeFailed         | *2     | *2     |  1     |
          -----------------------+--------+--------+--------+

        (U//FOUO) Note 1: *2 are transitions that happen only under incorrect 
        hPDERequest configurations.  To exit the 'controlError' state, it is 
        necessary for hPDERequest to be configured to 'discardDownload' in order 
        to guarantee that any ambiguous download is discarded. The *2 
        transitions should not occur under normal conditions.

        (U//FOUO) Note 2: Normal uninterrupted transitions after configuration 
        of the hPDERequest are shown with the following notation: 'a -> b'.  
        Where 'a' is the next state transition followed by state 'b'.  When 
        multiple rows are shown such as: 

          'a -> b'
          'a -> c'

        (U//FOUO) This implies that the next state is 'a' but the state after 
        'a' can be either 'b' or 'c'."
    ::= { hPDETableEntry 5 }

hPDEURI OBJECT-TYPE
    SYNTAX     OCTET STRING (SIZE(1..384))
    MAX-ACCESS read-create
    STATUS     current
    DESCRIPTION
        "(U//FOUO)  The URI that defines where to obtain KMI product from the 
        Product Delivery Enclave [PDE] or Over-the-Network Keying [OTNK] 
        Intermediary.  For PAL entries that contain a PKC rekey or issuance 
        notification, this is the fixed URI defined for certificate notification 
        retrieval.

        (U//FOUO)  The hostname in the hPDEURI is matched with the 
        hPDEMappingHostname (of hPDEMappingTable) to provide a link to its
        associated PT IP address located in the hPDEMappingPTIPAddress (of 
        hPDEMappingTable).

        (U//FOUO) Note:  'https' implies TLS, while 'http' implies no TLS."
    ::= { hPDETableEntry 6 }

hPDERowStatus OBJECT-TYPE
    SYNTAX     RowStatus
    MAX-ACCESS read-create
    STATUS     current
    DESCRIPTION
        "(U//FOUO) The status of the row, by which new entries may be created,
         or old entries deleted from this table.

         (U//FOUO) Entries created within this table may not become active
         unless all read-create columns in this table have valid values,
         as detailed by each individual column's description.

         (U//FOUO) At a minimum, implementations must support createAndGo,
         active, and destroy management functions. Support for createAndWait,
         notInService, and notReady management functions is optional."
    ::= { hPDETableEntry 7 }

-- **********************************************************************
-- PDE Mapping Table
-- **********************************************************************
    
hPDEMappingTableCount OBJECT-TYPE
    SYNTAX     Unsigned32
    MAX-ACCESS read-only
    STATUS     current
    DESCRIPTION
        "(U//FOUO) The number of rows in the hPDEMappingTable."
    ::= { hPDEInformation 8 }

hPDEMappingTableLastChanged OBJECT-TYPE
    SYNTAX     TimeStamp
    MAX-ACCESS read-only
    STATUS     current
    DESCRIPTION
        "(U//FOUO) The value of sysUpTime the last time any entry in the
         hPDEMappingTable was modified, created, or deleted by either SNMP or 
         other management method (e.g. via an HMI).

         (U//FOUO) Managers can use this object to ensure that no changes to
         configuration of this table have happened since the last time it
         examined the table.

         (U//FOUO) A value of 0 indicates that no entry has been changed since
         the agent initialized."
    ::= { hPDEInformation 9 }

hPDEMappingTable OBJECT-TYPE
    SYNTAX     SEQUENCE OF HPDEMappingTableEntry
    MAX-ACCESS not-accessible
    STATUS     current
    DESCRIPTION
        "(U//FOUO)  This table allows configuration of Product 
         Delivery Enclaves [PDEs] or Over-the-Network Keying [OTNK] 
         Intermediaries that the HAIPE will interface with in order to obtain
         Product Availability Lists [PALs] or other Key Management 
         Infrastructure [KMI] product.

        (U//FOUO)   This table provides the mapping between the hostname and
         PT IP address of the configured PDE or Over-the-Network Keying [OTNK] 
         Intermediary.  A row in the hPDEMappingTable links the PT IP address 
         from this table based on the hostname in the hPDEURI."
    ::= { hPDEInformation 10 }

hPDEMappingTableEntry OBJECT-TYPE
    SYNTAX     HPDEMappingTableEntry
    MAX-ACCESS not-accessible
    STATUS     current
    DESCRIPTION
        "(U//FOUO)  A row in the hPDEMappingTable that provides mapping of 
         hostname to PT IP address."
    INDEX  { hPDEMappingIndex }
    ::= { hPDEMappingTable 1 }

HPDEMappingTableEntry ::= SEQUENCE
{
       hPDEMappingIndex               Unsigned32,
       hPDEMappingPTIPAddressType     IPAddressType,
       hPDEMappingPTIPAddress         IPAddress,
       hPDEMappingHostname            SnmpAdminString,
       hPDEMappingRowStatus           RowStatus
}


hPDEMappingIndex OBJECT-TYPE
    SYNTAX     Unsigned32
    MAX-ACCESS not-accessible
    STATUS     current
    DESCRIPTION
        "(U//FOUO) A unique numeric index that identifies hostname to PT IP
         address mapping for a Product Delivery Enclave [PDE] or 
         Over-the-Network Keying [OTNK] Intermediary.  This column is the sole
         index to the hPDEMappingTable. This column conveys the priority in 
         which PDEs are to be contacted."
    ::= { hPDEMappingTableEntry 1 }

hPDEMappingPTIPAddressType OBJECT-TYPE
    SYNTAX     IPAddressType
    MAX-ACCESS read-create
    STATUS     current
    DESCRIPTION
        "(U//FOUO) The Internet Protocol Version, IPv4 or IPv6, of the PT IP
	 address associated with the Product Delivery Enclave [PDE].
	 Specifically, the value of this property determines the size and format
	 of hPDEMappingPTIPAddress."
    ::= { hPDEMappingTableEntry 2 }    

hPDEMappingPTIPAddress OBJECT-TYPE
    SYNTAX     IPAddress
    MAX-ACCESS read-create
    STATUS     current
    DESCRIPTION
        "(U//FOUO)  The PT IP address associated with the Product Delivery 
	 Enclave [PDE] or Over-the-Network Keying [OTNK] Intermediary configured
	 in the hPDEMappingHostname column."
    ::= { hPDEMappingTableEntry 3 }

hPDEMappingHostname OBJECT-TYPE
    SYNTAX     SnmpAdminString
    MAX-ACCESS read-create
    STATUS     current
    DESCRIPTION
        "(U//FOUO)  The fully qualified domain name (FQDN) of the Product 
        Delivery  Enclave [PDE] or Over-the-Network Keying [OTNK] 
        Intermediary where KMI product is requested."
    ::= { hPDEMappingTableEntry 4 }

hPDEMappingRowStatus OBJECT-TYPE
    SYNTAX     RowStatus
    MAX-ACCESS read-create
    STATUS     current
    DESCRIPTION
        "(U//FOUO) The status of the row, by which new entries may be created,
         or old entries deleted from this table.

         (U//FOUO) At a minimum, implementations must support createAndGo
         and destroy management functions. Support for createAndWait,
         notInService, and notReady management functions is optional."
    ::= { hPDEMappingTableEntry 5 }


END
