--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-FEATURE-HIERARCHY-MIB  DEFINITIONS  ::= BEGIN

IMPORTS
    haipe                                       FROM HAIPE-ASSIGNMENTS-MIB
    MODULE-IDENTITY                             FROM SNMPv2-SMI;

haipev4FeatureHierarchyMIB MODULE-IDENTITY
    LAST-UPDATED "201303292338Z"
    ORGANIZATION "HAIPE PO"
    CONTACT-INFO
         "(U//FOUO) Not Available"
    DESCRIPTION
        "(U//FOUO) This MIB defines the HAIPE MIB features in
        hierarchal MIB tree assignments.  It acts as a reservation
        mechanism for other MIB sets to be anchored below it.  New
        HAIPE related feature sets will get individual assignment
        numbers within this tree."
    REVISION     "201303292338Z"
    DESCRIPTION  "(U//FOUO) HAIPE MIB 4.1.2 Final"		
    ::= { haipe 100 }

--
-- Textual Conventions is { haipev4FeatureHierarchyMIB 1 }
--

--
-- Compliance is { haipev4FeatureHierarchyMIB 2 }
--

--
-- Traffic Protection features
--
hv4TrafficProtection   OBJECT IDENTIFIER ::= { haipev4FeatureHierarchyMIB 3 }

--
-- Discovery features
--
hv4Discovery           OBJECT IDENTIFIER ::= { haipev4FeatureHierarchyMIB 4 }

--
-- Networking features
--
hv4Networking          OBJECT IDENTIFIER ::= { haipev4FeatureHierarchyMIB 5 }

--
-- Management features
--
hv4Management          OBJECT IDENTIFIER ::= { haipev4FeatureHierarchyMIB 6 }

--
-- Bandwidth Management features
--
hv4BandwidthManagement OBJECT IDENTIFIER ::= { haipev4FeatureHierarchyMIB 7 }

--
-- ROHC features
--
hv4ROHC                OBJECT IDENTIFIER ::= { haipev4FeatureHierarchyMIB 8 }

--
-- DMDK features
--
hv4DMDK                OBJECT IDENTIFIER ::= { haipev4FeatureHierarchyMIB 9 }

--
-- KMI features
--
hv4KMI                 OBJECT IDENTIFIER ::= { haipev4FeatureHierarchyMIB 10 }

--
-- RUZ Client features
--
hv4RUZ                 OBJECT IDENTIFIER ::= { haipev4FeatureHierarchyMIB 11 }

--
-- RCIK features
--
hv4RCIK                OBJECT IDENTIFIER ::= { haipev4FeatureHierarchyMIB 12 }

--
-- CRL Transfer features
--
hv4CRLTransfer         OBJECT IDENTIFIER ::= { haipev4FeatureHierarchyMIB 13 }
END
