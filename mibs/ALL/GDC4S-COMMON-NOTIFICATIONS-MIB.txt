--BEGIN Revision History
--
--
--20160106 M. Coughlin - Added the commonAuditUploadEvents
--
--20100826 R. Berman DRN MIB00192 - Added the commonQkeyEvents and associated event
--variables.
--
--hPPKSegment
--
--20091028 - DRN MIB00183 - Added commonKeyTransferEvents and associated Notification-type
--objects.  Also added commonKeyTransferEventsVarObjects.
--
--20091027 - DRN MIB00182 - Add Transport Mode enumerations numbers 9, 10 & 11
--to commonFFTEKDeletedReason.
--
--20091027 - MIB00181 - Add enumeration invalidNATOAPayload( 27 ) to
--commonFFNegotiaFailureReason notification-object.
--
--20091012 - MIB00179 - Added enumerations invalidTransportPayload(25) and
--transportAddressNotSet(26)to commonFFNegotiaFailureReason notification-object.
--
--MIB00175 - 20090902 - Added 7th enumeration [resetPIN( 7 )] to commonPinActivity
--notification-object.
--
--20090409 - T. Huemiller - Revised commonSNMPUserUpdate notification. Added
--commonSNMPTableRowName notification object.
--
--DRN MIB00154 - 20090312 - Add hStationID and hrSystemDate to commonIPv6FavoredAddrChanged
--and commonIPv4AddrChanged notifications.
--
--DRN MIB00153 - 20090311 - Removed enumerations invalidKeyMaterial( 5 ) &
--keyMaterialUnsupported( 6 ), Added enumerations 5-11 for commonPACFailedFillReason
--
--DRN MIB00150 - 20090227 - Add enumeration storageCapacityExceeded( 12 )
--to commonFFFailedFillReason notification-object.
--
--DRN MIB00148 - 20090227 - Added enumeration superseded( 5 ) to commonFFVSDeleteReason.
--
--DRN MIB00147 - 20090227 - Add PSEQNError2.
--
--DRN MIB00144 - 20090227 - Deleted commonCorruptPACResponse notification-object and
--commonCorruptPACDetected notification.
--
--DRN MIB00140 20081217 - added enumeration fillDisabled( 11 ) to commonFFVSDeleteReason.
--
--DRN MIB00141 20081217 - Added PAC Moduli notifications and notification objects.
--
--DRN MIB00138 20081008 in commonFFTEKCreated, commonFFTEKDeleted and commonFFNegotiationFailure2,
--replaced hTPSAAddressType and hTPSARemoteCTAddress with commonAddressType and commonRemoteCTAddress.
--Added notification objects commonAddressType and commonRemoteCTAddress.
--
--
--DRN MIB00135 20081003 In commonFFVSFillOK2 notification, changed object
--commonFFNextVectoryPresent to hFFNextVector.
--
--DRN00134 20081003 Added commonKeyFilled Notification object to
--commonSecurityEvents group and in corformance to
--commonSecurityNotifs Notification-Group.
--
--20080711 - Deleted commonFTRIncrease notification and commonFTRCount notification
--object, as the operator is expected to manually keep track of how many times
--the FTR CIK has been used.

GDC4S-COMMON-NOTIFICATIONS-MIB DEFINITIONS ::= BEGIN
    IMPORTS
    MODULE-IDENTITY, NOTIFICATION-TYPE, OBJECT-TYPE,
    Unsigned32, Counter64, Integer32
        FROM SNMPv2-SMI
    NOTIFICATION-GROUP, OBJECT-GROUP
        FROM SNMPv2-CONF
    SnmpAdminString
        FROM SNMP-FRAMEWORK-MIB
    DateAndTime, AutonomousType, TEXTUAL-CONVENTION,
    TruthValue
        FROM SNMPv2-TC
    usmUserSecurityName
        FROM SNMP-USER-BASED-SM-MIB
    hrSystemDate
        FROM HOST-RESOURCES-MIB
    hTPiSPI, hTPiDestinationAddress, hTPiDestinationAddressType,
    hTPSAIntegrityAlgorithm, hPPKUsageType,
    hFFKMID, hFFAlgorithmPrivilege, hFFSecurityLevels,
    hFFMaterialType, hFFExpiration, hFFPartitionCode,
    hFFAuthority, hFFNextVector, hFFEnhancedFFTag,
    hPPKEffectiveDate, hPPKSecurityLevel, hPPKTrafficEncryptAlgorithm,
    hTPSAspi, hIPhFFSAFF, hIPhFFSADSCP, hIPhFFSADSCPValue,
    hIPhFFSAECN, hIPhFFSADFBit, hIPhFFSAConnectionType,
    KMID, hTPSAAddressType, hTPSALocalCTAddress,
    hTPSARemoteCTAddress, hTPSAPTAddressType,
    hTPSALocalPTAddress, hTPSARemotePTAddress,
    hTPSAConnectionType, hTPSAECN, hTPSADSCP,
    hTPSADSCPValue, hTPSADFBit, hTPSACryptoBlockSize,
    hTPSAPPK, hPPKEKKeyType, hPPKEKUniversalID,
    hPPKChainEffectiveDate, hTPSAReuseSpi, hTPSADIndexType,
    hLocalCKLReason, hPPKSegment
        FROM HAIPE-TRAFFIC-PROTECTION-MIB
    hNetSourceAddress, hNetSourceAddressType,
    hIfv6Side, hIfv4Side
        FROM HAIPE-NETWORKING-MIB
    hStationID
        FROM HAIPE-MANAGEMENT-MIB
    cikId, commonOvertemperatureEnvironmentalFault,
    commonFanEnvironmentalFault, gdc4sEncryptionProductsCommonMIB,
    commonACLKMIDRowStatus
        FROM GDC4S-ENCRYPTION-PRODUCTS-COMMON-MIB
    nePPKUseConfig, nePPKAssignmentChainID, nePPKAssignmentCtAddressType,
    nePPKAssignmentCtAddr, neACLKMID, neUnInstalledPACBaseType,
    neUnInstalledPACCOI, neUnInstalledPACUserID,
    neUnInstalledPACSourceID, neUnInstalledPACNationalID,
    neUnInstalledPACID, neUninstalledTAType,
    neUninstalledTAShortTitle, neUninstalledTAKMID
        FROM NETWORKENCRYPTOR-ENTERPRISE-MIB
    InetAddress, InetAddressType
        FROM INET-ADDRESS-MIB
    ifIndex
        FROM IF-MIB
    hKTLoadedKeyUse, hKTLoadedKeyClassification,
    hKTOOBClientAddressType, hKTOOBClientAddress,
    hKTOOBClientKeyFile, hKTOOBKeyFileShortTitle,
    hKTOOBKeyFileEdition, hKTOOBKeyFileSegment,
    hKTOOBKeyFileRegister, hKTIBClientAddressType,
    hKTLoadedKeySegment
        FROM HAIPE-KEY-TRANSFER-MIB;

    commonNotifications MODULE-IDENTITY
        LAST-UPDATED	    "200708161030Z"
        ORGANIZATION	    "General Dynamics C4 Systems"
        CONTACT-INFO        "Infosec Support
                            General Dynamics C4
                            Systems Corporation
                            77 A Street
                            Needham Heights, MA
                            02494-2806
                            Telephone: 877-230-0236
                            email: INFOSECSUPPORT@GDC4S.COM"
        DESCRIPTION         "This MIB module defines the notification and notification
                            variable objects used in support of communications
                            products developed by General Dynamics C4 Systems."

        REVISION	    "200708161030Z"
        DESCRIPTION         "Updates for GigE/Mini R3.4"
        REVISION	    "200608141433Z"
        DESCRIPTION         "initial version of this module"
        REVISION	    "201009301611Z"
        DESCRIPTION         "Changed neACLKMID to commonACLKMID in the commonACLUpdated
                            event in commonACLUpdated3."
        REVISION	    "201010050606Z"
        DESCRIPTION         "Added commonKEKCreated notification to commonSecurityEvents."
        REVISION	    "201011190744Z"
        DESCRIPTION         "Updated commonACLUpdated3 notification to use
                            ACL row status instead of KMID since KMID is
                            defined as non-accessible."
        ::= { gdc4sEncryptionProductsCommonMIB 2 }

    --BEGIN common notification textual conventions
    CommonEnableValue ::= TEXTUAL-CONVENTION
        STATUS		    deprecated
        DESCRIPTION         "(U//FOUO) Deprecated - EnableValue objects reported
                            using ConfigDataValue Objects. (U//FOUO) The
                            two states of a configuration object, DISABLED
                            and ENABLED."
        SYNTAX		    INTEGER {
                                disabled( 1 ),
                                enabled( 2 )
                            }

    CommonIfIndex ::= TEXTUAL-CONVENTION
        STATUS		    current
        DESCRIPTION         "(U//FOUO) The indication of the interface."
        SYNTAX		    INTEGER {
                                pt( 1 ),
                                ct( 2 ),
                                other( 3 ),
                                ptSensor( 4 ),
                                ctSensor( 5 )
                            }

    CommonIfSpeedMode ::= TEXTUAL-CONVENTION
        STATUS		    current
        DESCRIPTION         "(U//FOUO) The indication of the interface speed
                            mode."
        SYNTAX		    INTEGER {
                                disabled( 0 ),
                                speedMode10MbpsHalf( 1 ),
                                speedMode10MbpsFull( 2 ),
                                speedMode100MbpsHalf( 4 ),
                                speedMode100MbpsFull( 8 ),
                                speedMode1000MbpsHalf( 16 ),
                                speedMode1000MbpsFull( 32 )
                            }



    --END common notification textual conventions
    commonEvents OBJECT IDENTIFIER ::= { commonNotifications 1 }

    commonSecurityEvents OBJECT IDENTIFIER ::= { commonEvents 1 }

    commonTamper NOTIFICATION-TYPE
        OBJECTS	{
        		commonZeroizeReason
        	}
        STATUS		    current
        DESCRIPTION         "(U//FOUO) Notification of a Tamper Event in the
                            device."
        ::= { commonSecurityEvents 1 }

    commonZeroize NOTIFICATION-TYPE
        OBJECTS	{
        		usmUserSecurityName,
        		commonZeroizeReason
        	}
        STATUS		    current
        DESCRIPTION         "(U//FOUO) This notification is generated in response
                            to a Zeroize Command."
        ::= { commonSecurityEvents 2 }

    commonSsoPinActivity NOTIFICATION-TYPE
        OBJECTS	{
        		commonPinActivity
        	}
        STATUS		    current
        DESCRIPTION         "(U//FOUO) Notification of activity relating to
                            SSO PIN"
        ::= { commonSecurityEvents 3 }

    commonRealTimeClockSet NOTIFICATION-TYPE
        OBJECTS	{
        		usmUserSecurityName,
        		commonUpdateSystemDate
        	}
        STATUS		    current
        DESCRIPTION         "(U//FOUO) Notification that the Real Time Clock
                            has been set via the hrSystemDate object in the
                            HOST-RESOURCES-MIB."
        ::= { commonSecurityEvents 4 }

    commonHWSecurCriticalFault NOTIFICATION-TYPE
        OBJECTS	{
        		commonSecurCritFltType,
        		commonSecCritPrimeFirstReg,
        		commonSecCritPrimeSumReg,
        		commonSecCritSubFirstReg,
        		commonSecCritSubSumReg
        	}
        STATUS		    current
        DESCRIPTION         "(U//FOUO) Notification of a Security Critical
                            Fault in Hardware."
        ::= { commonSecurityEvents 5 }

    commonSWSecurCriticalFault NOTIFICATION-TYPE
        OBJECTS	{
        		commonSecurCritFltType,
        		commonSWFltAddressID,
        		commonSWFltFileName,
        		commonSWFltLineNum,
        		commonSWFltArg1,
        		commonSWFltArg2,
        		commonSWFltArg3,
        		commonSWFltArg4,
        		commonSWFltStackDump
        	}
        STATUS		    current
        DESCRIPTION         "(U//FOUO) A Security Critical Fault in Software"
        ::= { commonSecurityEvents 6 }

    commonPrivilegItemModToggle NOTIFICATION-TYPE
        OBJECTS	{
        		usmUserSecurityName,
        		commonPrivModItemName,
        		commonOrigEnableValue,
        		commonNewEnableValue
        	}
        STATUS		    deprecated
        DESCRIPTION         "(U//FOUO) Notification that enable/disable configuration
                            setting was modified."
        ::= { commonSecurityEvents 7 }

    commonPrivilegItemValue NOTIFICATION-TYPE
        OBJECTS	{
        		usmUserSecurityName,
        		commonPrivModItemName,
        		commonOrigConfigDataValue,
        		commonNewConfigDataValue
        	}
        STATUS		    current
        DESCRIPTION         "(U//FOUO) Notification of the change of a configuration
                            data value requiring SSO-Privilege to change."
        ::= { commonSecurityEvents 8 }

    commonEspBipError NOTIFICATION-TYPE
        OBJECTS	{
        		hTPiSPI,
        		commonBIPErrorCount
        	}
        STATUS		    deprecated
        DESCRIPTION         "(U//FOUO) Notification of a Bit Interleaved Parity
                            Error for the Encapsulated Security Payload."
        ::= { commonSecurityEvents 9 }

    commonDiagnosticFailed NOTIFICATION-TYPE
        OBJECTS	{
        		commonDiagnosticId,
        		commonDiagFailArg1,
        		commonDiagFailArg2,
        		commonDiagFailArg3,
        		commonDiagFailArg4
        	}
        STATUS		    current
        DESCRIPTION         "(U//FOUO) This notification identifies a software
                            diagnostic process has failed and includes four
                            arguments related to the failed process that
                            can be passed to the log."
        ::= { commonSecurityEvents 10 }

    commonKEKUpdated NOTIFICATION-TYPE
        OBJECTS	{
        		commonKEKId
        	}
        STATUS		    current
        DESCRIPTION         "(U//FOUO) Notification that the KEK has been updated."
        ::= { commonSecurityEvents 11 }

    commonConfigurationReset NOTIFICATION-TYPE
        OBJECTS	{
        		commonConfigurationResetType
        	}
        STATUS		    current
        DESCRIPTION         "(U//FOUO) Notifcation that some or all of the
                            unit's configuration has been reset."
        ::= { commonSecurityEvents 12 }

    commonConfigConflict NOTIFICATION-TYPE
        OBJECTS	{
        		hStationID,
        		hrSystemDate,
        		commonConfigConflictDescription
        	}
        STATUS		    current
        DESCRIPTION         "(U//FOUO) Notification that an otherwise valid
                            SNMP SET failed due to a configuration conflict
                            within the managed device. This notification
                            will be used to supplement the SNMP error responses
                            Inconsistent Name and Inconsistent Value to identify
                            the configuration conflict more specifically."
        ::= { commonSecurityEvents 13 }

    commonHWSecurCriticalFault2 NOTIFICATION-TYPE
        OBJECTS	{
        		commonSecCritPrimeFirstReg,
        		commonSecCritPrimeSumReg,
        		commonSecCritSubFirstReg,
        		commonSecCritSubSumReg,
        		commonHWFltArg1,
        		commonHWFltArg2,
        		commonHWFltArg3,
        		commonHWFltArg4
        	}
        STATUS		    current
        DESCRIPTION         "(U//FOUO) Notification of a Security Critical
                            Fault in Hardware."
        ::= { commonSecurityEvents 14 }

    commonSWSecurCriticalFault2 NOTIFICATION-TYPE
        OBJECTS	{
        		commonSecCritPrimeFirstReg,
        		commonSecCritPrimeSumReg,
        		commonSecCritSubFirstReg,
        		commonSecCritSubSumReg,
        		commonSWFltAddressID,
        		commonSWFltFileName,
        		commonSWFltLineNum,
        		commonSWFltArg1,
        		commonSWFltArg2,
        		commonSWFltArg3,
        		commonSWFltArg4,
        		commonSWFltStackDump
        	}
        STATUS		    current
        DESCRIPTION         "(U//FOUO) Notification of a Security Critical
                            Fault in Software."
        ::= { commonSecurityEvents 15 }

    --DRN MIB00134 20081003  Added notification object commonKeyFilled
    commonKeyFilled NOTIFICATION-TYPE
        OBJECTS	{
        		hStationID,
        		hrSystemDate
        	}
        STATUS		    current
        DESCRIPTION         "(U//FOUO) This notification indicates that one
                            or more keys were successfully filled."
        ::= { commonSecurityEvents 16 }

    commonUnIdentifiedKeyFillError NOTIFICATION-TYPE
        OBJECTS	{
        		usmUserSecurityName,
        		commonUnIdentifiedKeyFillErrorReason
        	}
        STATUS		    current
        DESCRIPTION         "(U//FOUO) A notification that unidentifiable data
                            filled to the ECU fill port was not accepted."
        ::= { commonSecurityEvents 17 }

    commonKEKCreated NOTIFICATION-TYPE
        OBJECTS	{
        		commonKEKId
        	}
        STATUS		    current
        DESCRIPTION         "(U//FOUO) Notification to announce the creation
                            of a GSK."
        ::= { commonSecurityEvents 18 }

    commonCIKEvents OBJECT IDENTIFIER ::= { commonEvents 2 }

    commonFTRKSDCreated NOTIFICATION-TYPE
        STATUS		    current
        DESCRIPTION         "(U//FOUO) Notification that a Field Tamper Recovery
                            CIK was created."
        ::= { commonCIKEvents 1 }

    commonCIKCreated NOTIFICATION-TYPE
        OBJECTS	{
        		usmUserSecurityName,
        		cikId,
        		commonCIKCreateReason
        	}
        STATUS		    current
        DESCRIPTION         "(U//FOUO) This notification indicates a CIK was
                            just created, and identifies the CIK Number and
                            what initiated the CIK creation."
        ::= { commonCIKEvents 2 }

    commonCIKDeleted NOTIFICATION-TYPE
        OBJECTS	{
        		usmUserSecurityName,
        		cikId
        	}
        STATUS		    current
        DESCRIPTION         "(U//FOUO) This notification indicates a CIK was
                            just deleted, and identifies the deleted CIK."
        ::= { commonCIKEvents 3 }

    commonCikActive NOTIFICATION-TYPE
        OBJECTS	{
        		cikId
        	}
        STATUS		    current
        DESCRIPTION         "(U//FOUO) This notification indicates the identified
                            CIK was successfully activated during startup
                            or restart."
        ::= { commonCIKEvents 4 }

    commonCikFailed NOTIFICATION-TYPE
        OBJECTS	{
        		cikId,
        		commonFailedCikOperation,
        		commonFailedCikReason
        	}
        STATUS		    current
        DESCRIPTION         "(U//FOUO) This notification indicates the CIK
                            that failed, the activity (activation or creation)
                            and the reason it failed (read fault, write fault
                            or invalid cik). The cikID is set to 99 when
                            a blank KSD, unreadable KSD, or CIK from another
                            unit is inserted during activation"
        ::= { commonCIKEvents 5 }

    --T. Huemiller - commonFTRIncrease deleted
    commonFFEvents OBJECT IDENTIFIER ::= { commonEvents 3 }

    commonFFVSFillOK NOTIFICATION-TYPE
        OBJECTS	{
        		usmUserSecurityName,
        		hFFKMID,
        		hFFAlgorithmPrivilege,
        		hFFSecurityLevels,
        		hFFMaterialType,
        		hFFExpiration,
        		hFFPartitionCode,
        		hFFAuthority,
        		hFFNextVector
        	}
        STATUS		    deprecated
        DESCRIPTION         "(U//FOUO) Deprecated - Replaced by commonFFVSFillOK2.
                            (U//FOUO) This notification indicates a FireFly
                            Vector Set was successfully filled. (U//FOUO)
                            Universal ID and Edition is derived from instance
                            of hFireflyTable indexed by hFFKMID."
        ::= { commonFFEvents 1 }

    commonFFVSFillFailed NOTIFICATION-TYPE
        OBJECTS	{
        		usmUserSecurityName,
        		commonFFFailedFillReason
        	}
        STATUS		    current
        DESCRIPTION         "(U//FOUO) This notification indicates the failure
                            of an attempted fill of a FireFly Vector Set."
        ::= { commonFFEvents 2 }

    commonFFVSDeleted NOTIFICATION-TYPE
        OBJECTS	{
        		usmUserSecurityName,
        		hFFKMID,
        		commonFFVSDeleteReason
        	}
        STATUS		    current
        DESCRIPTION         "(U/FOUO) This notification indicates the filled
                            FFVS, current or current/next has been deleted.
                            (U//FOUO) Universal ID and Edition is derived
                            from instance of hFireflyTable indexed by hFFKMID."
        ::= { commonFFEvents 3 }

    commonFFVSExpired NOTIFICATION-TYPE
        OBJECTS	{
        		hFFKMID,
        		hFFExpiration
        	}
        STATUS		    current
        DESCRIPTION         "(U//FOUO) Indicates the FFVS filled in this device
                            has expired. (U//FOUO) Universal ID and Edition
                            is derived from instance of hFireflyTable indexed
                            by hFFKMID."
        ::= { commonFFEvents 4 }

    commonACLUpdated NOTIFICATION-TYPE
        OBJECTS	{
        		usmUserSecurityName,
        		neACLKMID,
        		commonACLUpdateAction
        	}
        STATUS		    current
        DESCRIPTION         "(U//FOUO) Notification that the Access Control
                            List was updated."
        ::= { commonFFEvents 5 }

    commonFFNegotiationFailure NOTIFICATION-TYPE
        OBJECTS	{
        		hNetSourceAddressType,
        		hNetSourceAddress,
        		commonFFSARole,
        		commonFFNegotiaFailureReason
        	}
        STATUS		    deprecated
        DESCRIPTION         "(U//FOUO) Deprecated - Replaced by commonFFNegotiationFailure2.
                            (U//FOUO) This Notification identifies the failure
                            of an FFVS IKE Negotiation."
        ::= { commonFFEvents 6 }

    commonLocalCKLUpdated NOTIFICATION-TYPE
        OBJECTS	{
        		usmUserSecurityName,
        		hLocalCKLReason,
        		commonCKLUpdateAction
        	}
        STATUS		    current
        DESCRIPTION         "(U//FOUO) Notification that the local compromised
                            key list was updated. hLocalCKLIDBegin and hLocalCKLIDEnd
                            are the instance of hLocalCKLReason and should
                            be logged in all audit log entries and displayed
                            in all traps."
        ::= { commonFFEvents 7 }

    commonFFSPDTemplateActivated NOTIFICATION-TYPE
        OBJECTS	{
        		hIPhFFSAFF,
        		hIPhFFSADSCP,
        		hIPhFFSADSCPValue,
        		hIPhFFSAECN,
        		hIPhFFSADFBit,
        		hIPhFFSAConnectionType
        	}
        STATUS		    current
        DESCRIPTION         "(U//FOUO) Notification that a FF SPD template
                            was activated. hIPhFFSAName and hIPhFFSAPriority
                            are provided as instances of hIPhFFSAFF."
        ::= { commonFFEvents 8 }

    commonFFSPDTemplateDestroyed NOTIFICATION-TYPE
        OBJECTS	{
        		hIPhFFSAFF,
        		hIPhFFSADSCP,
        		hIPhFFSADSCPValue,
        		hIPhFFSAECN,
        		hIPhFFSADFBit,
        		hIPhFFSAConnectionType
        	}
        STATUS		    current
        DESCRIPTION         "(U//FOUO) Notification that a FF SPD template
                            was destroyed. hIPhFFSAName and hIPhFFSAPriority
                            are provided as instances of hIPhFFSAFF."
        ::= { commonFFEvents 9 }

    commonFFTEKCreated NOTIFICATION-TYPE
        OBJECTS	{
        		commonSAIndex,
        		commonRemoteFFKMID,
        		commonRemoteSAspi,
        		commonAddressType,
        		commonRemoteCTAddress,
        		commonFFSARole
        	}
        STATUS		    current
        DESCRIPTION         "(U//FOUO) This notification identifies the creation
                            of a TEK as the result of an IKE negotiation."
        ::= { commonFFEvents 10 }

    commonFFTEKDeleted NOTIFICATION-TYPE
        OBJECTS	{
        		commonSAIndex,
        		commonAddressType,
        		commonRemoteCTAddress,
        		commonFFTEKDeletedReason
        	}
        STATUS		    current
        DESCRIPTION         "(U//FOUO) This notification identifies the deletion
                            of a TEK."
        ::= { commonFFEvents 11 }

    --DRN MIB00135 20081003 In commonFFVSFillOK2 notification, changed object
    --commonFFNextVectoryPresent to hFFNextVector.
    commonFFVSFillOK2 NOTIFICATION-TYPE
        OBJECTS	{
        		usmUserSecurityName,
        		hFFSecurityLevels,
        		hFFMaterialType,
        		hFFExpiration,
        		hFFPartitionCode,
        		hFFNextVector,
        		hFFEnhancedFFTag
        	}
        STATUS		    current
        DESCRIPTION         "(U//FOUO) This notification indicates a FireFly
                            Vector Set was successfully filled. (U//FOUO)
                            KMID, Universal ID and Edition are derived from
                            instance of hFFSecurityLevels in hFireflyTable"
        ::= { commonFFEvents 12 }

    commonFFNegotiationFailure2 NOTIFICATION-TYPE
        OBJECTS	{
        		commonSAIndex,
        		commonAddressType,
        		commonRemoteCTAddress,
        		commonFFSARole,
        		commonFFNegotiaFailureReason,
        		commonLastIkePduSent
        	}
        STATUS		    current
        DESCRIPTION         "(U//FOUO) This Notification identifies the failure
                            of an FFVS IKE Negotiation."
        ::= { commonFFEvents 13 }

    commonACLUpdated3 NOTIFICATION-TYPE
        OBJECTS	{
        		usmUserSecurityName,
        		commonACLKMIDRowStatus,
        		commonACLUpdateAction
        	}
        STATUS		    current
        DESCRIPTION         "(U//FOUO) Notification that the Access Control
                            List was updated. The KMID is the index into
                            the ACL table; its value can be pulled from the
                            commonACLKMIDRowStatus object."
        ::= { commonFFEvents 14 }

    commonPPKEvents OBJECT IDENTIFIER ::= { commonEvents 4 }

    commonPPKFillOK NOTIFICATION-TYPE
        OBJECTS	{
        		usmUserSecurityName,
        		hPPKSecurityLevel,
        		hPPKUsageType
        	}
        STATUS		    current
        DESCRIPTION         "(U//FOUO) Notification that the identified PPK
                            was successfully filled. The PPK Short Title,
                            PPK Edition and PPK Segment information identifying
                            the specific PPK that was filled is provided
                            as the instance to the hPPKTable (thru hPPKUsageType)
                            where they are used as indicies and therefore
                            are non-accessible."
        ::= { commonPPKEvents 1 }

    commonPPKFillFail NOTIFICATION-TYPE
        OBJECTS	{
        		usmUserSecurityName,
        		commonPPKFailedFillReason
        	}
        STATUS		    current
        DESCRIPTION         "(U//FOUO) Notification that the PPK fill failed"
        ::= { commonPPKEvents 2 }

    commonPPKDeleted NOTIFICATION-TYPE
        OBJECTS	{
        		usmUserSecurityName,
        		hPPKUsageType,
        		commonPPKDeleteReason
        	}
        STATUS		    current
        DESCRIPTION         "(U//FOUO) Notification that the identified PPK
                            was deleted. The PPK Short Title, PPK Edition
                            and PPK Segment information identifying the specific
                            PPK that was deleted is provided as the instance
                            to the hPPKTable (thru hPPKUsageType) where they
                            are used as indicies and therefore are non-accessible."
        ::= { commonPPKEvents 3 }

    commonExpiredPPK NOTIFICATION-TYPE
        OBJECTS	{
        		hPPKEffectiveDate,
        		hPPKUsageType
        	}
        STATUS		    current
        DESCRIPTION         "(U//FOUO) Notification that an expired PPK is
                            in use. The PPK Short Title, PPK Edition and
                            PPK Segment information identifying the specific
                            PPK that expired is provided as the instance
                            to the hPPKTable (thru hPPKEffectiveDate) where
                            they are used as indicies and therefore are non-accessible."
        ::= { commonPPKEvents 4 }

    commonPPKUseConfig NOTIFICATION-TYPE
        OBJECTS	{
        		usmUserSecurityName,
        		hPPKEffectiveDate,
        		hPPKTrafficEncryptAlgorithm,
        		nePPKUseConfig
        	}
        STATUS		    deprecated
        DESCRIPTION         "(U//FOUO) Deprecated - Replaced by commonPPKTrafficUseConfig
                            and commonPPKEKUseConfig. (U//FOUO) Notification
                            that the identified PPK use was configured. The
                            PPK Short Title, PPK Edition and PPK Segment
                            information identifying the specific PPK that
                            was configured is provided as the instance to
                            the hPPKTable (thru hPPKEffectiveDate) where
                            they are used as indicies and therefore are non-accessible."
        ::= { commonPPKEvents 5 }

    commonPPKSACreationBlocked NOTIFICATION-TYPE
        OBJECTS	{
        		hStationID,
        		nePPKAssignmentChainID,
        		nePPKAssignmentCtAddressType,
        		nePPKAssignmentCtAddr
        	}
        STATUS		    deprecated
        DESCRIPTION         "(U//FOUO) A notification generated when a PPK
                            SA is not set up because there already exists
                            a FIREFLY SA supporting the connection to the
                            remote INE."
        ::= { commonPPKEvents 6 }

    commonPPKSADInEntryActivated NOTIFICATION-TYPE
        OBJECTS	{
        		commonSAIndex,
        		hTPSAspi,
        		hTPSAPPK,
        		hTPSAConnectionType,
        		hTPSAAddressType,
        		hTPSARemoteCTAddress,
        		hTPSAPTAddressType,
        		hTPSARemotePTAddress,
        		hTPSAECN,
        		hTPSAIntegrityAlgorithm,
        		hTPSAReuseSpi,
        		hTPSACryptoBlockSize,
        		hTPSADIndexType
        	}
        STATUS		    current
        DESCRIPTION         "(U//FOUO) Notification that an incoming PPK SAD
                            entry was activated. The SA index contained in
                            hTPSAIndex should also be carried in this notification.
                            However, hTPSAIndex is not accessible so it must
                            be obtained as the index that identifies hTPSAspi.
                            hTPSAspi is not just a placeholder for hTPSAIndex
                            and should still be carried as well."
        ::= { commonPPKEvents 7 }

    commonPPKSADInEntryDestroyed NOTIFICATION-TYPE
        OBJECTS	{
        		commonSAIndex,
        		hTPSAspi,
        		hTPSAPPK,
        		hTPSAConnectionType,
        		hTPSAAddressType,
        		hTPSARemoteCTAddress,
        		hTPSAPTAddressType,
        		hTPSARemotePTAddress,
        		hTPSAECN,
        		hTPSAIntegrityAlgorithm,
        		hTPSADIndexType
        	}
        STATUS		    current
        DESCRIPTION         "(U//FOUO) Notification that an incoming PPK SAD
                            entry was destroyed. The SA index contained in
                            hTPSAIndex should also be carried in this notification.
                            However, hTPSAIndex is not accessible so it must
                            be obtained as the index that identifies hTPSAspi.
                            hTPSAspi is not just a placeholder for hTPSAIndex
                            and should still be carried as well."
        ::= { commonPPKEvents 8 }

    commonPPKSADOutEntryActivated NOTIFICATION-TYPE
        OBJECTS	{
        		commonSAIndex,
        		hTPSAspi,
        		hTPSAPPK,
        		hTPSAConnectionType,
        		hTPSAAddressType,
        		hTPSALocalCTAddress,
        		hTPSAPTAddressType,
        		hTPSALocalPTAddress,
        		hTPSAECN,
        		hTPSAIntegrityAlgorithm,
        		hTPSAReuseSpi,
        		hTPSACryptoBlockSize,
        		hTPSADSCP,
        		hTPSADSCPValue,
        		hTPSADFBit
        	}
        STATUS		    current
        DESCRIPTION         "(U//FOUO) Notification that an outgoing PPK SAD
                            entry was activated. The SA index contained in
                            hTPSAIndex should also be carried in this notification.
                            However, hTPSAIndex is not accessible so it must
                            be obtained as the index that identifies hTPSAspi.
                            hTPSAspi is not just a placeholder for hTPSAIndex
                            and should still be carried as well."
        ::= { commonPPKEvents 9 }

    commonPPKSADOutEntryDestroyed NOTIFICATION-TYPE
        OBJECTS	{
        		commonSAIndex,
        		hTPSAspi,
        		hTPSAPPK,
        		hTPSAConnectionType,
        		hTPSAAddressType,
        		hTPSALocalCTAddress,
        		hTPSAPTAddressType,
        		hTPSALocalPTAddress,
        		hTPSAECN,
        		hTPSAIntegrityAlgorithm,
        		hTPSADSCP,
        		hTPSADSCPValue,
        		hTPSADFBit
        	}
        STATUS		    current
        DESCRIPTION         "(U//FOUO) Notification that an outgoing PPK SAD
                            entry was destroyed. The SA index contained in
                            hTPSAIndex should also be carried in this notification.
                            However, hTPSAIndex is not accessible so it must
                            be obtained as the index that identifies hTPSAspi.
                            hTPSAspi is not just a placeholder for hTPSAIndex
                            and should still be carried as well."
        ::= { commonPPKEvents 10 }

    commonPPKTrafficUseConfig NOTIFICATION-TYPE
        OBJECTS	{
        		usmUserSecurityName,
        		hPPKTrafficEncryptAlgorithm,
        		hPPKChainEffectiveDate
        	}
        STATUS		    current
        DESCRIPTION         "(U//FOUO) Notification that the identified PPK
                            use was configured. The PPK Short Title, PPK
                            Edition and PPK Segment information identifying
                            the specific PPK that was configured is provided
                            as the instance to the hPPKTable (thru hPPKTrafficEncryptAlgorithm)
                            where they are used as indices and therefore
                            are non-accessible. (U//FOUO) The Chain ID (hPPKChainID
                            and hPPKChainOrder) are provided as the instance
                            to the hPPKChainTable (thru hPPKChainEffectiveDate)
                            where they are used as indexes and therefore
                            are non-accessible."
        ::= { commonPPKEvents 11 }

    commonPPKEKUseConfig NOTIFICATION-TYPE
        OBJECTS	{
        		usmUserSecurityName,
        		hPPKEKKeyType,
        		hPPKChainEffectiveDate,
        		hPPKEKUniversalID
        	}
        STATUS		    current
        DESCRIPTION         "(U//FOUO) Notification that the identified Exclusion
                            Key PPK use was configured. The PPK Short Title,
                            PPK Edition and PPK Segment information identifying
                            the specific PPK that was configured is provided
                            as the instance to the hPPKEKTable (thru hPPKEKKeyType)
                            where they are used as indices and therefore
                            are non-accessible. hPPKEKeyType is a required
                            object in this notification. The Chain ID (hPPKChainID
                            and hPPKChainOrder) is provided as the instance
                            to the hPPKChainTable (thru hPPKChainEffectiveDate)
                            where it is used as an index and therefore is
                            non-accessible."
        ::= { commonPPKEvents 12 }

    commonSNMPEvents OBJECT IDENTIFIER ::= { commonEvents 5 }

    commonSNMPUserConfig NOTIFICATION-TYPE
        OBJECTS	{
        		usmUserSecurityName,
        		commonSNMPUserName,
        		commonUpdateUserAction
        	}
        STATUS		    current
        DESCRIPTION         "(U//FOUO) This Notification indicates a change
                            was made to an SNMP network manager's configuration
                            (add / delete / modify)"
        ::= { commonSNMPEvents 1 }

    commonSNMPAuthError NOTIFICATION-TYPE
        OBJECTS	{
        		commonSNMPUserName,
        		hNetSourceAddressType,
        		hNetSourceAddress
        	}
        STATUS		    deprecated
        DESCRIPTION         "(U//FOUO) Deprecated - Now using authenticationFailure
                            notification from IETF SNMP-V2 MIB (RFC 3418)
                            (U//FOUO) this Notification identifies when an
                            SNMP Authentication failed. It includes variables
                            identifying the manager by name and IP address."
        ::= { commonSNMPEvents 2 }

    --20090409 - T. Huemiller - Revised commonSNMPUserUpdate notification.
    commonSNMPUserUpdate NOTIFICATION-TYPE
        OBJECTS	{
        		usmUserSecurityName,
        		commonSNMPUserTableChanged,
        		commonSNMPTableRowName,
        		commonSNMPUserTableOperation
        	}
        STATUS		    current
        DESCRIPTION         "(U//FOUO) This Notification indicates the configuration
                            of an SNMP user has been changed in one of the
                            SNMPv2-MIB tables."
        ::= { commonSNMPEvents 4 }

    commonIPEvents OBJECT IDENTIFIER ::= { commonEvents 6 }

    commonPSEQNError NOTIFICATION-TYPE
        OBJECTS	{
        		hTPiSPI,
        		hNetSourceAddressType,
        		hNetSourceAddress,
        		hTPiDestinationAddressType,
        		hTPiDestinationAddress,
        		commonRejectedPSEQN,
        		commonPSEQNRejectCount
        	}
        STATUS		    current
        DESCRIPTION         "(U//FOUO) Notification of an initial PSEQN rejection
                            on an SA. (U/FOUO) The variable with the format
                            neHostAddr contains the source host IP address.
                            The variable with the format hTPSALocalPTAddress
                            contains the destination host IP address."
        ::= { commonIPEvents 1 }

    commonRateLimitOverflow NOTIFICATION-TYPE
        OBJECTS	{
        		commonRateLimitId,
        		commonOverflowCount
        	}
        STATUS		    current
        DESCRIPTION         "(U//FOUO) Notification of a rate limit counter
                            overflow"
        ::= { commonIPEvents 2 }

    --T. Huemiller - 20090312 - Added hStationID and hrSystemDate to AddrChanged
    --notifications so can be sent as HAIPE-compliant SNMP TRAPS
    commonIPv6FavoredAddrChanged NOTIFICATION-TYPE
        OBJECTS	{
        		hStationID,
        		hrSystemDate,
        		usmUserSecurityName,
        		hIfv6Side,
        		commonIPv6FavoredAddress,
        		commonIPv6Address
        	}
        STATUS		    current
        DESCRIPTION         "(U//FOUO) Notification that the favored IPv6 address
                            of the interface specified has changed. The additional
                            IPv6 address included in this notification is
                            the other IPv6 for the given interface."
        ::= { commonIPEvents 3 }

    commonIPv4AddrChanged NOTIFICATION-TYPE
        OBJECTS	{
        		hStationID,
        		hrSystemDate,
        		usmUserSecurityName,
        		hIfv4Side,
        		commonIPv4Address
        	}
        STATUS		    current
        DESCRIPTION         "(U//FOUO) Notification that the IPv4 address of
                            the interface specified has changed."
        ::= { commonIPEvents 4 }

    --T. Huemiller - 20090312 - End - added hStationID and hrSystemDate to AddrChanged
    --notifications so can be sent as HAIPE-compliant SNMP TRAPS
    commonAutoAddressConfigFail NOTIFICATION-TYPE
        OBJECTS	{
        		hStationID,
        		hrSystemDate,
        		hIfv6Side,
        		commonAutoconfigurationFailure
        	}
        STATUS		    current
        DESCRIPTION         "(U//FOUO) Notification that the Stateless Address
                            Autoconfiguration (SAA) protocol has failed to
                            aquire an address on the interface identified
                            by the notification object hIFv6Side."
        ::= { commonIPEvents 5 }

    --20090227 - DRN MIB00147 - Begin Add revised PSEQN Error Notification.
    commonPSEQNError2 NOTIFICATION-TYPE
        OBJECTS	{
        		commonSAIndex,
        		hNetSourceAddressType,
        		hNetSourceAddress,
        		hTPiDestinationAddressType,
        		hTPiDestinationAddress,
        		commonRejectedPSEQN,
        		commonPSEQNRejectCount
        	}
        STATUS		    current
        DESCRIPTION         "(U//FOUO) Notification of receipt of a PDU with
                            a PSEQN error on an SA and the number of PSEQN
                            errors in the measurement period. (U/FOUO) The
                            variable hNetSourceAddress contains the source
                            host IP address. The variable hTPiDestinationAddress
                            contains the destination host IP address."
        ::= { commonIPEvents 6 }

    --20090227 - DRN MIB00147 - End Add revised PSEQN Error Notification.
    commonIFEvents OBJECT IDENTIFIER ::= { commonEvents 7 }

    commonIFSpeedModeMismatch NOTIFICATION-TYPE
        OBJECTS	{
        		hStationID,
        		hrSystemDate,
        		commonPTSpeedMode,
        		commonCTSpeedMode
        	}
        STATUS		    current
        DESCRIPTION         "(U//FOUO) This notification is generated each
                            time the PT and CT interfaces are configured
                            at mismatched speeds or modes. (U//FOUO) In the
                            case where both interfaces are configured with
                            static values, the notification is sent when
                            the interfaces are enabled with mismatched speeds
                            or modes. (U//FOUO) In cases where one or both
                            interfaces are using auto-negotiation as a configuration
                            method, this notification is sent when the ECU
                            receives a response from an interface speed/mode
                            negotiation such that the PT and CT interface
                            speeds or modes are mismatched."
        ::= { commonIFEvents 1 }

    commonIFSpeedNegotiationFailure NOTIFICATION-TYPE
        OBJECTS	{
        		hStationID,
        		hrSystemDate,
        		ifIndex
        	}
        STATUS		    current
        DESCRIPTION         "(U//FOUO) This notification is generated each
                            time the PT and CT interfaces fail to negotiate
                            a speed over the network. (U//FOUO) A value of
                            1 for the ifIndex is the PT side interface and
                            a value of 2 for the ifIndex is the CT side interface."
        ::= { commonIFEvents 2 }

    --J. Holzhauer Note: BEGIN MIB items added for GigE/Mini R3.4
    commonFaultEvents OBJECT IDENTIFIER ::= { commonEvents 8 }

    commonEnvironmentalFaultEvents OBJECT IDENTIFIER ::= { commonFaultEvents 1 }

    --J. Holzhauer Note: the hStationID in the following item should be
    --the hStationID IMPORTED from the HAIPE-MANAGEMENT-MIB from the
    --actual HAIPE V3 MIBs, NOT from the 'experimental'
    --GDC4S-HAIPE-MANAGEMENT-MIB!
    --
    --J. Holzhauer Note: TL-Micro Systems/Software suggested making this
    --into towo separate notifications, one Overtemperature fault and one
    --for Fan Fault.  This would allow them to be throttled individually,
    --and logged separately in the NOTIFICATION-LOG-MIB.
    --
    --J. Holzhauer Clarification: the existing definition essentially
    --matches the single environmentalFault trap defined in the
    --TACLANE-Enterprise-MIB, and the corresponding single audit log
    --event logged by GigE/Mini R3.2.
    --
    --HAIPE-MANAGEMENT-MIB.hStationID,
    commonOvertemperatureFault NOTIFICATION-TYPE
        OBJECTS	{
        		hStationID,
        		hrSystemDate,
        		commonOvertemperatureEnvironmentalFault
        	}
        STATUS		    current
        DESCRIPTION         "(U//FOUO) The notification sent to a HAIPE Management
                            System (e.g., HCM) when an overtemperture 'environmental
                            fault' condition has occurred in the ECU. The
                            current status of an overtemperature 'environmental
                            fault' condition (i.e., whether or not an overtemperature
                            'environmental fault' condition is active/present
                            in the ECU) is reported in the appropriate object
                            in the commonEnvironmentalFaultGroup. Note that
                            each 'environmental fault' event will also be
                            reported/recorded in the 'Audit Log', refer to
                            the nlmLogTable and nlmLogVariableTable of the
                            RFC 3014 Notification Log MIB (NOTIFICATION-LOG-MIB
                            module) and their associated columnar objects."
        ::= { commonEnvironmentalFaultEvents 1 }

    commonFanFault NOTIFICATION-TYPE
        OBJECTS	{
        		hStationID,
        		hrSystemDate,
        		commonFanEnvironmentalFault
        	}
        STATUS		    current
        DESCRIPTION         "(U//FOUO) The notification sent to a HAIPE Management
                            System (e.g., HCM) when a fan 'environmental
                            fault' condition has occurred in the ECU. The
                            current status of a fan 'environmental fault'
                            condition (i.e., whether or not a fan 'environmental
                            fault' condition is active/present in the ECU)
                            is reported in the appropriate object in the
                            commonEnvironmentalFaultGroup. Note that each
                            'environmental fault' event will also be reported/recorded
                            in the 'Audit Log', refer to the nlmLogTable
                            and nlmLogVariableTable of the RFC 3014 Notification
                            Log MIB (NOTIFICATION-LOG-MIB module) and their
                            associated columnar objects."
        ::= { commonEnvironmentalFaultEvents 2 }

    --J. Holzhauer Note: END MIB items added for GigE/Mini R3.4
    --=====================================================
    --T. Huemiller 20081217 DRN MIB00141 - PAC Moduli management notifications
    commonPACEvents OBJECT IDENTIFIER ::= { commonEvents 9 }

    commonPACFilledOK NOTIFICATION-TYPE
        OBJECTS	{
        		usmUserSecurityName,
        		neUnInstalledPACBaseType,
        		neUnInstalledPACID,
        		neUnInstalledPACCOI,
        		neUnInstalledPACUserID,
        		neUnInstalledPACSourceID,
        		neUnInstalledPACNationalID
        	}
        STATUS		    current
        DESCRIPTION         "(U//FOUO) This notification indicates a PAC Moduli
                            has been filled successfully."
        ::= { commonPACEvents 1 }

    commonPACFillFailed NOTIFICATION-TYPE
        OBJECTS	{
        		usmUserSecurityName,
        		commonPACFailedFillReason
        	}
        STATUS		    current
        DESCRIPTION         "(U//FOUO) This notification indicates when the
                            fill of a PAC Moduli has failed."
        ::= { commonPACEvents 2 }

    --20090227 - DRN MIB00144 - Deleted commonCorruptPACDetected (commonPACEvents 3).
    commonPACDeleted NOTIFICATION-TYPE
        OBJECTS	{
        		usmUserSecurityName,
        		neUnInstalledPACBaseType,
        		neUnInstalledPACID,
        		neUnInstalledPACCOI,
        		neUnInstalledPACUserID,
        		neUnInstalledPACSourceID,
        		neUnInstalledPACNationalID,
        		commonPACState,
        		commonPACDeleteReason
        	}
        STATUS		    current
        DESCRIPTION         "(U//FOUO) A notification that a PAC Moduli was
                            deleted."
        ::= { commonPACEvents 4 }

    commonPACInstalled NOTIFICATION-TYPE
        OBJECTS	{
        		usmUserSecurityName,
        		neUnInstalledPACBaseType,
        		neUnInstalledPACID,
        		neUnInstalledPACCOI,
        		neUnInstalledPACUserID,
        		neUnInstalledPACSourceID,
        		neUnInstalledPACNationalID
        	}
        STATUS		    current
        DESCRIPTION         "(U//FOUO) A notification that a filled, but not
                            installed PAC Moduli was installed from the neUnInstalledPACModuliTable
                            in the GDC4S-NetworkEncryptor-Enterprise-MIB
                            into the hDePACModuliTable of the HAIPE-Traffic-Protection-MIB."
        ::= { commonPACEvents 5 }

    commonPACDeleteFail NOTIFICATION-TYPE
        OBJECTS	{
        		usmUserSecurityName,
        		commonPACDeleteFailureReason
        	}
        STATUS		    current
        DESCRIPTION         "(U//FOUO) A notification of a failed attempt to
                            delete a PAC Moduli from either the Uninstalled
                            PAC Moduli Table (neUnInstalledPACModuliTable)
                            or the HAIPE DePAC Moduli Table (hDePACModuliTable)"
        ::= { commonPACEvents 6 }

    --
    --20091028 - DRN MIB00183 - Added commonKeyTransferEvents and associated Notification-type
    --objects.
    --
    commonKeyTransferEvents OBJECT IDENTIFIER ::= { commonEvents 10 }

    commonKeyIssueOK NOTIFICATION-TYPE
        OBJECTS	{
        		hStationID,
        		hrSystemDate,
        		hKTLoadedKeyUse,
        		hKTLoadedKeyClassification
        	}
        STATUS		    current
        DESCRIPTION         "(U//FOUO) Identifies that a Traditional or FFVS
                            Key has been successfully issued from a key fill
                            device into an ECU. (U//FOUO) The values of hKTLoadedKeyShortTitle,
                            hKTLoadedKeyEdition, hKTLoadedKeySegment and
                            hKTLoadedKeyRegister are provided in the instance
                            of hKTLoadedKeyUse."
        ::= { commonKeyTransferEvents 1 }

    commonKeyIssueFailed NOTIFICATION-TYPE
        OBJECTS	{
        		hStationID,
        		hrSystemDate,
        		commonKeyIssueFailReason
        	}
        STATUS		    current
        DESCRIPTION         "(U//FOUO) Identifies that a Traditional or FFVS
                            Key failed an issue attempt from a key fill device
                            into an ECU."
        ::= { commonKeyTransferEvents 2 }

    commonIssuedKeyDeleted NOTIFICATION-TYPE
        OBJECTS	{
        		hStationID,
        		hrSystemDate,
        		usmUserSecurityName,
        		hKTLoadedKeyUse,
        		hKTLoadedKeyClassification,
        		commonIssuedKeyDeleteReason
        	}
        STATUS		    current
        DESCRIPTION         "(U//FOUO) Identifies that a key in the hKTLoadedKeyTable
                            was deleted."
        ::= { commonKeyTransferEvents 3 }

    commonOOBXmitOK NOTIFICATION-TYPE
        OBJECTS	{
        		hStationID,
        		hrSystemDate,
        		usmUserSecurityName,
        		hKTOOBClientAddressType,
        		hKTOOBClientAddress,
        		hKTOOBClientKeyFile
        	}
        STATUS		    current
        DESCRIPTION         "(U//FOUO) Identifies that the specified key file
                            was successfully transmitted Out-of-Band by a
                            Key Transfer NET CON."
        ::= { commonKeyTransferEvents 4 }

    commonOOBRcvdOK NOTIFICATION-TYPE
        OBJECTS	{
        		hStationID,
        		hrSystemDate,
        		commonOOBClientPath
        	}
        STATUS		    current
        DESCRIPTION         "(U//FOUO) Identifies that a key file was successfully
                            received Out-of-Band by the Client ECU."
        ::= { commonKeyTransferEvents 5 }

    commonOOBXmitFailed NOTIFICATION-TYPE
        OBJECTS	{
        		hStationID,
        		hrSystemDate,
        		usmUserSecurityName,
        		hKTOOBClientAddressType,
        		hKTOOBClientAddress,
        		hKTOOBClientKeyFile,
        		commonOOBIssueFailReason
        	}
        STATUS		    current
        DESCRIPTION         "(U//FOUO) Identifies that an issue attempted by
                            a NET CON failed."
        ::= { commonKeyTransferEvents 6 }

    commonOOBFileEntryDeleted NOTIFICATION-TYPE
        OBJECTS	{
        		hStationID,
        		hrSystemDate,
        		hKTOOBKeyFileShortTitle,
        		hKTOOBKeyFileEdition,
        		hKTOOBKeyFileSegment,
        		hKTOOBKeyFileRegister
        	}
        STATUS		    current
        DESCRIPTION         "(U//FOUO) Identifies that a Out-of-Band Key File
                            entry referencing a key in the hKTLoadedKeyTable
                            was deleted because the referenced key was deleted.
                            (U//FOUO) The Key File Name and Key File Number
                            are received in the instance of the hKTOOBKeyFileShortTitle
                            object."
        ::= { commonKeyTransferEvents 7 }

    commonOOBRcvFailed NOTIFICATION-TYPE
        OBJECTS	{
        		hStationID,
        		hrSystemDate,
        		commonOOBClientPath,
        		commonOOBRecvdFailReason
        	}
        STATUS		    current
        DESCRIPTION         "(U//FOUO) Identifies that an issue received by
                            a client ECU failed."
        ::= { commonKeyTransferEvents 8 }

    --20091110 - MIB00183 - replaced hPPKRegister in commonKTIBRcvOK which is  not supported
    --by TACLANE R3.5 to
    --hPPKSegment
    --
    commonKTIBRcvOK NOTIFICATION-TYPE
        OBJECTS	{
        		hStationID,
        		hrSystemDate,
        		hPPKSegment
        	}
        STATUS		    current
        DESCRIPTION         "(U//FOUO) Identifies that an In-Band Key Transfer
                            was successfully received. (U//FOUO) The Key
                            Short Title and Edition are received in the instance
                            of the hPPKSegment object"
        ::= { commonKeyTransferEvents 9 }

    commonKTIBLocalOK NOTIFICATION-TYPE
        OBJECTS	{
        		hStationID,
        		hrSystemDate,
        		hKTLoadedKeySegment
        	}
        STATUS		    current
        DESCRIPTION         "(U//FOUO) Identifies that the Key Material has
                            been filled and assigned to the NET CON ECU.
                            (U//FOUO) The Key Short Title, Edition and Register
                            are received in the instance of the hKTLoadedKeySegment
                            object."
        ::= { commonKeyTransferEvents 10 }

    commonKTIBLocalFailed NOTIFICATION-TYPE
        OBJECTS	{
        		hStationID,
        		hrSystemDate,
        		hKTLoadedKeySegment,
        		commonKTIBRcvdFailReason
        	}
        STATUS		    current
        DESCRIPTION         "(U//FOUO) Indentifies that at the NET CON ECU,
                            Key Material failed to be filled and assigned
                            in a local In-Band Key Transfer.(U//FOUO) The
                            Key Short Title, Edition and Register are received
                            in the instance of the hKTLoadedKeySegment object."
        ::= { commonKeyTransferEvents 11 }

    commonKTIBRcvFailed NOTIFICATION-TYPE
        OBJECTS	{
        		hStationID,
        		hrSystemDate,
        		commonKTIBRcvdFailReason
        	}
        STATUS		    current
        DESCRIPTION         "(U//FOUO) Identifies that an In-Band Key Transfer
                            failed at the receiving Client ECU."
        ::= { commonKeyTransferEvents 12 }

    commonKTIBXmitFailed NOTIFICATION-TYPE
        OBJECTS	{
        		hStationID,
        		hrSystemDate,
        		hKTIBClientAddressType,
        		commonKTIBXmitFailReason
        	}
        STATUS		    current
        DESCRIPTION         "(U//FOUO) Identifies that an In-Band Key Transfer
                            failed at the transmitting NET CON ECU. (U//FOUO)
                            The Chain ID, Client Address, Short Title, Edition,
                            Segment and Register are received in the instance
                            of the hKTIBClientAddressType Varbind."
        ::= { commonKeyTransferEvents 13 }

    commonKTIBClientEntryDeleted NOTIFICATION-TYPE
        OBJECTS	{
        		hStationID,
        		hrSystemDate,
        		hKTIBClientAddressType
        	}
        STATUS		    current
        DESCRIPTION         "(U//FOUO) Identifies that a In-Band Clients Table
                            entry referencing a key in the hKTLoadedKeyTable
                            was deleted because the referenced key was deleted.
                            (U//FOUO) The Chain ID, Client Address, Short
                            Title, Edition, Segment and Register are received
                            in the instance of the hKTIBClientAddressType
                            Varbind."
        ::= { commonKeyTransferEvents 14 }

    --R. Berman 20100826 DRN MIB00192 - Added Q-key notifications
    commonQkeyEvents OBJECT IDENTIFIER ::= { commonEvents 11 }

    commonQkeyFilled NOTIFICATION-TYPE
        OBJECTS	{
        		commonUserName,
        		neUninstalledTAType,
        		neUninstalledTAShortTitle,
        		neUninstalledTAKMID
        	}
        STATUS		    current
        DESCRIPTION         "(U//FOUO) This notification indicates a Q-key
                            has been filled successfully."
        ::= { commonQkeyEvents 1 }

    commonQkeyFillFailed NOTIFICATION-TYPE
        OBJECTS	{
        		commonUserName,
        		commonQkeyFillFailureReason
        	}
        STATUS		    current
        DESCRIPTION         "(U//FOUO) This notification indicates when the
                            fill of a Q-key has failed."
        ::= { commonQkeyEvents 2 }

    commonQkeyDeleted NOTIFICATION-TYPE
        OBJECTS	{
        		commonUserName,
        		neUninstalledTAType,
        		neUninstalledTAShortTitle,
        		neUninstalledTAKMID,
        		commonQkeyState,
        		commonQkeyDeleteReason
        	}
        STATUS		    current
        DESCRIPTION         "(U//FOUO) A notification that a Q-key was deleted."
        ::= { commonQkeyEvents 3 }

    commonQkeyDeleteFailed NOTIFICATION-TYPE
        OBJECTS	{
        		commonUserName,
        		commonQkeyDeleteFailureReason
        	}
        STATUS		    current
        DESCRIPTION         "(U//FOUO) A notification of a failed attempt to
                            delete a Q-key from either the Uninstalled Trust
                            Anchor Table or the APPK Trust Anchor Table ."
        ::= { commonQkeyEvents 4 }

    commonQkeyInstalled NOTIFICATION-TYPE
        OBJECTS	{
        		commonUserName,
        		neUninstalledTAType,
        		neUninstalledTAShortTitle,
        		neUninstalledTAKMID
        	}
        STATUS		    current
        DESCRIPTION         "(U//FOUO) A notification that a filled, but not
                            installed Q-key was installed from the Uninstalled
                            Trust Anchor Table into the APPK Trust Anchor
                            Table ."
        ::= { commonQkeyEvents 5 }

    commonQkeyInstallFailed NOTIFICATION-TYPE
        OBJECTS	{
        		commonUserName,
        		commonQkeyInstallFailureReason
        	}
        STATUS		    current
        DESCRIPTION         "(U//FOUO) A notification of a failed attempt to
                            install a Q-key from the Uninstalled Trust Anchor
                            Table into the APPK Trust AnchorTable."
        ::= { commonQkeyEvents 6 }

    --T. Huemiller 20081217 DRN MIB00141 - End of PAC Moduli management notifications
    commonEventVariableObjects OBJECT IDENTIFIER ::= { commonNotifications 2 }

    commonSecurityEventVarObjects OBJECT IDENTIFIER ::= { commonEventVariableObjects 1 }

    commonZeroizeReason OBJECT-TYPE
        SYNTAX              INTEGER {
                                hw( 1 ),
                                swdl( 2 ),
                                partial( 3 ),
                                full( 4 ),
                                renderInoperable( 5 ),
                                sanitize( 7 )
                            }
        MAX-ACCESS          accessible-for-notify
        STATUS              current
        DESCRIPTION         "(U//FOUO) This object identifies which type of
                            zeroize command occurred and how the device received
                            the command. The enumeration values indicate
                            the following: hw( 1 ) - zeroize was commanded
                            via the hardware discrete signal; all application
                            key material, common KEK, and credentials deleted
                            swdl( 2 ) - zeroize was commanded as a result
                            of a software install; all application key material,
                            common KEK, credentials, and all delivery key
                            material (e.g., Benign Fill FFVS) deleted partial(
                            3 ) - partial zeroize was externally commanded;
                            all application key material, common KEK, and
                            credentials deleted full( 4 ) - full zeroize
                            was externally commanded; a partial zeroize was
                            performed and in addition all delivery key material
                            (e.g., Benign Fill FFVS) was deleted renderInoperable(
                            5 ) - render inoperable zeroize was externally
                            commanded; a full zeroize was performed and in
                            addition the device was rendered inoperable sanitize(
                            7 ) - sanitize zeroize was externally commanded;
                            a full zeroize was performed and in addition
                            the device was sanitized"
        ::= { commonSecurityEventVarObjects 1 }

    commonSecurCritFltType OBJECT-TYPE
        SYNTAX              Unsigned32
        MAX-ACCESS          accessible-for-notify
        STATUS              current
        DESCRIPTION         "(U//FOUO) Fault code representing reported Hardware
                            or Software Security Critical Fault."
        ::= { commonSecurityEventVarObjects 2 }

    commonPrivModItemName OBJECT-TYPE
        SYNTAX              INTEGER {
                                fixedPacketLength( 1 ),
                                fplEnableDisable( 2 ),
                                deprecated-pmtuBypassEnableDisable( 3 ),
                                igmpBypassEnableDisable( 4 ),
                                aclModeEnableDisable( 5 ),
                                securityLevelChange( 6 ),
                                deprecated-mtekMtekKeyUpdateEnableDisable( 7 ),
                                deprecated-pseqnCheckEnable( 8 ),
                                deprecated-dfBypassEnable( 9 ),
                                deprecated-dfDoNotFragmentEnable( 10 ),
                                deprecated-flowLabelBypassEnable( 11 ),
                                deprecated-flowLabelValue( 12 ),
                                deprecated-tosTrafficClassBypassEnable( 13 ),
                                deprecated-tosTrafficClassValue( 14 ),
                                deprecated-dscpAcceptedValueLow( 15 ),
                                deprecated-dscpAcceptedValueHigh( 16 ),
                                deprecated-saHostTimerEnable( 17 ),
                                deprecated-saHostTimerValue( 18 ),
                                mldBypassEnableDisable( 19 ),
								igmpLeaveBypassEnableDisable( 20 ),
								mldDoneBypassEnableDisable( 21 )
                            }
        MAX-ACCESS          accessible-for-notify
        STATUS              current
        DESCRIPTION         "(U//FOUO) This object contains the name of the
                            privileged item that was modified."
        ::= { commonSecurityEventVarObjects 3 }

    commonOrigEnableValue OBJECT-TYPE
        SYNTAX              CommonEnableValue
        MAX-ACCESS          accessible-for-notify
        STATUS              deprecated
        DESCRIPTION         "(U//FOUO) Deprecated - EnabledValue objects reported
                            using ConfigDataValueObjects. (U//FOUO) The original
                            value of a configuration data item that was changed,
                            and requires Site Security Officer Privileges
                            to make that change."
        ::= { commonSecurityEventVarObjects 4 }

    commonNewEnableValue OBJECT-TYPE
        SYNTAX              CommonEnableValue
        MAX-ACCESS          accessible-for-notify
        STATUS              deprecated
        DESCRIPTION         "(U//FOUO) Deprecated - EnableValue objects reported
                            using ConfigDataValueObjects. (U//FOUO) The new
                            value of a configuration data item that was changed,
                            and requires Site Security Officer Privileges
                            to make that change."
        ::= { commonSecurityEventVarObjects 5 }

    commonOrigConfigDataValue OBJECT-TYPE
        SYNTAX              Unsigned32
        MAX-ACCESS          accessible-for-notify
        STATUS              current
        DESCRIPTION         "(U//FOUO) The original value of a configuration
                            data item that requires an operator having SSO-Privileges
                            to edit."
        ::= { commonSecurityEventVarObjects 6 }

    commonNewConfigDataValue OBJECT-TYPE
        SYNTAX              Unsigned32
        MAX-ACCESS          accessible-for-notify
        STATUS              current
        DESCRIPTION         "(U//FOUO) The new value of a configuration data
                            item that requires an operator having SSO-Privileges
                            to edit."
        ::= { commonSecurityEventVarObjects 7 }

    --MIB00175 - T. Huemiller - 20090902 - Added 7th enumeration [resetPIN( 7 )] to commonPinActivity.
    commonPinActivity OBJECT-TYPE
        SYNTAX              INTEGER {
                                enablePrivileges( 1 ),
                                invalidPIN( 2 ),
                                disablePrivileges( 3 ),
                                updatePIN( 4 ),
                                inactivityTimeout( 5 ),
                                invalidPINReset( 6 ),
                                resetPIN( 7 )
                            }
        MAX-ACCESS          accessible-for-notify
        STATUS              current
        DESCRIPTION         "(U//FOUO) Identification of action relating to
                            the SSO PIN."
        ::= { commonSecurityEventVarObjects 8 }

    commonUpdateSystemDate OBJECT-TYPE
        SYNTAX              DateAndTime
        MAX-ACCESS          accessible-for-notify
        STATUS              current
        DESCRIPTION         "(U//FOUO) The time/date to which the INE was set.
                            The Data/Time included in the entry header is
                            the value before the change."
        ::= { commonSecurityEventVarObjects 9 }

    commonSecCritPrimeFirstReg OBJECT-TYPE
        SYNTAX              Unsigned32
        MAX-ACCESS          accessible-for-notify
        STATUS              current
        DESCRIPTION         "(U//FOUO) The number of the Primary First Latch
                            Register associated with a detected Hardware
                            Security Critical fault."
        ::= { commonSecurityEventVarObjects 10 }

    commonSecCritPrimeSumReg OBJECT-TYPE
        SYNTAX              Unsigned32
        MAX-ACCESS          accessible-for-notify
        STATUS              current
        DESCRIPTION         "(U//FOUO) The number of the Primary Summary Register
                            associated with a detected Hardware Security
                            Critical fault."
        ::= { commonSecurityEventVarObjects 11 }

    commonSecCritSubFirstReg OBJECT-TYPE
        SYNTAX              Unsigned32
        MAX-ACCESS          accessible-for-notify
        STATUS              current
        DESCRIPTION         "(U//FOUO) The number of the Sub First Latch Register
                            associated with a detected Hardware Security
                            Critical fault."
        ::= { commonSecurityEventVarObjects 12 }

    commonSecCritSubSumReg OBJECT-TYPE
        SYNTAX              Unsigned32
        MAX-ACCESS          accessible-for-notify
        STATUS              current
        DESCRIPTION         "(U//FOUO) The number of the Sub Summary Register
                            associated with a detected Hardware Security
                            Critical fault."
        ::= { commonSecurityEventVarObjects 13 }

    --J. Holzhauer Note: DESCRIPTION of this object updated for GigE/Mini R3.4
    --DEFVAL              { 0 }
    commonSWFltAddressID OBJECT-TYPE
        SYNTAX              Unsigned32
        MAX-ACCESS          accessible-for-notify
        STATUS              current
        DESCRIPTION         "(U//FOUO) The address ID associated with a detected
                            Software Security Critical fault (see the commonSWSecurCriticalFault
                            notification defined in this MIB module). (U//FOUO)
                            The 'default' value of 0 (zero) is used when
                            the associated address ID is unknown, cannot
                            be determined, or is otherwise unsupported."
        ::= { commonSecurityEventVarObjects 14 }

    commonSWFltFileName OBJECT-TYPE
        SYNTAX              OCTET STRING
        MAX-ACCESS          accessible-for-notify
        STATUS              current
        DESCRIPTION         "(U//FOUO) The software file name associated with
                            a detected Software Security Critical fault.
                            The file name is a 64-bit octet string."
        ::= { commonSecurityEventVarObjects 15 }

    commonSWFltLineNum OBJECT-TYPE
        SYNTAX              Unsigned32
        MAX-ACCESS          accessible-for-notify
        STATUS              current
        DESCRIPTION         "(U//FOUO) The software line number associated
                            with a detected Software Security Critical fault."
        ::= { commonSecurityEventVarObjects 16 }

    commonSWFltArg1 OBJECT-TYPE
        SYNTAX              Unsigned32
        MAX-ACCESS          accessible-for-notify
        STATUS              current
        DESCRIPTION         "(U//FOUO) The first argument associated with a
                            detected Software Security Critical fault."
        ::= { commonSecurityEventVarObjects 17 }

    commonSWFltArg2 OBJECT-TYPE
        SYNTAX              Unsigned32
        MAX-ACCESS          accessible-for-notify
        STATUS              current
        DESCRIPTION         "(U//FOUO) The second argument associated with
                            a detected Software Security Critical fault."
        ::= { commonSecurityEventVarObjects 18 }

    commonSWFltArg3 OBJECT-TYPE
        SYNTAX              Unsigned32
        MAX-ACCESS          accessible-for-notify
        STATUS              current
        DESCRIPTION         "(U//FOUO) The third argument associated with a
                            detected Software Security Critical fault."
        ::= { commonSecurityEventVarObjects 19 }

    commonSWFltArg4 OBJECT-TYPE
        SYNTAX              Unsigned32
        MAX-ACCESS          accessible-for-notify
        STATUS              current
        DESCRIPTION         "(U//FOUO) The fourth argument associated with
                            a detected Software Security Critical fault."
        ::= { commonSecurityEventVarObjects 20 }

    --J. Holzhauer Note: DESCRIPTION of this object updated for GigE/Mini R3.4
    --DEFVAL              { "" }
    commonSWFltStackDump OBJECT-TYPE
        SYNTAX              OCTET STRING
        MAX-ACCESS          accessible-for-notify
        STATUS              current
        DESCRIPTION         "(U//FOUO) The 128-bit (16 octet) stack dump associated
                            with a detected Software Security Critical fault
                            (see the commonSWSecurCriticalFault notification
                            defined in this MIB module). (U//FOUO) The 'default'
                            value of the zero-length string is used when
                            the associated stack dump is unknown, cannot
                            be determined, or is otherwise unsupported."
        ::= { commonSecurityEventVarObjects 21 }

    commonBIPErrorCount OBJECT-TYPE
        SYNTAX              Unsigned32
        MAX-ACCESS          accessible-for-notify
        STATUS              deprecated
        DESCRIPTION         "(U//FOUO) The number of Bit Interleaved Parity
                            errors in the interval."
        ::= { commonSecurityEventVarObjects 22 }

    commonDiagnosticId OBJECT-TYPE
        SYNTAX              Unsigned32
        MAX-ACCESS          accessible-for-notify
        STATUS              current
        DESCRIPTION         "(U//FOUO) Designation of diagnostic software process."
        ::= { commonSecurityEventVarObjects 23 }

    commonDiagFailArg1 OBJECT-TYPE
        SYNTAX              Unsigned32
        MAX-ACCESS          accessible-for-notify
        STATUS              current
        DESCRIPTION         "(U//FOUO) The first argument associated with a
                            detected diagnostic software fault."
        ::= { commonSecurityEventVarObjects 24 }

    commonDiagFailArg2 OBJECT-TYPE
        SYNTAX              Unsigned32
        MAX-ACCESS          accessible-for-notify
        STATUS              current
        DESCRIPTION         "(U//FOUO) The second argument associated with
                            a detected diagnostic software fault."
        ::= { commonSecurityEventVarObjects 25 }

    commonDiagFailArg3 OBJECT-TYPE
        SYNTAX              Unsigned32
        MAX-ACCESS          accessible-for-notify
        STATUS              current
        DESCRIPTION         "(U//FOUO) The third argument associated with a
                            detected diagnostic software fault."
        ::= { commonSecurityEventVarObjects 26 }

    commonDiagFailArg4 OBJECT-TYPE
        SYNTAX              Unsigned32
        MAX-ACCESS          accessible-for-notify
        STATUS              current
        DESCRIPTION         "(U//FOUO) The fourth argument associated with
                            a detected diagnostic software fault."
        ::= { commonSecurityEventVarObjects 27 }

    commonConfigurationResetType OBJECT-TYPE
        SYNTAX              INTEGER {
                                spd( 1 ),
                                snmp( 2 ),
                                all( 3 )
                            }
        MAX-ACCESS          accessible-for-notify
        STATUS              current
        DESCRIPTION         "(U//FOUO) This object indicates how much of the
                            unit's configuration has been reset."
        ::= { commonSecurityEventVarObjects 28 }

    commonAuditLogInitializeReason OBJECT-TYPE
        SYNTAX              INTEGER {
                                tamper( 1 ),
                                deletedByNetworkManager( 2 ),
                                nvramUpgraded( 3 ),
                                sanitized( 4 ),
                                internalError( 5 )
                            }
        MAX-ACCESS          accessible-for-notify
        STATUS              current
        DESCRIPTION         "(U//FOUO) Indicates the reason why the audit log
                            was initialized."
        ::= { commonSecurityEventVarObjects 29 }

    commonKEKId OBJECT-TYPE
        SYNTAX              INTEGER {
                                ks( 1 ),
                                gsk1( 2 ),
                                gsk2( 3 )
                            }
        MAX-ACCESS          accessible-for-notify
        STATUS              current
        DESCRIPTION         "(U//FOUO)This object identifies the Key Encryption
                            Key (KEK) that the notification is reporting
                            on."
        ::= { commonSecurityEventVarObjects 30 }

    commonConfigConflictDescription OBJECT-TYPE
        SYNTAX              OCTET STRING (SIZE(1..128))
        MAX-ACCESS          accessible-for-notify
        STATUS              current
        DESCRIPTION         "(U//FOUO) The explanation of why an otherwise
                            valid SNMP SET failed due to a configuration
                            conflict within the managed device. This description
                            is used to supplement the SNMP error responses
                            Inconsistent Name and Inconsistent Value to identify
                            the configuration conflict more specifically."
        ::= { commonSecurityEventVarObjects 31 }

    commonHWFltArg1 OBJECT-TYPE
        SYNTAX              Unsigned32
        MAX-ACCESS          accessible-for-notify
        STATUS              current
        DESCRIPTION         "(U//FOUO) The first argument associated with a
                            detected Hardware Security Critical fault."
        ::= { commonSecurityEventVarObjects 32 }

    commonHWFltArg2 OBJECT-TYPE
        SYNTAX              Unsigned32
        MAX-ACCESS          accessible-for-notify
        STATUS              current
        DESCRIPTION         "(U//FOUO) The second argument associated with
                            a detected Hardware Security Critical fault."
        ::= { commonSecurityEventVarObjects 33 }

    commonHWFltArg3 OBJECT-TYPE
        SYNTAX              Unsigned32
        MAX-ACCESS          accessible-for-notify
        STATUS              current
        DESCRIPTION         "(U//FOUO) The third argument associated with a
                            detected Hardware Security Critical fault."
        ::= { commonSecurityEventVarObjects 34 }

    commonHWFltArg4 OBJECT-TYPE
        SYNTAX              Unsigned32
        MAX-ACCESS          accessible-for-notify
        STATUS              current
        DESCRIPTION         "(U//FOUO) The fourth argument associated with
                            a detected Hardware Security Critical fault."
        ::= { commonSecurityEventVarObjects 35 }

    commonUnIdentifiedKeyFillErrorReason OBJECT-TYPE
        SYNTAX              INTEGER {
                                invalidCommand( 1 ),
                                invalidKeyMaterial( 2 )
                            }
        MAX-ACCESS          accessible-for-notify
        STATUS              current
        DESCRIPTION         "(U//FOUO) This notification-object identifies
                            the reason data received on the ECU fill port
                            was deemed unidentifiable."
        ::= { commonSecurityEventVarObjects 36 }

    commonCIKEventVarObjects OBJECT IDENTIFIER ::= { commonEventVariableObjects 2 }

    commonCIKCreateReason OBJECT-TYPE
        SYNTAX              INTEGER {
                                tamperRecovery( 1 ),
                                operatorCommand( 2 ),
                                fieldSoftwareUpgrade( 3 )
                            }
        MAX-ACCESS          accessible-for-notify
        STATUS              current
        DESCRIPTION         "(U//FOUO) This object identifies the entity that
                            initiated the action of CIK creation."
        ::= { commonCIKEventVarObjects 1 }

    commonFailedCikReason OBJECT-TYPE
        SYNTAX              INTEGER {
                                readFault( 1 ),
                                writeFault( 2 ),
                                invalidCik( 3 )
                            }
        MAX-ACCESS          accessible-for-notify
        STATUS              current
        DESCRIPTION         "(U//FOUO) This object identifies the reason the
                            CIK inserted in the device was not able to be
                            activated."
        ::= { commonCIKEventVarObjects 2 }

    commonFailedCikOperation OBJECT-TYPE
        SYNTAX              INTEGER {
                                activation( 1 ),
                                creation( 2 )
                            }
        MAX-ACCESS          accessible-for-notify
        STATUS              current
        DESCRIPTION         "(U//FOUO) CIK operation in process when CIK failed."
        ::= { commonCIKEventVarObjects 3 }

    --T. Huemiller - commonFTRCount deleted
    commonFFEventVarObjects OBJECT IDENTIFIER ::= { commonEventVariableObjects 3 }

    --T. Huemiller - DRN MIB00140 20081217 - added enumeration fillDisabled( 11 )
    --to commonFFVSDeleteReason.
    --20090227 - DRN MIB00150 - added enumeration storageCapacityExceeded( 12 )
    commonFFFailedFillReason OBJECT-TYPE
        SYNTAX              INTEGER {
                                pACFailure( 1 ),
                                invalidKeyMaterial( 2 ),
                                invalidFFVSKeyTag( 3 ),
                                ds-101ProtocolTimeout( 4 ),
                                commandAbort( 5 ),
                                duplicateKMID( 6 ),
                                vectorSetHasMultipleSecLevels( 7 ),
                                unsupportedFireflyType( 8 ),
                                dataLinkError( 9 ),
                                keyMaterialUnsupported( 10 ),
                                fillDisabled( 11 ),
                                storageCapacityExceeded( 12 )
                            }
        MAX-ACCESS          accessible-for-notify
        STATUS              current
        DESCRIPTION         "(U//FOUO) This object identifies the reason for
                            the FireFly Vector Set Fill failure."
        ::= { commonFFEventVarObjects 1 }

    commonFFSARole OBJECT-TYPE
        SYNTAX              INTEGER {
                                initiator( 1 ),
                                responder( 2 )
                            }
        MAX-ACCESS          accessible-for-notify
        STATUS              current
        DESCRIPTION         "(U//FOUO) The role this INE played in establishing
                            the FFVS-based SA."
        ::= { commonFFEventVarObjects 2 }

    --20090227 - MIB00149 - Added enumeration remoteSpiMatchesLocalSpi ( 24 )
    --20091012 - MIB00179 - Added enumerations invalidTransportPayload(25)
    --and transportAddressNotSet(26)
    --20091027 - MIB00181 - Add enumeration invalidNATOAPayload( 27 )
    --
    commonFFNegotiaFailureReason OBJECT-TYPE
        SYNTAX              INTEGER {
                                deprecated-ffvsNotFilled( 1 ),
                                ikeTimeout( 2 ),
                                ikeCollision( 3 ),
                                fireflyResolveFault( 4 ),
                                invalidPortNumber( 5 ),
                                invalidTransportProtocol( 6 ),
                                invalidHashValue( 7 ),
                                localRemoteFFVSIncompatible( 8 ),
                                localRemoteEncryptionAlgorithmMismatch( 9 ),
                                localRemoteSecurityLevelMismatch( 10 ),
                                aclViolation( 11 ),
                                negotiationAborted( 12 ),
                                negotiationAlreadyInProgress( 13 ),
                                eklProcessingError( 14 ),
                                invalidConnectionType( 15 ),
                                invalidDeletePayload( 16 ),
                                invalidIKE3-4( 17 ),
                                localIPAddressDeleted( 18 ),
                                ipAddressMismatch( 19 ),
                                localIPAddressNotSet( 20 ),
                                saSetupFailure( 21 ),
                                transformMismatch( 22 ),
                                maximumNegotiationsInProgress( 23 ),
                                remoteSpiMatchesLocalSpi( 24 ),
                                invalidTransportPayload( 25 ),
                                transportAddressNotSet( 26 ),
                                invalidNATOAPayload( 27 )
                            }
        MAX-ACCESS          accessible-for-notify
        STATUS              current
        DESCRIPTION         "(U//FOUO) The reason the FireFly Negotiation failed.
                            (U//FOUO) Enumeration meanings: (U//FOUO) ffvsNotfilled
                            - A FFVS is not filled in this device. (U//FOUO)
                            ikeTimeOut - The IKE did not complete within
                            the allotted time. (U//FOUO) ikeCollision - IKE
                            1 is received while awaiting an IKE 2 from the
                            same INE and we modify our role from Initiator
                            to Responder. (U//FOUO) fireflyResolveFault (U//FOUO)
                            invalidPortNumber (U//FOUO) invalidTransportProtocol
                            (U//FOUO) invalidHashValue (U//FOUO) localRemoteFFVSIncompatible
                            (U//FOUO) localRemoteEncryptionAlgorithmMismatch
                            (U//FOUO) localRemoteSecurityLevelMismatch (U//FOUO)
                            aclViolation (U//FOUO) negotiationAborted - The
                            negotiation was aborted (for any number of reasons).
                            (U//FOUO) negotiationAlreadyInProgress - When
                            trying to start a negotiation for a given SA
                            ID, a negotiation for the specified SA ID was
                            already in progress. (U//FOUO) eklProcessingError
                            - EKL Processing failed upon receiving IKE3/4.(U//FOUO)
                            invalidConnectionType - The Connection Type in
                            IKE5/6 was incorrectly set to MANAGER. (U//FOUO)
                            invalidDeletePayload - A Delete Payload received
                            in IKE5 was invalid. (U//FOUO) invalidIKE3-4
                            - The IKE 3/4 Nonce or Key Exchange payload was
                            formatted incorrectly. (U//FOUO) localIPAddressDeleted
                            - A local IP address was deleted That this negotiation
                            depended on. (U//FOUO) ipAddressMismatch - The
                            CT-Out field in the FF SA template specifies
                            a different IP version than the remote CT IP
                            address. The CT-Out field in the FF SA Template
                            specifies a different IP address than the IKE1
                            destination. (U//FOUO) localIPAddressNotSet -
                            A local IP address of the appropriate version
                            for this IKE Exchange is not set on either the
                            PT or CT interface. (U//FOUO) saSetupFailure
                            - During the negotiation, the SA was not able
                            to be set up ( for any number of reasons). (U//FOUO)
                            transformMismatch - Upon receiving IKE1/2, no
                            matching transform was found. (U//FOUO) maximumNegotiationsInProgress
                            - When trying to start a negotiation, the maximum
                            number of concurrent negotiations were already
                            in progress (U//FOUO) remoteSpiMatchesLocalSpi
                            - The responder in IKE2 matches the SPI sent
                            by the initiator in IKE1. (U//FOUO) invalidTransportPayload
                            - A Transport Payload received in IKE5 was invalid.
                            (U//FOUO)transportAddressNotSet - Transport Addresses
                            are unspecified while processing IKE2. (U//FOUO)
                            InvalidNATOAPayload - OA payload fails verification."
        ::= { commonFFEventVarObjects 3 }

    commonACLUpdateAction OBJECT-TYPE
        SYNTAX              INTEGER {
                                add( 1 ),
                                delete( 2 )
                            }
        MAX-ACCESS          accessible-for-notify
        STATUS              current
        DESCRIPTION         "(U//FOUO) Indicates whether an entry in the Access
                            Control List was added or deleted."
        ::= { commonFFEventVarObjects 4 }

    --DRN MIB00148 - 20090227 - Added enumeration superseded( 5 ).
    commonFFVSDeleteReason OBJECT-TYPE
        SYNTAX              INTEGER {
                                userRequest( 1 ),
                                replacedByNext( 2 ),
                                deletedForExpiration( 3 ),
                                pacDeleted( 4 ),
                                superseded( 5 )
                            }
        MAX-ACCESS          accessible-for-notify
        STATUS              current
        DESCRIPTION         "(U//FOUO) The reason theFFVS was deleted"
        ::= { commonFFEventVarObjects 5 }

    commonCKLUpdateAction OBJECT-TYPE
        SYNTAX              INTEGER {
                                add( 1 ),
                                delete( 2 )
                            }
        MAX-ACCESS          accessible-for-notify
        STATUS              current
        DESCRIPTION         "(U//FOUO) Indicates whether an object in the compromised
                            key list was added or deleted."
        ::= { commonFFEventVarObjects 6 }

    commonRemoteFFKMID OBJECT-TYPE
        SYNTAX              KMID
        MAX-ACCESS          accessible-for-notify
        STATUS              current
        DESCRIPTION         "(U//FOUO) The KMID of the remote FFVS."
        ::= { commonFFEventVarObjects 7 }

    --
    --20091027 - DRN MIB00182 - Add Transport Mode enumerations numbers 9, 10 & 11.
    commonFFTEKDeletedReason OBJECT-TYPE
        SYNTAX              INTEGER {
                                operatorRelease( 1 ),
                                saTableFullReplacement( 2 ),
                                mtekUpdateFailure( 3 ),
                                deletePayloadReceived( 4 ),
                                ipConfigUpdated( 5 ),
                                spdUpdated( 6 ),
                                duplicateSADetected( 7 ),
                                orphanRecovery( 8 ),
                                transport-FPLModeConflict( 9 ),
                                transportMapAddFailed( 10 ),
                                transportMapDeleted( 11 )
                            }
        MAX-ACCESS          accessible-for-notify
        STATUS              current
        DESCRIPTION         "(U//FOUO) The reason why a FF TEK was deleted."
        ::= { commonFFEventVarObjects 8 }

    commonFFNextVectorPresent OBJECT-TYPE
        SYNTAX              TruthValue
        MAX-ACCESS          accessible-for-notify
        STATUS              current
        DESCRIPTION         "(U//FOUO) Indication of whether or not this FF
                            has a NextVector."
        ::= { commonFFEventVarObjects 9 }

    commonRemoteSAspi OBJECT-TYPE
        SYNTAX              Unsigned32
        MAX-ACCESS          accessible-for-notify
        STATUS              current
        DESCRIPTION         "(U//FOUO) The remote Security Parameters Index
                            (SPI) value for the outgoing Security Association
                            (SA) associated with this FFTEK."
        ::= { commonFFEventVarObjects 10 }

    commonLastIkePduSent OBJECT-TYPE
        SYNTAX              Integer32 (0..6)
        MAX-ACCESS          accessible-for-notify
        STATUS              current
        DESCRIPTION         "(U//FOUO) The last IKE PDU sent before the FFVS
                            Negotiation failed."
        ::= { commonFFEventVarObjects 11 }

    commonPPKEventVarObjects OBJECT IDENTIFIER ::= { commonEventVariableObjects 4 }

    commonPPKFailedFillReason OBJECT-TYPE
        SYNTAX              INTEGER {
                                ds-101ProtocolTimeout( 1 ),
                                operatorCommandedAbort( 2 ),
                                ds-101-1ParityError( 3 ),
                                ecdsaAuthenticationFailure( 4 ),
                                ppkAlreadyLoaded( 5 ),
                                deprecated-previousPPKInChainMissing( 6 ),
                                dataLinkError( 7 ),
                                deprecated-cryptosuiteMismatch( 8 ),
                                invalidDataFilled( 9 ),
                                securityLevelMismatch( 10 ),
                                storageCapacityExceeded( 11 ),
                                invalidKeyMaterial( 12 ),
                                keyMaterialUnsupported( 13 )
                            }
        MAX-ACCESS          accessible-for-notify
        STATUS              current
        DESCRIPTION         "(U//FOUO) This object identifies the reason the
                            PPK fill operation failed."
        ::= { commonPPKEventVarObjects 1 }

    commonPPKDeleteReason OBJECT-TYPE
        SYNTAX              INTEGER {
                                noReason( 0 ),
                                userRequest( 1 ),
                                deprecated-maximumUpdateCount( 2 ),
                                changeover( 3 ),
                                purgedByNewPPK( 4 ),
                                cryptoPeriodExpired( 5 ),
                                q-KeyDeleted( 6 ),
                                purgedDueToIncompatibility( 7 )
                            }
        MAX-ACCESS          accessible-for-notify
        STATUS              current
        DESCRIPTION         "(U//FOUO) Reason the identified PPK was deleted."
        ::= { commonPPKEventVarObjects 2 }

    commonSNMPEventVarObjects OBJECT IDENTIFIER ::= { commonEventVariableObjects 5 }

    commonSNMPUserName OBJECT-TYPE
        SYNTAX              SnmpAdminString
        MAX-ACCESS          accessible-for-notify
        STATUS              current
        DESCRIPTION         "(U//FOUO) This object contains the name of the
                            SNMP user whose account configuration was updated.
                            Size = 1...32."
        ::= { commonSNMPEventVarObjects 1 }

    commonUpdateUserAction OBJECT-TYPE
        SYNTAX              INTEGER {
                                addUser( 1 ),
                                modifyUser( 2 ),
                                deleteUser( 3 ),
                                keyChange( 4 )
                            }
        MAX-ACCESS          accessible-for-notify
        STATUS              current
        DESCRIPTION         "(U//FOUO) The action taken in configuring a Remote
                            Manager for this device (add, modify or delete)."
        ::= { commonSNMPEventVarObjects 2 }

    commonSNMPUserTableChanged OBJECT-TYPE
        SYNTAX              INTEGER {
                                snmpTargetAddrEntry( 1 ),
                                snmpTargetParamsEntry( 2 ),
                                snmpNotifyEntry( 3 ),
                                snmpNotifyFilterProfileEntry( 4 ),
                                snmpNotifyFilterEntry( 5 ),
                                vacmSecurityToGroupEntry( 6 ),
                                vacmAccessEntry( 7 ),
                                vacmViewTreeFamilyEntry( 8 ),
                                usmUserEntry( 9 )
                            }
        MAX-ACCESS          accessible-for-notify
        STATUS              current
        DESCRIPTION         "(U//FOUO) The type of configuration (table entry)
                            that was changed on behalf of a remote user configuration
                            change."
        ::= { commonSNMPEventVarObjects 3 }

    commonSNMPUserTableOperation OBJECT-TYPE
        SYNTAX              INTEGER {
                                create( 1 ),
                                modify( 2 ),
                                delete( 3 )
                            }
        MAX-ACCESS          accessible-for-notify
        STATUS              current
        DESCRIPTION         "(U//FOUO) The type of operation applied to a table
                            associated with a user configuration change."
        ::= { commonSNMPEventVarObjects 4 }

    --20090409 - T. Huemiller - Add commonSNMPTableRowName
    commonSNMPTableRowName OBJECT-TYPE
        SYNTAX              SnmpAdminString
        MAX-ACCESS          accessible-for-notify
        STATUS              current
        DESCRIPTION         "(U//FOUO) This notification-object identifies
                            the key index of the row of the table for which
                            the reported action occurred. Length is 1 to
                            32 Octets. (U//FOUO) The SnmpAdminString value
                            of the SNMPv2-MIB row reported by this object
                            depends on the table being changed as follows:
                            usmUserTable change reports usmUserName; snmpTargetAddrTable
                            reports snmpTargetAddrName; vacmSecurityToGroupTable
                            reports vacmSecurityName; vacmAccessTable reports
                            vacmGroupName; vacmViewTree FamilyTable reports
                            vacmViewTreeFamilyViewName; snmpTargetParamsTable
                            reports snmpTargetParamsName; and snmpNotifyFilterProfileTable
                            reports snmpNotifyFilterProfileName."
        ::= { commonSNMPEventVarObjects 5 }

    commonIPEventVarObjects OBJECT IDENTIFIER ::= { commonEventVariableObjects 6 }

    commonRejectedPSEQN OBJECT-TYPE
        SYNTAX              Counter64
        MAX-ACCESS          accessible-for-notify
        STATUS              current
        DESCRIPTION         "(U//FOUO) The Packet Sequence Number rejected."
        ::= { commonIPEventVarObjects 1 }

    --Tim Huemiller note:  060613 Changed syntax of commonPSEQNRejectCount from
    --Counter64 to Unsigned32 per TACLANE-Micro UDRN00349.
    commonPSEQNRejectCount OBJECT-TYPE
        SYNTAX              Unsigned32
        MAX-ACCESS          accessible-for-notify
        STATUS              current
        DESCRIPTION         "(U//FOUO) The number of Payload Sequence Number
                            errors during the interval."
        ::= { commonIPEventVarObjects 2 }

    commonRateLimitId OBJECT-TYPE
        SYNTAX              INTEGER {
                                igmpBypass( 0 ),
                                icmpPmtu( 1 )
                            }
        MAX-ACCESS          accessible-for-notify
        STATUS              current
        DESCRIPTION         "(U//FOUO) The counter in which a rate limit overflow
                            occurred"
        ::= { commonIPEventVarObjects 3 }

    commonOverflowCount OBJECT-TYPE
        SYNTAX              Unsigned32
        MAX-ACCESS          accessible-for-notify
        STATUS              current
        DESCRIPTION         "(U//FOUO) The number of 1-minute intervals in
                            a 1-hour reporting period in which an overflow
                            occurred for the named counter. The range is
                            0-60 one-minute intervals."
        ::= { commonIPEventVarObjects 4 }

    commonIPv6FavoredAddress OBJECT-TYPE
        SYNTAX              InetAddress
        MAX-ACCESS          accessible-for-notify
        STATUS              current
        DESCRIPTION         "(U//FOUO) The favored IPv6 address of a given
                            interface."
        ::= { commonIPEventVarObjects 5 }

    commonIPv6Address OBJECT-TYPE
        SYNTAX              InetAddress
        MAX-ACCESS          accessible-for-notify
        STATUS              current
        DESCRIPTION         "(U//FOUO) The IPv6 address (usually non-favored)
                            of a given interface."
        ::= { commonIPEventVarObjects 6 }

    commonIPv4Address OBJECT-TYPE
        SYNTAX              InetAddress
        MAX-ACCESS          accessible-for-notify
        STATUS              current
        DESCRIPTION         "(U//FOUO) The IPv4 address of a given interface."
        ::= { commonIPEventVarObjects 7 }

    commonAutoconfigurationFailure OBJECT-TYPE
        SYNTAX              INTEGER {
                                routerProvidedNoPrefix( 1 )
                            }
        MAX-ACCESS          accessible-for-notify
        STATUS              current
        DESCRIPTION         "(U//FOUO) This notification object identifies
                            the reason that the Stateless Address Autoconfiguration
                            (SAA) protocol has failed to acquire an address."
        ::= { commonIPEventVarObjects 8 }

    commonIFEventVarObjects OBJECT IDENTIFIER ::= { commonEventVariableObjects 7 }

    commonPTSpeedMode OBJECT-TYPE
        SYNTAX              AutonomousType
        MAX-ACCESS          accessible-for-notify
        STATUS              current
        DESCRIPTION         "(U//FOUO) Provides the OID from the MAU-MIB dot3MauType
                            group to identify the speed and mode of the PT
                            Interface of the ECU."
        ::= { commonIFEventVarObjects 1 }

    commonCTSpeedMode OBJECT-TYPE
        SYNTAX              AutonomousType
        MAX-ACCESS          accessible-for-notify
        STATUS              current
        DESCRIPTION         "(U//FOUO) Provides the OID from the MAU-MIB dot3MauType
                            group to identify the speed and mode of the CT
                            Interface of the ECU."
        ::= { commonIFEventVarObjects 2 }

    commonSAEventVarObjects OBJECT IDENTIFIER ::= { commonEventVariableObjects 8 }

    commonSAIndex OBJECT-TYPE
        SYNTAX              Unsigned32
        MAX-ACCESS          accessible-for-notify
        STATUS              current
        DESCRIPTION         "(U//FOUO) A common index to pair incomming and
                            outgoing SAs (which have different indexes) together."
        ::= { commonSAEventVarObjects 1 }

    commonSAspi OBJECT-TYPE
        SYNTAX              Unsigned32
        MAX-ACCESS          accessible-for-notify
        STATUS              current
        DESCRIPTION         "(U//FOUO) The Security Parameters Index (SPI)
                            value for this Security Association (SA). This
                            SPI will either be the local SPI when hTPSADirection
                            is incoming, or the remote SPI when hTPSADirection
                            is outgoing. This common SPI can be used when
                            it is impractical to index into the hTPSATable
                            for the SPI value."
        ::= { commonSAEventVarObjects 2 }

    --DRN MIB00138 20081008 Added commonAddressType and commonRemoteCTAddress.
    commonAddressType OBJECT-TYPE
        SYNTAX              InetAddressType
        MAX-ACCESS          accessible-for-notify
        STATUS              current
        DESCRIPTION         "(U//FOUO) The type of the address stored in commonRemoteCTAddress."
        ::= { commonSAEventVarObjects 3 }

    commonRemoteCTAddress OBJECT-TYPE
        SYNTAX              InetAddress
        MAX-ACCESS          accessible-for-notify
        STATUS              current
        DESCRIPTION         "(U//FOUO) The remote CT IP address for the SA."
        ::= { commonSAEventVarObjects 4 }

    --T. Huemiller DRN MIB00141 - PAC Moduli management notification objects
    commonPACEventVarObjects OBJECT IDENTIFIER ::= { commonEventVariableObjects 9 }

    --T. Huemiller DRN MIB00153 - Add enumerations to commonPACFailedFillReason
    commonPACFailedFillReason OBJECT-TYPE
        SYNTAX              INTEGER {
                                ds-101ProtocolTimeout( 1 ),
                                ds-100-1ParityError( 2 ),
                                dataLinkError( 3 ),
                                storageCapacityExceeded( 4 ),
                                duplicateKey( 5 ),
                                cpcInvalidKeyMaterial( 6 ),
                                cpcKeyMaterialUnsupported( 7 ),
                                cpcPACFailure( 8 ),
                                ppcInvalidKeyMaterial( 9 ),
                                ppcKeyMaterialUnsupported( 10 ),
                                ppcPACFailure( 11 )
                            }
        MAX-ACCESS          accessible-for-notify
        STATUS              current
        DESCRIPTION         "(U//FOUO) The reason the PAC Moduli fill failed."
        ::= { commonPACEventVarObjects 1 }

    --20090227 - DRN MIB00144 - Deleted commonCorruptPACResponse( commonPACEventVarObjects
    --2 )
    commonPACDeleteReason OBJECT-TYPE
        SYNTAX              INTEGER {
                                userRequest( 1 ),
                                newBasePAC( 2 )
                            }
        MAX-ACCESS          accessible-for-notify
        STATUS              current
        DESCRIPTION         "(U//FOUO) The reason the PAC was deleted."
        ::= { commonPACEventVarObjects 3 }

    commonPACDeleteFailureReason OBJECT-TYPE
        SYNTAX              INTEGER {
                                basePAC( 1 )
                            }
        MAX-ACCESS          accessible-for-notify
        STATUS              current
        DESCRIPTION         "(U//FOUO) The reason the PAC Moduli failed to
                            be deleted"
        ::= { commonPACEventVarObjects 4 }

    commonPACState OBJECT-TYPE
        SYNTAX              INTEGER {
                                uninstalled( 1 ),
                                installed( 2 )
                            }
        MAX-ACCESS          accessible-for-notify
        STATUS              current
        DESCRIPTION         "(U//FOUO) This object is used to indicate whether
                            a PAC Moduli that is being reported as deleted
                            was removed from the uninstalled PAC Table (neUnInstalledPACModuliTable)
                            or the installed PAC Table (hDePACModuliTable)."
        ::= { commonPACEventVarObjects 5 }

    --
    --20091028 - DRN MIB00183 - Added commonKeyTransferEventsVarObjects.
    --
    commonKeyTransferEventVarObjects OBJECT IDENTIFIER ::= { commonEventVariableObjects 10 }

    commonKeyIssueFailReason OBJECT-TYPE
        SYNTAX              INTEGER {
                                duplicateIssueKey( 1 ),
                                maxIssuedKeysFilled( 2 ),
                                issuedPPKInvalid( 3 ),
                                issuedFFVSInvalid( 4 )
                            }
        MAX-ACCESS          accessible-for-notify
        STATUS              current
        DESCRIPTION         "(U//FOUO) This object is reported in commonKeyIssueFailed
                            and identifies the cause of the failure to Issue
                            Key Material (load key from fill device into
                            hKTLoadedKeyTable)."
        ::= { commonKeyTransferEventVarObjects 1 }

    commonIssuedKeyDeleteReason OBJECT-TYPE
        SYNTAX              INTEGER {
                                managerRequest( 1 ),
                                deletedByFill( 2 )
                            }
        MAX-ACCESS          accessible-for-notify
        STATUS              current
        DESCRIPTION         "(U//FOUO) This object is reported in commonIssuedKeyDeleted
                            and identifies what prompted the key to be deleted
                            from the hKTLoadedKeyTable."
        ::= { commonKeyTransferEventVarObjects 2 }

    commonOOBIssueFailReason OBJECT-TYPE
        SYNTAX              INTEGER {
                                tftpError( 1 ),
                                referencedKeyNotPresent( 2 ),
                                targetClientNotConnected( 3 ),
                                sa-keySecurityLevelMismatch( 4 )
                            }
        MAX-ACCESS          accessible-for-notify
        STATUS              current
        DESCRIPTION         "(U//FOUO) This object is reported in commonOOBXmitFailed
                            and identifies the cause of the failure to transmit
                            Key Material Out-of-Band (to hKTLoadedKeyTable
                            of a client ECU)."
        ::= { commonKeyTransferEventVarObjects 3 }

    commonOOBRecvdFailReason OBJECT-TYPE
        SYNTAX              INTEGER {
                                unauthorizedController( 1 ),
                                malformedOOBKeyFile( 2 )
                            }
        MAX-ACCESS          accessible-for-notify
        STATUS              current
        DESCRIPTION         "(U//FOUO) This object is reported in commonOOBRcvFailed
                            and identifies the reason the Key Material received
                            Out-of-Band was rejected (Not placed in hKTLoadedKeyTable
                            of the reporting client ECU)."
        ::= { commonKeyTransferEventVarObjects 4 }

    commonKTIBRcvdFailReason OBJECT-TYPE
        SYNTAX              INTEGER {
                                saNotFound( 1 ),
                                unauthorizedControl( 2 ),
                                malformedKTIBPacket( 3 ),
                                ppkInvalidKeyMaterial( 4 ),
                                invalidDataFilled( 5 ),
                                ppkKeyMaterialNotSupported( 6 ),
                                addToChainFailed( 7 ),
                                receiveTimeInvalid( 8 ),
                                ppkChainNotFound( 9 ),
                                ppkSupersessionNotAllowed( 10 ),
                                issuedKeyMissing( 11 )
                            }
        MAX-ACCESS          accessible-for-notify
        STATUS              current
        DESCRIPTION         "(U//FOUO) This object is reported in commonKTIBRcvFailed
                            and identifies the reason the Key Material received
                            In-Band was rejected (Not filled and assigned
                            in the reporting client ECU)."
        ::= { commonKeyTransferEventVarObjects 5 }

    commonKTIBXmitFailReason OBJECT-TYPE
        SYNTAX              INTEGER {
                                targetClientNotConnected( 1 ),
                                referencedKeyNotPresent( 2 ),
                                hv3SANotFound( 3 ),
                                ppkSANotFound( 4 ),
                                saNotFound( 5 ),
                                issuedKeyMissing( 6 ),
                                encryptionFailed( 7 )
                            }
        MAX-ACCESS          accessible-for-notify
        STATUS              current
        DESCRIPTION         "(U//FOUO) This object is reported in commonKTIBXmitFailed
                            and identifies the reason the Key Material that
                            the NET CON attempted to transmit through an
                            In-Band key transfer failed to be transmitted."
        ::= { commonKeyTransferEventVarObjects 6 }

    commonOOBClientPath OBJECT-TYPE
        SYNTAX              OCTET STRING (SIZE(0..256))
        MAX-ACCESS          accessible-for-notify
        STATUS              current
        DESCRIPTION         "(U//FOUO) This object specifies the Filename given
                            to the client during the Out-of-Band key file
                            transfer."
        ::= { commonKeyTransferEventVarObjects 7 }

    --R. Berman 20100826 DRN MIB00192 - Q-key management notification objects
    commonQkeyEventVarObjects OBJECT IDENTIFIER ::= { commonEventVariableObjects 11 }

    commonQkeyFillFailureReason OBJECT-TYPE
        SYNTAX              INTEGER {
                                ds-101ProtocolTimeout( 1 ),
                                ds-101ParityError( 2 ),
                                dataLinkError( 3 ),
                                storageCapacityExceeded( 4 ),
                                duplicateKey( 5 ),
                                cqcInvalidKeyMaterial( 6 ),
                                cqcKeyMaterialUnsupported( 7 ),
                                cqcKeyFailure( 8 ),
                                qpcInvalidKeyMaterial( 9 ),
                                qpcKeyMaterialUnsupported( 10 ),
                                qpcKeyFailure( 11 )
                            }
        MAX-ACCESS          accessible-for-notify
        STATUS              current
        DESCRIPTION         "(U//FOUO) The reason the Q-key fill failed."
        ::= { commonQkeyEventVarObjects 1 }

    commonQkeyDeleteReason OBJECT-TYPE
        SYNTAX              INTEGER {
                                userRequest( 1 ),
                                newBaseQkey( 2 )
                            }
        MAX-ACCESS          accessible-for-notify
        STATUS              current
        DESCRIPTION         "(U//FOUO) The reason the Q-key was deleted."
        ::= { commonQkeyEventVarObjects 2 }

    commonQkeyDeleteFailureReason OBJECT-TYPE
        SYNTAX              INTEGER {
                                baseQkey( 1 )
                            }
        MAX-ACCESS          accessible-for-notify
        STATUS              current
        DESCRIPTION         "(U//FOUO) The reason the Q-key failed to be deleted."
        ::= { commonQkeyEventVarObjects 3 }

    commonQkeyState OBJECT-TYPE
        SYNTAX              INTEGER {
                                uninstalled( 1 ),
                                installed( 2 )
                            }
        MAX-ACCESS          accessible-for-notify
        STATUS              current
        DESCRIPTION         "(U//FOUO) This object is used to indicate whether
                            a Q-key that is being reported as deleted was
                            removed from the uninstalled Q-key Table (neUninstalledTATable)
                            or the installed APPK Trust Anchors Table (hAPPKTrustAnchorTable)."
        ::= { commonQkeyEventVarObjects 4 }

    commonQkeyInstallFailureReason OBJECT-TYPE
        SYNTAX              INTEGER {
                                qkeyExpired( 1 )
                            }
        MAX-ACCESS          accessible-for-notify
        STATUS              current
        DESCRIPTION         "(U//FOUO) The reason the Q-key failed to be installed."
        ::= { commonQkeyEventVarObjects 5 }

    commonSysLevelEventVarObjects OBJECT IDENTIFIER ::= { commonEventVariableObjects 12 }

    commonUserName OBJECT-TYPE
        SYNTAX              SnmpAdminString (SIZE(1..32))
        MAX-ACCESS          accessible-for-notify
        STATUS              current
        DESCRIPTION         "(U//FOUO) The name of the operator or Remote Manager
                            issuing the reported configuration change or
                            command."
        ::= { commonSysLevelEventVarObjects 1 }

    commonNotifEvents OBJECT IDENTIFIER ::= { commonNotifications 3 }

    commonSecurityNotifEvents OBJECT IDENTIFIER ::= { commonNotifEvents 1 }

    commonAudLogInitialized NOTIFICATION-TYPE
        OBJECTS	{
        		commonStationID,
        		commonSystemDate,
        		commonSNMPUserName,
        		commonAuditLogInitializeReason
        	}
        STATUS		    current
        DESCRIPTION         "(U//FOUO) The notification from the device indicating
                            that the notification log (nlmLogTable) is no
                            longer full or close to full. This notification
                            should be sent when room has been made in the
                            log for any reason (EG, an operator has cleared
                            the log)."
        ::= { commonSecurityNotifEvents 1 }

    commonAudLogStatusChanged NOTIFICATION-TYPE
        OBJECTS	{
        		commonStationID,
        		commonSystemDate,
        		commonAudLogStatus
        	}
        STATUS		    current
        DESCRIPTION         "(U//FOUO) The notification from the device indicating
                            that the notification log (nlmLogTable) is no
                            longer full or close to full. This notification
                            should be sent when room has been made in the
                            log for any reason (EG, an operator has cleared
                            the log).
                            
                            (U//FOUO) Notification from the device indicating
                            that the notification log (nlmLogTable) threshold
                            has been crossed and that the log is close to
                            being full and needs to be downloaded and cleared.
                            
                            (U//FOUO) The notification from the device indicating
                            that the notification log (nlmLogTable) is full,
                            and the device will begin deleting or overwriting
                            the oldest events."
        ::= { commonSecurityNotifEvents 2 }

    commonBatteryStatusChanged NOTIFICATION-TYPE
        OBJECTS	{
        		commonStationID,
        		commonSystemDate,
        		commonBatteryStatus
        	}
        STATUS		    current
        DESCRIPTION         "(U//FOUO) The notification from the device indicating
                            that the battery should be or has been charged
                            or changed."
        ::= { commonSecurityNotifEvents 3 }

    commonConfigConflict2 NOTIFICATION-TYPE
        OBJECTS	{
        		commonStationID,
        		commonSystemDate,
        		commonConfigConflictDescription
        	}
        STATUS		    current
        DESCRIPTION         "(U//FOUO) Notification that an otherwise valid
                            SNMP SET failed due to a configuration conflict
                            within the managed device. This notification
                            will be used to supplement the SNMP error responses
                            Inconsistent Name and Inconsistent Value to identify
                            the configuration conflict more specifically."
        ::= { commonSecurityNotifEvents 4 }

    commonKeyFilled2 NOTIFICATION-TYPE
        OBJECTS	{
        		commonStationID,
        		commonSystemDate
        	}
        STATUS		    current
        DESCRIPTION         "(U//FOUO) This notification indicates that one
                            or more keys were successfully filled."
        ::= { commonSecurityNotifEvents 5 }

    commonPrivilegItemValue2 NOTIFICATION-TYPE
        OBJECTS	{
        		commonUserName,
        		commonPrivModItemName,
        		commonOrigConfigDataValue,
        		commonNewConfigDataValue
        	}
        STATUS		    current
        DESCRIPTION         "(U//FOUO) Notification of the change of a configuration
                            data value requiring SSO-Privilege to change."
        ::= { commonSecurityNotifEvents 6 }

    commonRealTimeClockSet2 NOTIFICATION-TYPE
        OBJECTS	{
        		commonUserName,
        		commonUpdateSystemDate
        	}
        STATUS		    current
        DESCRIPTION         "(U//FOUO) Notification that the Real Time Clock
                            has been set."
        ::= { commonSecurityNotifEvents 7 }

    commonUnIdentifiedKeyFillError2 NOTIFICATION-TYPE
        OBJECTS	{
        		commonUserName,
        		commonUnIdentifiedKeyFillErrorReason
        	}
        STATUS		    current
        DESCRIPTION         "(U//FOUO) A notification that unidentifiable data
                            filled to the ECU fill port was not accepted."
        ::= { commonSecurityNotifEvents 8 }

    commonZeroize2 NOTIFICATION-TYPE
        OBJECTS	{
        		commonUserName,
        		commonZeroizeReason
        	}
        STATUS		    current
        DESCRIPTION         "(U//FOUO) This notification is generated in response
                            to a Zeroize Command."
        ::= { commonSecurityNotifEvents 9 }

    commonCIKNotifEvents OBJECT IDENTIFIER ::= { commonNotifEvents 2 }

    commonCikCreated2 NOTIFICATION-TYPE
        OBJECTS	{
        		commonUserName,
        		cikId,
        		commonCIKCreateReason
        	}
        STATUS		    current
        DESCRIPTION         "(U//FOUO) This notification indicates a CIK was
                            just created, and identifies the CIK Number and
                            what initiated the CIK creation."
        ::= { commonCIKNotifEvents 1 }

    commonCikDeleted2 NOTIFICATION-TYPE
        OBJECTS	{
        		commonUserName,
        		cikId
        	}
        STATUS		    current
        DESCRIPTION         "(U//FOUO) This notification indicates a CIK was
                            just deleted, and identifies the deleted CIK."
        ::= { commonCIKNotifEvents 2 }

    commonFFNotifEvents OBJECT IDENTIFIER ::= { commonNotifEvents 3 }

    commonACLUpdated2 NOTIFICATION-TYPE
        OBJECTS	{
        		commonUserName,
        		neACLKMID,
        		commonACLUpdateAction
        	}
        STATUS		    current
        DESCRIPTION         "(U//FOUO) Notification that the Access Control
                            List was updated."
        ::= { commonFFNotifEvents 1 }

    commonChildSATEKCreated NOTIFICATION-TYPE
        OBJECTS	{
        		commonSAChildIndex,
        		commonSAIndex,
        		commonRemoteSAspi,
        		commonAddressType,
        		commonRemoteCTAddress,
        		commonFFSARole
        	}
        STATUS		    current
        DESCRIPTION         "(U//FOUO) This notification identifies the creation
                            of a Child SA TEK as the result of an IKE negotiation."
        ::= { commonFFNotifEvents 2 }

    commonChildSATEKDeleted NOTIFICATION-TYPE
        OBJECTS	{
        		commonSAChildIndex,
        		commonSAIndex,
        		commonIKEv2DeletedReason
        	}
        STATUS		    current
        DESCRIPTION         "(U//FOUO) This notification identifies the deletion
                            of a Child SA TEK."
        ::= { commonFFNotifEvents 3 }

    commonFFKeyExpirationWarning NOTIFICATION-TYPE
        OBJECTS	{
        		commonStationID,
        		commonSystemDate,
        		commonKMID,
        		commonUniversalID,
        		commonUniversalEdition,
        		commonExpirationDate
        	}
        STATUS		    current
        DESCRIPTION         "(U//FOUO) The notification from the device indicating
                            that a given Firefly key is going to expire within
                            one month. This notification should be sent when
                            the one month time is reached, and should be
                            sent after startup for any key within the system
                            which has less than one month left in its expiration
                            window."
        ::= { commonFFNotifEvents 4 }

    commonFFTEKDeleted2 NOTIFICATION-TYPE
        OBJECTS	{
        		commonSAIndex,
        		commonBankNum,
        		commonIKEv1DeletedReason
        	}
        STATUS		    current
        DESCRIPTION         "(U/FOUO) This notification indicates the FF TEK
                            has been deleted."
        ::= { commonFFNotifEvents 5 }

    commonFFVSDeleted2 NOTIFICATION-TYPE
        OBJECTS	{
        		commonUserName,
        		commonKMID,
        		commonUniversalID,
        		commonUniversalEdition,
        		commonFFVSDeleteReason
        	}
        STATUS		    current
        DESCRIPTION         "(U/FOUO) This notification indicates the filled
                            FFVS, current or current/next has been deleted."
        ::= { commonFFNotifEvents 6 }

    commonFFVSExpired2 NOTIFICATION-TYPE
        OBJECTS	{
        		commonKMID,
        		commonUniversalID,
        		commonUniversalEdition,
        		commonExpirationDate
        	}
        STATUS		    current
        DESCRIPTION         "(U//FOUO) Indicates the FFVS filled in this device
                            has expired."
        ::= { commonFFNotifEvents 7 }

    commonFFVSFillFailed2 NOTIFICATION-TYPE
        OBJECTS	{
        		commonUserName,
        		commonFFFailedFillReason
        	}
        STATUS		    current
        DESCRIPTION         "(U//FOUO) This notification indicates the failure
                            of an attempted fill of a FireFly Vector Set."
        ::= { commonFFNotifEvents 8 }

    commonFFVSFillOK3 NOTIFICATION-TYPE
        OBJECTS	{
        		commonUserName,
        		commonKMID,
        		commonUniversalID,
        		commonUniversalEdition,
        		commonClassification,
        		commonFireFlyMaterialType,
        		commonExpirationDate,
        		commonFireFlyPartitionCode,
        		commonFireFlyKeyType,
        		commonFireFlyVectorType
        	}
        STATUS		    current
        DESCRIPTION         "(U//FOUO) This notification indicates a FireFly
                            Vector Set was successfully filled."
        ::= { commonFFNotifEvents 9 }

    commonIKESACreated NOTIFICATION-TYPE
        OBJECTS	{
        		commonSAIndex,
        		commonAddressType,
        		commonRemoteCTAddress,
        		commonInitiatorSAspi,
        		commonResponderSAspi
        	}
        STATUS		    current
        DESCRIPTION         "(U//FOUO) This Notification identifies the creation
                            of an FFVS IKEv2 SA."
        ::= { commonFFNotifEvents 10 }

    commonIKESADeleted NOTIFICATION-TYPE
        OBJECTS	{
        		commonSAIndex,
        		commonIKEv2DeletedReason
        	}
        STATUS		    current
        DESCRIPTION         "(U//FOUO) This Notification identifies the deletion
                            of an FFVS IKEv2 SA."
        ::= { commonFFNotifEvents 11 }

    commonIKEv1NegotiationFailure NOTIFICATION-TYPE
        OBJECTS	{
        		commonSAIndex,
        		commonAddressType,
        		commonRemoteCTAddress,
        		commonFFSARole,
        		commonFFNegotiaFailureReason,
        		commonLastIkePduSent
        	}
        STATUS		    current
        DESCRIPTION         "(U//FOUO) This Notification identifies the failure
                            of an FFVS IKEv1 Negotiation."
        ::= { commonFFNotifEvents 12 }

    commonIKEv2NegotiationFailure NOTIFICATION-TYPE
        OBJECTS	{
        		commonSAIndex,
        		commonSAChildIndex,
        		commonAddressType,
        		commonRemoteCTAddress,
        		commonPort,
        		commonInitiatorSAspi,
        		commonResponderSAspi,
        		commonFFSARole,
        		commonIKEv2NegotiaFailureReason,
        		commonIKEv2ExchangeType
        	}
        STATUS		    current
        DESCRIPTION         "(U//FOUO) This Notification identifies the failure
                            of an FFVS IKEv2 Negotiation."
        ::= { commonFFNotifEvents 13 }

    commonFFTEKCreated2 NOTIFICATION-TYPE
        OBJECTS	{
        		commonSAIndex,
        		commonBankNum,
        		commonRemoteFFKMID,
        		commonRemoteSAspi,
        		commonAddressType,
        		commonRemoteCTAddress,
        		commonFFSARole
        	}
        STATUS		    current
        DESCRIPTION         "(U//FOUO) This notification identifies the creation
                            of a TEK as the result of an IKE negotiation."
        ::= { commonFFNotifEvents 14 }

    commonPPKNotifEvents OBJECT IDENTIFIER ::= { commonNotifEvents 4 }

    commonDGSKCreated NOTIFICATION-TYPE
        OBJECTS	{
        		commonUserName,
        		commonDGSKIndex,
        		commonShortTitle,
        		commonUsageType
        	}
        STATUS		    current
        DESCRIPTION         "(U//FOUO) Notification that the identified DGSK
                            was created."
        ::= { commonPPKNotifEvents 1 }

    commonDGSKDeleted NOTIFICATION-TYPE
        OBJECTS	{
        		commonUserName,
        		commonDGSKIndex,
        		commonShortTitle,
        		commonUsageType,
        		commonDGSKDeleteReason
        	}
        STATUS		    current
        DESCRIPTION         "(U//FOUO) Notification that the identified DGSK
                            was deleted."
        ::= { commonPPKNotifEvents 2 }

    commonDGSKExpired NOTIFICATION-TYPE
        OBJECTS	{
        		commonDGSKIndex,
        		commonShortTitle,
        		commonEffectiveDate,
        		commonUsageType
        	}
        STATUS		    current
        DESCRIPTION         "(U//FOUO) Notification that an expired DGSK is
                            in use."
        ::= { commonPPKNotifEvents 3 }

    commonDGSKFillFail NOTIFICATION-TYPE
        OBJECTS	{
        		commonUserName,
        		commonDGSKFailedFillReason
        	}
        STATUS		    current
        DESCRIPTION         "(U//FOUO) Notification that the DGSK fill failed."
        ::= { commonPPKNotifEvents 4 }

    commonEKExpiredIKEv1 NOTIFICATION-TYPE
        OBJECTS	{
        		commonStationID,
        		commonSystemDate,
        		commonClassification,
        		commonCryptoSuite,
        		commonUniversalID
        	}
        STATUS		    current
        DESCRIPTION         "(U//FOUO) Notification that the identified group
                            of Exclusion Keys, with the same classification,
                            suite, and universal ID, are in use and no changeover
                            key IKEv1 EK exists."
        ::= { commonPPKNotifEvents 5 }

    commonEKExpiredIKEv2 NOTIFICATION-TYPE
        OBJECTS	{
        		commonStationID,
        		commonSystemDate,
        		commonClassification,
        		commonCryptoSuite
        	}
        STATUS		    current
        DESCRIPTION         "(U//FOUO) Notification that the identified group
                            of Exclusion Keys, with the same classification
                            and suite, are in use and no changeover key IKEv2
                            EK exists."
        ::= { commonPPKNotifEvents 6 }

    commonEKUseDGSK NOTIFICATION-TYPE
        OBJECTS	{
        		commonUserName,
        		commonDGSKIndex,
        		commonShortTitle,
        		commonEKType,
        		commonUniversalID,
        		commonEffectiveDate,
        		commonCryptoSuite
        	}
        STATUS		    current
        DESCRIPTION         "(U//FOUO) Notification that the identified Exclusion
                            DGSK Key use was configured."
        ::= { commonPPKNotifEvents 7 }

    commonEKUsePPK NOTIFICATION-TYPE
        OBJECTS	{
        		commonUserName,
        		commonShortTitle,
        		commonEdition,
        		commonSegment,
        		commonEKType,
        		commonUniversalID,
        		commonEffectiveDate,
        		commonCryptoSuite
        	}
        STATUS		    current
        DESCRIPTION         "(U//FOUO) Notification that the identified Exclusion
                            PPK Key use was configured."
        ::= { commonPPKNotifEvents 8 }

    commonManualSAUsePPK NOTIFICATION-TYPE
        OBJECTS	{
        		commonUserName,
        		commonShortTitle,
        		commonEdition,
        		commonSegment,
        		commonChainName,
        		commonChainOrder,
        		commonEffectiveDate,
        		commonCryptoSuite
        	}
        STATUS		    current
        DESCRIPTION         "(U//FOUO) Notification that the identified Manuals
                            SA PPK use was configured."
        ::= { commonPPKNotifEvents 9 }

    commonPPKDeleted2 NOTIFICATION-TYPE
        OBJECTS	{
        		commonUserName,
        		commonShortTitle,
        		commonEdition,
        		commonSegment,
        		commonUsageType,
        		commonPPKDeleteReason
        	}
        STATUS		    current
        DESCRIPTION         "(U//FOUO) Notification that the identified PPK
                            was deleted."
        ::= { commonPPKNotifEvents 10 }

    commonPPKExpired2 NOTIFICATION-TYPE
        OBJECTS	{
        		commonShortTitle,
        		commonEdition,
        		commonSegment,
        		commonEffectiveDate,
        		commonUsageType
        	}
        STATUS		    current
        DESCRIPTION         "(U//FOUO) Notification that an expired PPK is
                            in use."
        ::= { commonPPKNotifEvents 11 }

    commonPPKFillFail2 NOTIFICATION-TYPE
        OBJECTS	{
        		commonUserName,
        		commonPPKFailedFillReason
        	}
        STATUS		    current
        DESCRIPTION         "(U//FOUO) Notification that the PPK fill failed."
        ::= { commonPPKNotifEvents 12 }

    commonPPKFillOK2 NOTIFICATION-TYPE
        OBJECTS	{
        		commonUserName,
        		commonShortTitle,
        		commonEdition,
        		commonSegment,
        		commonClassification,
        		commonUsageType
        	}
        STATUS		    current
        DESCRIPTION         "(U//FOUO) Notification that the identified PPK
                            was successfully filled."
        ::= { commonPPKNotifEvents 13 }

    commonPPKKeyExpirationWarning NOTIFICATION-TYPE
        OBJECTS	{
        		commonStationID,
        		commonSystemDate
        	}
        STATUS		    current
        DESCRIPTION         "(U//FOUO) The notification from the device indicating
                            that 1 or more PPK chains' current key is expiring
                            within 30 days. This notification should be sent
                            when the 30 day time period is reached, and should
                            be sent after startup for at least one key within
                            the system which has less than 30 days left in
                            its expiration window."
        ::= { commonPPKNotifEvents 14 }

    commonPPKSADInEntryOperation NOTIFICATION-TYPE
        OBJECTS	{
        		commonAction,
        		commonSAIndex,
        		commonSPIChainReference,
        		commonChainName,
        		commonAddressType,
        		commonRemoteCTAddress,
        		commonRemotePTAddress,
        		commonECNSetting,
        		commonTransformSuite
        	}
        STATUS		    current
        DESCRIPTION         "(U//FOUO) Notification that an incoming PPK SAD
                            entry was activated or destroyed."
        ::= { commonPPKNotifEvents 15 }

    commonPPKSADOutEntryOperation NOTIFICATION-TYPE
        OBJECTS	{
        		commonAction,
        		commonSAIndex,
        		commonSPIChainReference,
        		commonChainName,
        		commonAddressType,
        		commonLocalCTAddress,
        		commonLocalPTAddress,
        		commonECNSetting,
        		commonTransformSuite,
        		commonDSCPSetting,
        		commonDSCPValue,
        		commonDFBitSetting
        	}
        STATUS		    current
        DESCRIPTION         "(U//FOUO) Notification that an outgoing PPK SAD
                            entry was activated or destroyed."
        ::= { commonPPKNotifEvents 16 }

    commonSharedSecretExpired NOTIFICATION-TYPE
        OBJECTS	{
        		commonStationID,
        		commonSystemDate,
        		commonClassification,
        		commonCryptoSuite,
        		commonKeyMode
        	}
        STATUS		    current
        DESCRIPTION         "(U//FOUO) Notification that an expired Shared
                            Secret Key is in use."
        ::= { commonPPKNotifEvents 17 }

    commonSharedSecretExpiringDGSK NOTIFICATION-TYPE
        OBJECTS	{
        		commonStationID,
        		commonSystemDate,
        		commonDGSKIndex,
        		commonShortTitle,
        		commonClassification,
        		commonCryptoSuite,
        		commonKeyMode,
        		commonEffectiveDate
        	}
        STATUS		    current
        DESCRIPTION         "(U//FOUO) Notification that the Shared Secret
                            DGSK key is expiring within 30 days and no changeover
                            key exists. This notification should be sent
                            when the 30 day time period is reached, and should
                            be sent after startup when the indicated key
                            has less than 30 days left in its expiration
                            window."
        ::= { commonPPKNotifEvents 18 }

    commonSharedSecretExpiringPPK NOTIFICATION-TYPE
        OBJECTS	{
        		commonStationID,
        		commonSystemDate,
        		commonShortTitle,
        		commonEdition,
        		commonSegment,
        		commonClassification,
        		commonCryptoSuite,
        		commonKeyMode,
        		commonEffectiveDate
        	}
        STATUS		    current
        DESCRIPTION         "(U//FOUO) Notification that the Shared Secret
                            PPK key is expiring within 30 days and no changeover
                            key exists. This notification should be sent
                            when the 30 day time period is reached, and should
                            be sent after startup when the indicated key
                            has less than 30 days left in its expiration
                            window."
        ::= { commonPPKNotifEvents 19 }

    commonSharedSecretUseDGSK NOTIFICATION-TYPE
        OBJECTS	{
        		commonUserName,
        		commonDGSKIndex,
        		commonShortTitle,
        		commonEffectiveDate,
        		commonCryptoSuite,
        		commonKeyMode
        	}
        STATUS		    current
        DESCRIPTION         "(U//FOUO) Notification that the identified Shared
                            Secret DGSK Key use was configured."
        ::= { commonPPKNotifEvents 20 }

    commonSharedSecretUsePPK NOTIFICATION-TYPE
        OBJECTS	{
        		commonUserName,
        		commonShortTitle,
        		commonEdition,
        		commonSegment,
        		commonEffectiveDate,
        		commonCryptoSuite
        	}
        STATUS		    current
        DESCRIPTION         "(U//FOUO) Notification that the identified Shared
                            Secret PPK Key use was configured."
        ::= { commonPPKNotifEvents 21 }

    commonSNMPNotifEvents OBJECT IDENTIFIER ::= { commonNotifEvents 5 }

    commonSNMPUserUpdate2 NOTIFICATION-TYPE
        OBJECTS	{
        		commonUserName,
        		commonSNMPUserTableChanged,
        		commonSNMPTableRowName,
        		commonSNMPUserTableOperation
        	}
        STATUS		    current
        DESCRIPTION         "(U//FOUO) This Notification indicates the configuration
                            of an SNMP user has been changed in one of the
                            SNMPv2-MIB tables."
        ::= { commonSNMPNotifEvents 1 }

    commonIPNotifEvents OBJECT IDENTIFIER ::= { commonNotifEvents 6 }

    commonAutoAddressConfigFail2 NOTIFICATION-TYPE
        OBJECTS	{
        		commonStationID,
        		commonSystemDate,
        		commonIfIndex,
        		commonAutoconfigurationFailure
        	}
        STATUS		    current
        DESCRIPTION         "(U//FOUO) Notification that the Stateless Address
                            Autoconfiguration (SAA) protocol has failed to
                            aquire an address on the interface identified
                            by the notification object commonIfIndex."
        ::= { commonIPNotifEvents 1 }

    commonIPAddrChanged NOTIFICATION-TYPE
        OBJECTS	{
        		commonStationID,
        		commonSystemDate,
        		commonUserName,
        		commonIfIndex,
        		commonAddressType
        	}
        STATUS		    current
        DESCRIPTION         "(U//FOUO) Notification that the IP address of
                            the interface specified has changed."
        ::= { commonIPNotifEvents 2 }

    commonNetDuplicateAddressDetected NOTIFICATION-TYPE
        OBJECTS	{
        		commonStationID,
        		commonSystemDate,
        		commonAddressType,
        		commonRemoteCTAddress
        	}
        STATUS		    current
        DESCRIPTION         "(U//FOUO) This notification event indicates that
                            a duplicate address has been detected during
                            the duplicate address detection process.
                            
                            (U//FOUO) commonAddressType and commonRemoteCTAddress
                            indicate the duplicated address."
        ::= { commonIPNotifEvents 3 }

    commonPSEQNError3 NOTIFICATION-TYPE
        OBJECTS	{
        		commonSAIndex,
        		commonAddressType,
        		commonRemoteHostAddress,
        		commonLocalHostAddress,
        		commonRejectedPSEQN,
        		commonPSEQNRejectCount
        	}
        STATUS		    current
        DESCRIPTION         "(U//FOUO) Notification of receipt of a PDU with
                            a PSEQN error on an SA and the number of PSEQN
                            errors in the measurement period.
                            
                            (U/FOUO) The variable commonRemoteHostAddress
                            contains the source host IP address. The variable
                            commonLocalHostAddress contains the destination
                            host IP address."
        ::= { commonIPNotifEvents 4 }

    commonIFNotifEvents OBJECT IDENTIFIER ::= { commonNotifEvents 7 }

    commonIFSpeedModeMismatch2 NOTIFICATION-TYPE
        OBJECTS	{
        		commonStationID,
        		commonSystemDate,
        		commonIfSpeedModePT,
        		commonIfSpeedModeCT
        	}
        STATUS		    current
        DESCRIPTION         "(U//FOUO) This notification is generated each
                            time the PT and CT interfaces are configured
                            at mismatched speeds or modes.
                            
                            (U//FOUO) In the case where both interfaces are
                            configured with static values, the notification
                            is sent when the interfaces are enabled with
                            mismatched speed or modes.
                            
                            (U//FOUO) In cases where one or both interfaces
                            are using auto-negotiation as a configuration
                            method, this notification is sent when the ECU
                            receives a response from an interface speed/mode
                            negotiation such that the PT and CT interface
                            speeds or modes are mismatched."
        ::= { commonIFNotifEvents 1 }

    commonIFSpeedNegotiationFailure2 NOTIFICATION-TYPE
        OBJECTS	{
        		commonStationID,
        		commonSystemDate,
        		commonIfIndex
        	}
        STATUS		    current
        DESCRIPTION         "(U//FOUO) This notification is generated each
                            time the PT and CT interfaces fail to negotiate
                            a speed over the network.
                            
                            (U//FOUO) A value of 1 for the commonIfIndex
                            is the PT side interface and a value of 2 for
                            the commonIfIndex is the CT side interface."
        ::= { commonIFNotifEvents 2 }

    commonLinkStatusChanged NOTIFICATION-TYPE
        OBJECTS	{
        		commonStationID,
        		commonSystemDate,
        		commonLinkStatus,
        		commonIfIndex,
        		commonIfAdminStatus,
        		commonIfOperStatus
        	}
        STATUS		    current
        DESCRIPTION         "(U//FOUO) A linkDown trap signifies that the SNMP
                            entity, acting in an agent role, has detected
                            that the commonIfOperStatus object for one of
                            its communication links is about to enter the
                            down state from some other state (but not from
                            the notPresent state). This other state is indicated
                            by the included value of commonIfOperStatus.
                            
                            (U//FOUO) A linkUp trap signifies that the SNMP
                            entity, acting in an agent role, has detected
                            that the commonIfOperStatus object for one of
                            its communication links left the down state and
                            transitioned into some other state (but not into
                            the notPresent state). This other state is indicated
                            by the included value of commonIfOperStatus."
        ::= { commonIFNotifEvents 3 }

    commonDhcpStateChanged NOTIFICATION-TYPE
        OBJECTS	{
        		commonStationID,
        		commonSystemDate,
        		commonSNMPUserName,
        		commonIfIndex,
        		commonAddressType,
        		commonDhcpState
        	}
        STATUS		    current
        DESCRIPTION         "(U//FOUO) Notification that the DHCP state of
                            the interface specified has changed."
        ::= { commonIFNotifEvents 4 }
		
    commonPACNotifEvents OBJECT IDENTIFIER ::= { commonNotifEvents 8 }

    commonPACOperation NOTIFICATION-TYPE
        OBJECTS	{
        		commonUserName,
        		commonPACAction,
        		neUnInstalledPACBaseType,
        		neUnInstalledPACID,
        		neUnInstalledPACCOI,
        		neUnInstalledPACUserID,
        		neUnInstalledPACSourceID,
        		neUnInstalledPACNationalID,
        		commonPACState,
        		commonPACReason
        	}
        STATUS		    current
        DESCRIPTION         "(U//FOUO) This notification indicates a PAC Moduli
                            operation completed successfully."
        ::= { commonPACNotifEvents 1 }

    commonPACOperationFailed NOTIFICATION-TYPE
        OBJECTS	{
        		commonUserName,
        		commonPACAction,
        		commonPACFailedReason
        	}
        STATUS		    current
        DESCRIPTION         "(U//FOUO) This notification indicates a PAC Moduli
                            operation failed."
        ::= { commonPACNotifEvents 2 }

    commonKTNotifEvents OBJECT IDENTIFIER ::= { commonNotifEvents 9 }

    commonIssuedKeyDeleted2 NOTIFICATION-TYPE
        OBJECTS	{
        		commonStationID,
        		commonSystemDate,
        		commonShortTitle,
        		commonEdition,
        		commonSegment,
        		commonRegister,
        		commonKeyUse,
        		commonClassification,
        		commonIssuedKeyDeleteReason
        	}
        STATUS		    current
        DESCRIPTION         "(U//FOUO) Identifies that an issued key was deleted."
        ::= { commonKTNotifEvents 1 }

    commonKeyIssueFailed2 NOTIFICATION-TYPE
        OBJECTS	{
        		commonStationID,
        		commonSystemDate,
        		commonKeyIssueFailReason
        	}
        STATUS		    current
        DESCRIPTION         "(U//FOUO) Identifies that a Traditional or FFVS
                            Key failed an issue attempt from a key fill device
                            into an ECU."
        ::= { commonKTNotifEvents 2 }

    commonKeyIssueOK2 NOTIFICATION-TYPE
        OBJECTS	{
        		commonStationID,
        		commonSystemDate,
        		commonShortTitle,
        		commonEdition,
        		commonSegment,
        		commonRegister,
        		commonKeyUse,
        		commonClassification
        	}
        STATUS		    current
        DESCRIPTION         "(U//FOUO) Identifies that a Traditional or FFVS
                            Key has been successfully issued from a key fill
                            device into an ECU."
        ::= { commonKTNotifEvents 3 }

    commonKTIBClientEntryDeleted2 NOTIFICATION-TYPE
        OBJECTS	{
        		commonStationID,
        		commonSystemDate,
        		commonAddressType,
        		commonRemoteCTAddress,
        		commonKeyIndex
        	}
        STATUS		    current
        DESCRIPTION         "(U//FOUO) Identifies that an in-band clients table
                            entry referencing a key in the loaded key table
                            was deleted because the referenced key was deleted."
        ::= { commonKTNotifEvents 4 }

    commonKTIBLocalOperation NOTIFICATION-TYPE
        OBJECTS	{
        		commonStationID,
        		commonSystemDate,
        		commonShortTitle,
        		commonEdition,
        		commonSegment,
        		commonRegister,
        		commonStatus,
        		commonKTIBLocalReason
        	}
        STATUS		    current
        DESCRIPTION         "(U//FOUO) Identifies that the Key Material has
                            been successfully or unsuccessfully filled and
                            assigned to the NET CON ECU."
        ::= { commonKTNotifEvents 5 }

    commonKTIBRcvFailed2 NOTIFICATION-TYPE
        OBJECTS	{
        		commonStationID,
        		commonSystemDate,
        		commonKTIBRcvdFailReason
        	}
        STATUS		    current
        DESCRIPTION         "(U//FOUO) Identifies that an In-Band Key Transfer
                            failed at the receiving Client ECU."
        ::= { commonKTNotifEvents 6 }

    commonKTIBRcvOK2 NOTIFICATION-TYPE
        OBJECTS	{
        		commonStationID,
        		commonSystemDate,
        		commonShortTitle,
        		commonEdition,
        		commonSegment
        	}
        STATUS		    current
        DESCRIPTION         "(U//FOUO) Identifies that an In-Band Key Transfer
                            was successfully received."
        ::= { commonKTNotifEvents 7 }

    commonKTIBXmitFailed2 NOTIFICATION-TYPE
        OBJECTS	{
        		commonStationID,
        		commonSystemDate,
        		commonAddressType,
        		commonRemoteCTAddress,
        		commonKeyIndex,
        		commonKTIBXmitFailReason
        	}
        STATUS		    current
        DESCRIPTION         "(U//FOUO) Identifies that an In-Band Key Transfer
                            failed at the transmitting NET CON ECU."
        ::= { commonKTNotifEvents 8 }

    commonOOBFileEntryDeleted2 NOTIFICATION-TYPE
        OBJECTS	{
        		commonStationID,
        		commonSystemDate,
        		commonKeyFile,
        		commonKeyIndex,
        		commonShortTitle,
        		commonEdition,
        		commonSegment,
        		commonRegister
        	}
        STATUS		    current
        DESCRIPTION         "(U//FOUO) Identifies that an Out-of-Band Key File
                            entry referencing a key in the Loaded Key table
                            was deleted because the referenced key was deleted."
        ::= { commonKTNotifEvents 9 }

    commonOOBRcvOperation NOTIFICATION-TYPE
        OBJECTS	{
        		commonStationID,
        		commonSystemDate,
        		commonOOBClientPath,
        		commonStatus,
        		commonOOBRcvdReason
        	}
        STATUS		    current
        DESCRIPTION         "(U//FOUO) Identifies that an issue received by
                            a client ECU completed successfully or failed."
        ::= { commonKTNotifEvents 10 }

    commonOOBXmitOperation NOTIFICATION-TYPE
        OBJECTS	{
        		commonStationID,
        		commonSystemDate,
        		commonUserName,
        		commonAddressType,
        		commonAddress,
        		commonKeyFile,
        		commonStatus,
        		commonOOBIssueReason
        	}
        STATUS		    current
        DESCRIPTION         "(U//FOUO) Identifies that the specified key file
                            was successfully or unsuccessfully transmitted
                            Out-of-Band by a Key Transfer NET CON."
        ::= { commonKTNotifEvents 11 }

    commonQKeyNotifEvents OBJECT IDENTIFIER ::= { commonNotifEvents 10 }

    commonQkeyOperation NOTIFICATION-TYPE
        OBJECTS	{
        		commonUserName,
        		commonQkeyAction,
        		neUninstalledTAType,
        		neUninstalledTAShortTitle,
        		neUninstalledTAKMID,
        		commonQkeyState,
        		commonQkeyReason
        	}
        STATUS		    current
        DESCRIPTION         "(U//FOUO) This notification indicates a Q-key
                            operation completed successfully."
        ::= { commonQKeyNotifEvents 1 }

    commonQkeyOperationFailed NOTIFICATION-TYPE
        OBJECTS	{
        		commonUserName,
        		commonQkeyAction,
        		commonQkeyFailedReason
        	}
        STATUS		    current
        DESCRIPTION         "(U//FOUO) This notification indicates a Q-key
                            operation failed."
        ::= { commonQKeyNotifEvents 2 }

    commonSWDLNotifEvents OBJECT IDENTIFIER ::= { commonNotifEvents 11 }

    commonFirmwareOperation NOTIFICATION-TYPE
        OBJECTS	{
        		commonStationID,
        		commonSystemDate,
        		commonFirmwareAction,
        		commonFdsURI
        	}
        STATUS		    current
        DESCRIPTION         "(U//FOUO) This notification is sent when a download
                            has been completed and has succeeded. The commonFdsURI
                            should reference the URI that was used for the
                            download.
                            
                            (U//FOUO) This notification is sent when the
                            installation of a new firmware image has succeeded
                            to the point that the device is about to restart
                            to load the new firmware. IE, this is sent just
                            before resetting the device and not after it
                            has rebooted. Sending of this notification is
                            not mandatory."
        ::= { commonSWDLNotifEvents 1 }

    commonFirmwareOperationFailed NOTIFICATION-TYPE
        OBJECTS	{
        		commonStationID,
        		commonSystemDate,
        		commonFirmwareAction,
        		commonFdsURI,
        		commonFdErrCode,
        		commonFdErrDetail
        	}
        STATUS		    current
        DESCRIPTION         "(U//FOUO) This notification is sent when a download
                            fails due to a transfer error. The commonFdsURI
                            should reference the URI with which the error
                            occurred.
                            
                            (U//FOUO) This notification is sent when the
                            installation of a new firmware image has failed."
        ::= { commonSWDLNotifEvents 2 }

    commonFileTransferSucceeded NOTIFICATION-TYPE
        OBJECTS	{
        		commonStationID,
        		commonSystemDate,
        		commonURI
        	}
        STATUS		    current
        DESCRIPTION         "(U//FOUO) This notification is sent when a file
                            transfer has been completed and has succeeded."
        ::= { commonSWDLNotifEvents 3 }

    commonFileTransferFailed NOTIFICATION-TYPE
        OBJECTS	{
        		commonStationID,
        		commonSystemDate,
        		commonURI,
        		commonErrDetail
        	}
        STATUS		    current
        DESCRIPTION         "(U//FOUO) This notification is sent when a file
                            transfer fails."
        ::= { commonSWDLNotifEvents 4 }

    commonAuditUploadNotifEvents OBJECT IDENTIFIER ::= { commonNotifEvents 12 }

    commonAuditUploadRequested NOTIFICATION-TYPE
        OBJECTS	{
        		commonStationID,
        		commonSystemDate,
        		commonUserName
        	}
        STATUS		    current
        DESCRIPTION         "(U//FOUO) This notification indicates an audit upload
                            has been initiated."
        ::= { commonAuditUploadNotifEvents 1 }

    commonAuditUploadOperation NOTIFICATION-TYPE
        OBJECTS	{
        		commonStationID,
        		commonSystemDate,
        		commonStatus,
        		commonURI,
        		commonErrDetail
        	}
        STATUS		    current
        DESCRIPTION         "(U//FOUO) This notification indicates an audit upload
                            has completed successfully or failed."
        ::= { commonAuditUploadNotifEvents 2 }

    commonAuditUploadKeyPairGen NOTIFICATION-TYPE
        OBJECTS	{
        		commonStationID,
        		commonSystemDate,
        		commonUserName
        	}
        STATUS		    current
        DESCRIPTION         "(U//FOUO) This notification is sent when an audit upload
                            key pair is generated."
        ::= { commonAuditUploadNotifEvents 3 }


    commonNotifEventVariableObjects OBJECT IDENTIFIER ::= { commonNotifications 4 }

    commonSecurityNotifEventVarObjects
        OBJECT IDENTIFIER
        ::= { commonNotifEventVariableObjects 1 }

    commonAudLogStatus OBJECT-TYPE
        SYNTAX              INTEGER {
                                initialized( 1 ),
                                thresholdCrossed( 2 ),
                                full( 3 )
                            }
        MAX-ACCESS          accessible-for-notify
        STATUS              current
        DESCRIPTION         "(U//FOUO) Identification of the status of the
                            audit log."
        ::= { commonSecurityNotifEventVarObjects 1 }

    commonBatteryStatus OBJECT-TYPE
        SYNTAX              INTEGER {
                                ok( 1 ),
                                low( 2 )
                            }
        MAX-ACCESS          accessible-for-notify
        STATUS              current
        DESCRIPTION         "(U//FOUO) Identification of the status of the
                            battery."
        ::= { commonSecurityNotifEventVarObjects 2 }

    commonCIKNotifEventVarObjects OBJECT IDENTIFIER
        ::= { commonNotifEventVariableObjects 2 }

    commonFFNotifEventVarObjects OBJECT IDENTIFIER
        ::= { commonNotifEventVariableObjects 3 }

    commonFireFlyKeyType OBJECT-TYPE
        SYNTAX              INTEGER {
                                transition( 1 ),
                                enhanced( 2 ),
                                basic( 3 )
                            }
        MAX-ACCESS          accessible-for-notify
        STATUS              current
        DESCRIPTION         "(U//FOUO) Indicates the usage potential of the
                            key."
        ::= { commonFFNotifEventVarObjects 1 }

    commonFireFlyMaterialType OBJECT-TYPE
        SYNTAX              INTEGER {
                                seed( 1 ),
                                operational( 2 ),
                                oneTimeUse( 3 )
                            }
        MAX-ACCESS          accessible-for-notify
        STATUS              current
        DESCRIPTION         "(U//FOUO) The Material Type of this Firefly key."
        ::= { commonFFNotifEventVarObjects 2 }

    commonFireFlyPartitionCode OBJECT-TYPE
        SYNTAX              OCTET STRING (SIZE(6))
        MAX-ACCESS          accessible-for-notify
        STATUS              current
        DESCRIPTION         "(U//FOUO) The Partition Code of this Firefly key.
                            This value is used to segment the Universal into
                            separate networks."
        ::= { commonFFNotifEventVarObjects 3 }

    commonFireFlyVectorType OBJECT-TYPE
        SYNTAX              INTEGER {
                                current( 1 ),
                                currentNext( 2 )
                            }
        MAX-ACCESS          accessible-for-notify
        STATUS              current
        DESCRIPTION         "(U//FOUO) The type of the vector set."
        ::= { commonFFNotifEventVarObjects 4 }

    commonIKEv1DeletedReason OBJECT-TYPE
        SYNTAX              INTEGER {
                                keyMaterialDeleted( 1 ),
                                operatorDeletion( 2 ),
                                saReplacement( 3 ),
                                negotiationFailure( 4 ),
                                nonLegacyRecoverySa( 5 ),
                                duplicateSa( 6 ),
                                ruleDeletion( 7 ),
                                ikev1DeletePayload( 8 ),
                                ikev2InvalidSpi( 9 ),
                                orphanSa( 10 ),
                                natTConflict( 11 ),
                                transportModeFplConflict( 12 ),
                                ipAddrChanged( 13 ),
                                ikev2DeletePayload( 14 ),
                                secAttrsDeletion( 15 ),
                                transformSuiteMismatch( 16 ),
                                mtekMtekUpdateSuccess( 17 ),
                                mtekMtekUpdateFailure( 18 ),
                                endOfTekLife( 19 ),
                                ruleModification( 20 ),
                                secAttrsModification( 21 ),
                                initialContactReceived( 22 ),
                                invalidTransportMappings( 23 )
                            }
        MAX-ACCESS          accessible-for-notify
        STATUS              current
        DESCRIPTION         "(U//FOUO) The reason for deleteion of an IKEv1
                            SA."
        ::= { commonFFNotifEventVarObjects 5 }

    commonIKEv2DeletedReason OBJECT-TYPE
        SYNTAX              INTEGER {
                                childSaTekExpiration( 1 ),
                                childSaOperatorDeletion( 2 ),
                                childSaReplacement( 3 ),
                                childSaRuleDeletion( 4 ),
                                childSaDeletePayload( 5 ),
                                childSaInvalidSpi( 6 ),
                                childSaTransportModeFplConflict( 7 ),
                                childSaIpAddrTransformSuiteMismatch( 8 ),
                                childSaPseqnRollover( 9 ),
                                ikeSaDeletePayload( 10 ),
                                ikeSaTekExpiration( 11 ),
                                ikeSaOperatorDeletion( 12 ),
                                ikeSaReplacement( 13 ),
                                ikeSaRuleDeletion( 14 ),
                                ikeSaEkExpiration( 15 ),
                                ikeSaUnreacheableChildless( 16 ),
                                initialContactReceived( 17 ),
                                ipAddrChanged( 18 )
                            }
        MAX-ACCESS          accessible-for-notify
        STATUS              current
        DESCRIPTION         "(U//FOUO) The reason for deleteion of an IKEv2
                            SA."
        ::= { commonFFNotifEventVarObjects 6 }

    commonIKEv2ExchangeType OBJECT-TYPE
        SYNTAX              INTEGER {
                                ikeSAInitialization( 1 ),
                                ikeAuthorization( 2 ),
                                childSACreation( 3 ),
                                informational( 4 ),
                                ikeSessionResumption( 5 )
                            }
        MAX-ACCESS          accessible-for-notify
        STATUS              current
        DESCRIPTION         "(U//FOUO) The Exchange Type of an IKEv2 Negotiation."
        ::= { commonFFNotifEventVarObjects 7 }

    commonIKEv2NegotiaFailureReason OBJECT-TYPE
        SYNTAX              INTEGER {
                                ikeTimeout( 1 ),
                                negotiationAborted( 2 ),
                                localIPAddressNotSet( 3 ),
                                saSetupFailure( 4 ),
                                noProposalChosenIKESA( 5 ),
                                maximumNegotiationsInProgress( 6 ),
                                noProposalChosenChildSA( 7 ),
                                configurationError( 8 ),
                                invalidKEPayload( 9 ),
                                invalidPreauthentication( 10 ),
                                authenticationFailure( 11 ),
                                invalidSyntax( 12 ),
                                unacceptableTrafficSelector( 13 ),
                                additionalTrafficSelectorPossible( 14 ),
                                remoteErrorReceived( 15 ),
                                noAdditionalSa( 16 ),
                                negotiationAlreadyInProgress( 17 ),
                                natDetectionError( 18 ),
                                firstTrafficSelectorProhibited( 19 ),
                                transportMapErr( 20 )
                            }
        MAX-ACCESS          accessible-for-notify
        STATUS              current
        DESCRIPTION         "(U//FOUO) The reason for IKEv2 negotiation failure."
        ::= { commonFFNotifEventVarObjects 8 }

    commonInitiatorSAspi OBJECT-TYPE
        SYNTAX              Counter64
        MAX-ACCESS          accessible-for-notify
        STATUS              current
        DESCRIPTION         "(U//FOUO) The SPI value of the initiator."
        ::= { commonFFNotifEventVarObjects 9 }

    commonKMID OBJECT-TYPE
        SYNTAX              OCTET STRING (SIZE(6))
        MAX-ACCESS          accessible-for-notify
        STATUS              current
        DESCRIPTION         "(U//FOUO) The Firefly Key Material ID for this
                            Firefly key.
                            
                            (U//FOUO) Current convention is that the left
                            more 16 bits will be 0 value only. However, implementations
                            should be prepared to use full 48-bit values
                            for use in the future. It is possible that future
                            values and/or values assigned by other organizations
                            may be larger than 32 bits so storing these values
                            as a 32-bit integer and prepending zeros is not
                            a recommended implementation."
        ::= { commonFFNotifEventVarObjects 10 }

    commonResponderSAspi OBJECT-TYPE
        SYNTAX              Counter64
        MAX-ACCESS          accessible-for-notify
        STATUS              current
        DESCRIPTION         "(U//FOUO) The SPI value of the responder."
        ::= { commonFFNotifEventVarObjects 11 }

    commonUniversalEdition OBJECT-TYPE
        SYNTAX              OCTET STRING (SIZE(2))
        MAX-ACCESS          accessible-for-notify
        STATUS              current
        DESCRIPTION         "(U//FOUO) The universal edition of this Firefly
                            key. This is an ASCII encoded number from 01-99."
        ::= { commonFFNotifEventVarObjects 12 }

    commonUniversalID OBJECT-TYPE
        SYNTAX              OCTET STRING (SIZE(4))
        MAX-ACCESS          accessible-for-notify
        STATUS              current
        DESCRIPTION         "(U//FOUO) The universal ID uniquely identifying
                            a FF universal. This is an ASCII encoded number
                            from 0000-9999."
        ::= { commonFFNotifEventVarObjects 13 }

    commonPPKNotifEventVarObjects OBJECT IDENTIFIER
        ::= { commonNotifEventVariableObjects 4 }

    commonChainName OBJECT-TYPE
        SYNTAX              SnmpAdminString (SIZE(1..32))
        MAX-ACCESS          accessible-for-notify
        STATUS              current
        DESCRIPTION         "(U//FOUO) The administrative name defining a unique
                            symmetric key chain."
        ::= { commonPPKNotifEventVarObjects 1 }

    commonChainOrder OBJECT-TYPE
        SYNTAX              Unsigned32
        MAX-ACCESS          accessible-for-notify
        STATUS              current
        DESCRIPTION         "(U//FOUO) A unique numeric index used to indicate
                            the ordering of the keys within a chain."
        ::= { commonPPKNotifEventVarObjects 2 }

    commonDGSKDeleteReason OBJECT-TYPE
        SYNTAX              INTEGER {
                                noReason( 0 ),
                                userRequest( 1 ),
                                cryptoPeriodExpired( 2 )
                            }
        MAX-ACCESS          accessible-for-notify
        STATUS              current
        DESCRIPTION         "(U//FOUO) Reason the identified DGSK was deleted."
        ::= { commonPPKNotifEventVarObjects 3 }

    commonDGSKFailedFillReason OBJECT-TYPE
        SYNTAX              INTEGER {
                                invalidDgskKey( 1 ),
                                dgskAlreadyLoaded( 2 )
                            }
        MAX-ACCESS          accessible-for-notify
        STATUS              current
        DESCRIPTION         "(U//FOUO) Reason the DGSK fill failed."
        ::= { commonPPKNotifEventVarObjects 4 }

    commonDGSKIndex OBJECT-TYPE
        SYNTAX              Unsigned32
        MAX-ACCESS          accessible-for-notify
        STATUS              current
        DESCRIPTION         "(U//FOUO) A unique numeric index that identifies
                            this device-generated raw string."
        ::= { commonPPKNotifEventVarObjects 5 }

    commonEdition OBJECT-TYPE
        SYNTAX              OCTET STRING (SIZE(5))
        MAX-ACCESS          accessible-for-notify
        STATUS              current
        DESCRIPTION         "(U//FOUO) The short title for a pre-placed key
                            (PPK). It is sent as 6 characters, six-bit encoded,
                            in 5 bytes. It is 36 bits wide, and the right
                            most 4 bits in this field SHOULD be set to 0
                            and MUST be ignored by implementations expecting
                            only exactly 36 bits."
        ::= { commonPPKNotifEventVarObjects 6 }

    commonEffectiveDate OBJECT-TYPE
        SYNTAX              DateAndTime
        MAX-ACCESS          accessible-for-notify
        STATUS              current
        DESCRIPTION         "(U//FOUO) The local date and time when this key
                            was or will be active."
        ::= { commonPPKNotifEventVarObjects 7 }

    commonEKType OBJECT-TYPE
        SYNTAX              INTEGER {
                                global( 1 ),
                                local( 2 ),
                                privacy( 3 ),
                                separation( 4 )
                            }
        MAX-ACCESS          accessible-for-notify
        STATUS              current
        DESCRIPTION         "(U//FOUO) Indicates the key type of this exclusion
                            key. The possible values are: local, global,
                            separation, and privacy."
        ::= { commonPPKNotifEventVarObjects 8 }

    commonKeyMode OBJECT-TYPE
        SYNTAX              INTEGER {
                                unassigned( 0 ),
                                haipe( 1 ),
                                ipmeir( 2 )
                            }
        MAX-ACCESS          accessible-for-notify
        STATUS              current
        DESCRIPTION         "(U//FOUO) The key mode for this key."
        ::= { commonPPKNotifEventVarObjects 9 }

    commonSegment OBJECT-TYPE
        SYNTAX              Unsigned32 (0..255)
        MAX-ACCESS          accessible-for-notify
        STATUS              current
        DESCRIPTION         "(U//FOUO) The segment number for a pre-placed
                            key (PPK)."
        ::= { commonPPKNotifEventVarObjects 10 }

    commonShortTitle OBJECT-TYPE
        SYNTAX              OCTET STRING (SIZE(18))
        MAX-ACCESS          accessible-for-notify
        STATUS              current
        DESCRIPTION         "(U//FOUO) The short title for a pre-placed key
                            (PPK). It is sent as 24 characters, six-bit encoded,
                            in 18 bytes."
        ::= { commonPPKNotifEventVarObjects 11 }

    commonUsageType OBJECT-TYPE
        SYNTAX              BITS {
                                manual-sa( 0 ),
                                ek( 1 ),
                                shared-secret( 2 )
                            }
        MAX-ACCESS          accessible-for-notify
        STATUS              current
        DESCRIPTION         "(U//FOUO) Indicates how this pre-placed key (PPK)
                            is used.
                            
                            (U//FOUO) The bits value translations: 1000 0000
                            = Manual SA 0100 0000 = EK 0010 0000 = Shared
                            Secret 000x xxxx = RESERVED
                            
                            (U//FOUO) The bit positions are represented in
                            big-endian format, where the high/left most bit
                            is the most significant bit. There are two ways
                            that a device can represent the unassigned value:
                            set the bit position 0, or have no bits set."
        ::= { commonPPKNotifEventVarObjects 12 }

    commonSANotifEventVarObjects OBJECT IDENTIFIER
        ::= { commonNotifEventVariableObjects 5 }

    commonDFBitSetting OBJECT-TYPE
        SYNTAX              INTEGER {
                                set( 1 ),
                                clear( 2 ),
                                copy( 3 )
                            }
        MAX-ACCESS          accessible-for-notify
        STATUS              current
        DESCRIPTION         "(U//FOUO) The setting that controls the processing
                            mode of the Don't Fragment (DF) bit in the IPv4
                            CT header (encapsulation)."
        ::= { commonSANotifEventVarObjects 1 }

    commonDSCPSetting OBJECT-TYPE
        SYNTAX              INTEGER {
                                set( 1 ),
                                acceptList( 2 )
                            }
        MAX-ACCESS          accessible-for-notify
        STATUS              current
        DESCRIPTION         "(U//FOUO) The setting that controls the processing
                            mode of the Differentiated Service Code Points
                            (DSCP) bits. The possible values are: set, acceptList.
                            For IPv4 headers, the DSCP bits are the six most
                            significant bits of the Type of Service (TOS)
                            field. For IPv6 headers, the DSCP bits are the
                            six most significant bits of the Traffic Class
                            (TC) field."
        ::= { commonSANotifEventVarObjects 2 }

    commonDSCPValue OBJECT-TYPE
        SYNTAX              OCTET STRING (SIZE(1 | 8))
        MAX-ACCESS          accessible-for-notify
        STATUS              current
        DESCRIPTION         "(U//FOUO) Depending on the value set in the commonDSCPSetting
                            column (set, acceptList), this column is used
                            in two ways. For IPv4 headers, the DSCP bits
                            are the six most significant bits of the Type
                            of Service (TOS) field. For IPv6 headers, the
                            DSCP bits are the six most significant bits of
                            the Traffic Class (TC) field.
                            
                            (U//FOUO) [commonDSCPSetting=set] this value
                            must be one octet in length in the range 0x00
                            to 0x3f.
                            
                            (U//FOUO) [commonDSCPSetting=acceptList] this
                            value must be 8 octets in length and the value
                            in this column will provide a list of acceptable
                            DSCP values represented as a 64-bit vector. Each
                            bit of this value represents one acceptable DSCP
                            value and acceptable matches are indicated with
                            its mapped bit is set to 1 (binary).
                            
                            (U//FOUO) 64 bit vector representation: DSCP
                            value matches 64-bit Vector Map 0 000...000001
                            1 000...000010 2 000...000100 . . . . . . . .
                            . 62 010000...000 63 100000...000"
        ::= { commonSANotifEventVarObjects 3 }

    commonECNSetting OBJECT-TYPE
        SYNTAX              INTEGER {
                                disabled( 1 ),
                                congestionNotification( 2 ),
                                admissionControl( 3 )
                            }
        MAX-ACCESS          accessible-for-notify
        STATUS              current
        DESCRIPTION         "(U//FOUO) The setting that controls the processing
                            mode of the Explicit Congestion Notification
                            (ECN) bits, during encapsulation and decapsulation."
        ::= { commonSANotifEventVarObjects 4 }

    commonSAChildIndex OBJECT-TYPE
        SYNTAX              Unsigned32
        MAX-ACCESS          accessible-for-notify
        STATUS              current
        DESCRIPTION         "(U//FOUO) A common child index to pair incomming
                            and outgoing SAs (which have different indexes)
                            together."
        ::= { commonSANotifEventVarObjects 5 }

    commonSPIChainReference OBJECT-TYPE
        SYNTAX              SnmpAdminString (SIZE(1..32))
        MAX-ACCESS          accessible-for-notify
        STATUS              current
        DESCRIPTION         "(U//FOUO) A reference string that points to a
                            SPI chain group. This referenced SPI chain group
                            provides a group of SPIs that are cycled through
                            upon SPI changeover."
        ::= { commonSANotifEventVarObjects 6 }

    commonTransformSuite OBJECT-TYPE
        SYNTAX              INTEGER {
                                suiteAMedleyGCM128TunnelMode( 1 ),
                                suiteAMedleyGCM96TunnelMode( 2 ),
                                suiteAMedleyGCM128TransportMode( 3 ),
                                suiteAMedleyGCM96TransportMode( 4 ),
                                suiteBAESGCM128TunnelMode( 8 ),
                                suiteBAESGCM96TunnelMode( 9 ),
                                suiteBAESGCM128TransportMode( 10 ),
                                suiteBAESGCM96TransportMode( 11 ),
                                legacyMedley( 15 ),
                                legacyBaton( 16 )
                            }
        MAX-ACCESS          accessible-for-notify
        STATUS              current
        DESCRIPTION         "(U//FOUO) The list of transform suites. The following
                            description fully defines the specific details
                            of each transform suite:
                            
                            (U//FOUO)(1) suiteAMedleyGCM128TunnelMode: Medley
                            with GCM128 (Data Integrity Algorithm). Additionally,
                            the Crypto Block Size is 4 bytes, the Key Update
                            mechanism is Accordion 3.0 and the ESP Mechanism
                            is ESPv3 in Tunnel Mode.
                            
                            (U//FOUO)(2) suiteAMedleyGCM96TunnelMode: Medley
                            with GCM96 (Data Integrity Algorithm). Additionally,
                            the Crypto Block Size is 4 bytes, the Key Update
                            mechanism is Accordion 3.0 and the ESP Mechanism
                            is ESPv3 in Tunnel Mode.
                            
                            (U//FOUO)(3) suiteAMedleyGCM128TransportMode:
                            Medley with GCM128 (Data Integrity Algorithm).
                            Additionally, the Crypto Block Size is 4 bytes,
                            the Key Update mechanism is Accordion 3.0 and
                            the ESP Mechanism is ESPv3 in Transport Mode.
                            
                            (U//FOUO)(4) suiteAMedleyGCM96TransportMode:
                            Medley with GCM96 (Data Integrity Algorithm).
                            Additionally, the Crypto Block Size is 4 bytes,
                            the Key Update mechanism is Accordion 3.0 and
                            the ESP Mechanism is ESPv3 in Transport Mode.
                            
                            (U//FOUO)(8) suiteBAESGCM128TunnelMode: AES with
                            GCM128 (Data Integrity Algorithm). Additionally,
                            the Crypto Block Size is 4 bytes, the Key Update
                            mechanism is AES Key Wrap and the ESP Mechanism
                            is ESPv3 in Tunnel Mode.
                            
                            (U//FOUO)(9) suiteBAESGCM96TunnelMode: AES with
                            GCM96 (Data Integrity Algorithm). Additionally,
                            the Crypto Block Size is 4 bytes, the Key Update
                            mechanism is AES Key Wrap and the ESP Mechanism
                            is ESPv3 in Tunnel Mode.
                            
                            (U//FOUO)(10) suiteBAESGCM128TransportMode: AES
                            with GCM128 (Data Integrity Algorithm). Additionally,
                            the Crypto Block Size is 4 bytes, the Key Update
                            mechanism is AES Key Wrap and the ESP Mechanism
                            is ESPv3 in Transport Mode.
                            
                            (U//FOUO)(11) suiteBAESGCM96TransportMode: AES
                            with GCM96 (Data Integrity Algorithm). Additionally,
                            the Crypto Block Size is 4 bytes, the Key Update
                            mechanism is AES Key Wrap and the ESP Mechanism
                            is ESPv3 in Transport Mode.
                            
                            (U//FOUO)(15) legacyMedley: Medley with BIP32
                            (Data Integrity Algorithm). Additionally, the
                            Crypto Block Size is 8 bytes, the Key Update
                            mechanism is Accordion 3.0 and the ESP Mechanism
                            is ESP in Tunnel Mode.
                            
                            (U//FOUO)(16) legacyBaton: Baton with BIP32 (Data
                            Integrity Algorithm). Additionally, the Crypto
                            Block Size is 48 bytes, the Key Update mechanism
                            is Accordion 1.3 and the ESP Mechanism is ESP
                            in Tunnel Mode."
        ::= { commonSANotifEventVarObjects 7 }

    commonBankNum OBJECT-TYPE
        SYNTAX              Unsigned32
        MAX-ACCESS          accessible-for-notify
        STATUS              current
        DESCRIPTION         "(U//FOUO) Value used to designate the bank number
                            an SA uses for a given TEK."
        ::= { commonSANotifEventVarObjects 8 }

    commonSNMPNotifEventVarObjects OBJECT IDENTIFIER
        ::= { commonNotifEventVariableObjects 6 }

    commonIPNotifEventVarObjects OBJECT IDENTIFIER
        ::= { commonNotifEventVariableObjects 7 }

    commonIFNotifEventVarObjects OBJECT IDENTIFIER
        ::= { commonNotifEventVariableObjects 8 }

    commonIfAdminStatus OBJECT-TYPE
        SYNTAX              INTEGER {
                                up( 1 ),
                                down( 2 ),
                                testing( 3 )
                            }
        MAX-ACCESS          accessible-for-notify
        STATUS              current
        DESCRIPTION         "(U//FOUO) The desired state of the interface.
                            The testing(3) state indicates that no operational
                            packets can be passed. When a managed system
                            initializes, all interfaces start with commonIfAdminStatus
                            in the down(2) state. As a result of either explicit
                            management action or per configuration information
                            retained by the managed system, commonIfAdminStatus
                            is then changed to either the up(1) or testing(3)
                            states (or remains in the down(2) state)."
        ::= { commonIFNotifEventVarObjects 1 }

    commonIfOperStatus OBJECT-TYPE
        SYNTAX              INTEGER {
                                up( 1 ),
                                down( 2 ),
                                testing( 3 ),
                                unknown( 4 ),
                                dormant( 5 ),
                                notPresent( 6 ),
                                lowerLayerDown( 7 )
                            }
        MAX-ACCESS          accessible-for-notify
        STATUS              current
        DESCRIPTION         "(U//FOUO) The current operational state of the
                            interface. The testing(3) state indicates that
                            no operational packets can be passed. If commonIfAdminStatus
                            is down(2) then commonIfOperStatus should be
                            down(2). If commonIfAdminStatus is changed to
                            up(1) then ifOperStatus should change to up(1)
                            if the interface is ready to transmit and receive
                            network traffic; it should change to dormant(5)
                            if the interface is waiting for external actions
                            (such as a serial line waiting for an incoming
                            connection); it should remain in the down(2)
                            state if and only if there is a fault that prevents
                            it from going to the up(1) state; it should remain
                            in the notPresent(6) state if the interface has
                            missing (typically, hardware) components."
        ::= { commonIFNotifEventVarObjects 2 }

    commonIfSpeedModeCT OBJECT-TYPE
        SYNTAX              CommonIfSpeedMode
        MAX-ACCESS          accessible-for-notify
        STATUS              current
        DESCRIPTION         "(U//FOUO) This identifies the speed mofe for the
                            CT interface."
        ::= { commonIFNotifEventVarObjects 3 }

    commonIfSpeedModePT OBJECT-TYPE
        SYNTAX              CommonIfSpeedMode
        MAX-ACCESS          accessible-for-notify
        STATUS              current
        DESCRIPTION         "(U//FOUO) This identifies the speed mode for the
                            PT interface."
        ::= { commonIFNotifEventVarObjects 4 }

    commonLinkStatus OBJECT-TYPE
        SYNTAX              INTEGER {
                                linkUp( 1 ),
                                linkDown( 2 )
                            }
        MAX-ACCESS          accessible-for-notify
        STATUS              current
        DESCRIPTION         "(U//FOUO) This identifies the link status."
        ::= { commonIFNotifEventVarObjects 5 }

    commonDhcpState OBJECT-TYPE
        SYNTAX              INTEGER {
                                bound( 0 ),
                                renewingOrRebinding( 1 ),
                                enabled( 2 ),
                                disabled( 3 ),
                                bindFailed( 4 ), 
                                deconfigured( 5 ), 
                                nakProcessed( 6 )
                            }
        MAX-ACCESS          accessible-for-notify
        STATUS              current
        DESCRIPTION         "(U//FOUO) This identifies the DHCP state."
        ::= { commonIFNotifEventVarObjects 6 }
		
    commonPACNotifEventVarObjects OBJECT IDENTIFIER
        ::= { commonNotifEventVariableObjects 9 }

    commonPACAction OBJECT-TYPE
        SYNTAX              INTEGER {
                                fill( 1 ),
                                install( 2 ),
                                delete( 3 )
                            }
        MAX-ACCESS          accessible-for-notify
        STATUS              current
        DESCRIPTION         "(U//FOUO) This object identifies the PAC action
                            performed."
        ::= { commonPACNotifEventVarObjects 1 }

    commonPACFailedReason OBJECT-TYPE
        SYNTAX              OCTET STRING (SIZE(1..128))
        MAX-ACCESS          accessible-for-notify
        STATUS              current
        DESCRIPTION         "(U//FOUO) The reason for a PAC operation failure."
        ::= { commonPACNotifEventVarObjects 2 }

    commonPACReason OBJECT-TYPE
        SYNTAX              OCTET STRING (SIZE(1..128))
        MAX-ACCESS          accessible-for-notify
        STATUS              current
        DESCRIPTION         "(U//FOUO) The reason for a PAC operation."
        ::= { commonPACNotifEventVarObjects 3 }

    commonKTNotifEventVarObjects OBJECT IDENTIFIER
        ::= { commonNotifEventVariableObjects 10 }

    commonKeyFile OBJECT-TYPE
        SYNTAX              SnmpAdminString (SIZE(1..32))
        MAX-ACCESS          accessible-for-notify
        STATUS              current
        DESCRIPTION         "(U//FOUO) The name of the key file."
        ::= { commonKTNotifEventVarObjects 1 }

    commonKeyIndex OBJECT-TYPE
        SYNTAX              Unsigned32
        MAX-ACCESS          accessible-for-notify
        STATUS              current
        DESCRIPTION         "(U//FOUO) The position of a key."
        ::= { commonKTNotifEventVarObjects 2 }

    commonKeyUse OBJECT-TYPE
        SYNTAX              INTEGER {
                                tek( 6 ),
                                eff( 9 )
                            }
        MAX-ACCESS          accessible-for-notify
        STATUS              current
        DESCRIPTION         "(U//FOUO) This object indicates the type of key.
                            This is from the use field of the DS-100-1 tag
                            for this key.
                            
                            (U//FOUO) [tek] = Traffic Encryption Key
                            
                            (U//FOUO) [eff] = Enhanced FIREFLY Key"
        ::= { commonKTNotifEventVarObjects 3 }

    commonKTIBLocalReason OBJECT-TYPE
        SYNTAX              OCTET STRING (SIZE(1..128))
        MAX-ACCESS          accessible-for-notify
        STATUS              current
        DESCRIPTION         "(U//FOUO) This object identifies the reason for
                            an in-band local fill or why it failed."
        ::= { commonKTNotifEventVarObjects 4 }

    commonOOBIssueReason OBJECT-TYPE
        SYNTAX              OCTET STRING (SIZE(1..128))
        MAX-ACCESS          accessible-for-notify
        STATUS              current
        DESCRIPTION         "(U//FOUO) This object identifies the reason for
                            an out-of-band key issue or why it failed."
        ::= { commonKTNotifEventVarObjects 5 }

    commonOOBRcvdReason OBJECT-TYPE
        SYNTAX              OCTET STRING (SIZE(1..128))
        MAX-ACCESS          accessible-for-notify
        STATUS              current
        DESCRIPTION         "(U//FOUO) This object identifies the reason for
                            an out-of-band key receipt or why it failed."
        ::= { commonKTNotifEventVarObjects 6 }

    commonRegister OBJECT-TYPE
        SYNTAX              OCTET STRING (SIZE(5))
        MAX-ACCESS          accessible-for-notify
        STATUS              current
        DESCRIPTION         "(U//FOUO) The DS-100-1 Register Number of this
                            key. This number conforms to network-byte order
                            and the 4 most significant bits should be set
                            to zero."
        ::= { commonKTNotifEventVarObjects 7 }

    commonQKeyNotifEventVarObjects OBJECT IDENTIFIER
        ::= { commonNotifEventVariableObjects 11 }

    commonQkeyAction OBJECT-TYPE
        SYNTAX              INTEGER {
                                fill( 1 ),
                                install( 2 ),
                                delete( 3 )
                            }
        MAX-ACCESS          accessible-for-notify
        STATUS              current
        DESCRIPTION         "(U//FOUO) This object identifies the Q-Key action
                            performed."
        ::= { commonQKeyNotifEventVarObjects 1 }

    commonQkeyFailedReason OBJECT-TYPE
        SYNTAX              OCTET STRING (SIZE(1..128))
        MAX-ACCESS          accessible-for-notify
        STATUS              current
        DESCRIPTION         "(U//FOUO) The reason for a Q-key operation failure."
        ::= { commonQKeyNotifEventVarObjects 2 }

    commonQkeyReason OBJECT-TYPE
        SYNTAX              OCTET STRING (SIZE(1..128))
        MAX-ACCESS          accessible-for-notify
        STATUS              current
        DESCRIPTION         "(U//FOUO) The reason for a Q-key operation."
        ::= { commonQKeyNotifEventVarObjects 3 }

    commonSWDLNotifEventVarObjects OBJECT IDENTIFIER
        ::= { commonNotifEventVariableObjects 12 }

    commonFdErrCode OBJECT-TYPE
        SYNTAX              Integer32
        MAX-ACCESS          accessible-for-notify
        STATUS              current
        DESCRIPTION         "(U//FOUO) The Error code that triggered the notification.
                            This code is protocol-specific depending on the
                            type of transfer being performed based on the
                            commonFdsURI column."
        ::= { commonSWDLNotifEventVarObjects 1 }

    commonFdErrDetail OBJECT-TYPE
        SYNTAX              OCTET STRING (SIZE(0..4096))
        MAX-ACCESS          accessible-for-notify
        STATUS              current
        DESCRIPTION         "(U//FOUO) The string, which is likely to be commonFdsURI
                            protocol-specific or action-specific, indicating
                            the result of the download operation. The value
                            contained within this object must not be expected
                            to be machine parsable. If no supplemental information
                            is needed to be transmitted, this object should
                            consist of a zero-length string."
        ::= { commonSWDLNotifEventVarObjects 2 }

    commonFdsURI OBJECT-TYPE
        SYNTAX              SnmpAdminString
        MAX-ACCESS          accessible-for-notify
        STATUS              current
        DESCRIPTION         "(U//FOUO) The URI to indicate a download server,
                            path, etc... from which to pull a firmware image
                            from. URIs containing username and/or password
                            will be rejected.
                            
                            (U//FOUO) It is important to note that devices
                            may or may not support DNS name resolution and
                            thus some devices may only support URIs containing
                            IP addresses."
        ::= { commonSWDLNotifEventVarObjects 3 }

    commonFirmwareAction OBJECT-TYPE
        SYNTAX              INTEGER {
                                download( 1 ),
                                install( 2 )
                            }
        MAX-ACCESS          accessible-for-notify
        STATUS              current
        DESCRIPTION         "(U//FOUO) Identification of the action relating
                            to the Firmware Download."
        ::= { commonSWDLNotifEventVarObjects 4 }

    commonSysLevelNotifEventVarObjects
        OBJECT IDENTIFIER
        ::= { commonNotifEventVariableObjects 13 }

    commonAction OBJECT-TYPE
        SYNTAX              INTEGER {
                                noAction( 0 ),
                                create( 1 ),
                                add( 2 ),
                                modify( 3 ),
                                delete( 4 ),
                                copy( 5 ),
                                activate( 6 ),
                                destroy( 7 )
                            }
        MAX-ACCESS          accessible-for-notify
        STATUS              current
        DESCRIPTION         "(U//FOUO) Identification of the action performed."
        ::= { commonSysLevelNotifEventVarObjects 1 }

    commonAddress OBJECT-TYPE
        SYNTAX              InetAddress
        MAX-ACCESS          accessible-for-notify
        STATUS              current
        DESCRIPTION         "(U//FOUO) The IP address."
        ::= { commonSysLevelNotifEventVarObjects 2 }

    commonClassification OBJECT-TYPE
        SYNTAX              BITS {
                                unclassified( 0 ),
                                restricted( 1 ),
                                confidential( 2 ),
                                secret( 3 ),
                                top-secret( 4 ),
                                nato-restricted( 5 ),
                                nato-confidential( 6 ),
                                nato-secret( 7 ),
                                cosmic-top-secret( 8 )
                            }
        MAX-ACCESS          accessible-for-notify
        STATUS              current
        DESCRIPTION         "(U//PR) The classification level of this pre-placed
                            key (PPK).
                            
                            (U//PR) This column is taken directly from the
                            DS-100-1 tag without modification.
                            
                            (U//PR) Bits value translation: 1000 0000 0000
                            0000 = UNCLASSIFIED 0100 0000 0000 0000 = RESTRICTED
                            0010 0000 0000 0000 = CONFIDENTIAL 0001 0000
                            0000 0000 = SECRET 0000 1000 0000 0000 = TOP
                            SECRET 0000 0100 0000 0000 = NATO RESTRICTED
                            0000 0010 0000 0000 = NATO CONFIDENTIAL 0000
                            0001 0000 0000 = NATO SECRET 0000 0000 1000 0000
                            = COSMIC TOP SECRET
                            
                            (U//PR) All other bits values are reserved."
        ::= { commonSysLevelNotifEventVarObjects 3 }

    commonCryptoSuite OBJECT-TYPE
        SYNTAX              INTEGER {
                                noSuite( 0 ),
                                suiteA( 1 ),
                                suiteB( 2 )
                            }
        MAX-ACCESS          accessible-for-notify
        STATUS              current
        DESCRIPTION         "(U//FOUO) Indicates the crypto suite of this key."
        ::= { commonSysLevelNotifEventVarObjects 4 }

    commonExpirationDate OBJECT-TYPE
        SYNTAX              DateAndTime
        MAX-ACCESS          accessible-for-notify
        STATUS              current
        DESCRIPTION         "(U//FOUO) The date and time of expiration."
        ::= { commonSysLevelNotifEventVarObjects 5 }

    commonIfIndex OBJECT-TYPE
        SYNTAX              Unsigned32
        MAX-ACCESS          accessible-for-notify
        STATUS              current
        DESCRIPTION         "(U//FOUO) A unique numeric index that identifies
                            the interface."
        ::= { commonSysLevelNotifEventVarObjects 6 }

    commonLocalCTAddress OBJECT-TYPE
        SYNTAX              InetAddress
        MAX-ACCESS          accessible-for-notify
        STATUS              current
        DESCRIPTION         "(U//FOUO) The local CT IP address."
        ::= { commonSysLevelNotifEventVarObjects 7 }

    commonLocalHostAddress OBJECT-TYPE
        SYNTAX              InetAddress
        MAX-ACCESS          accessible-for-notify
        STATUS              current
        DESCRIPTION         "(U//FOUO) The local Host IP address."
        ::= { commonSysLevelNotifEventVarObjects 8 }

    commonLocalPTAddress OBJECT-TYPE
        SYNTAX              InetAddress
        MAX-ACCESS          accessible-for-notify
        STATUS              current
        DESCRIPTION         "(U//FOUO) The local PT IP address."
        ::= { commonSysLevelNotifEventVarObjects 9 }

    commonPort OBJECT-TYPE
        SYNTAX              Unsigned32
        MAX-ACCESS          accessible-for-notify
        STATUS              current
        DESCRIPTION         "(U//FOUO) The address port."
        ::= { commonSysLevelNotifEventVarObjects 10 }

    commonRemoteHostAddress OBJECT-TYPE
        SYNTAX              InetAddress
        MAX-ACCESS          accessible-for-notify
        STATUS              current
        DESCRIPTION         "(U//FOUO) The remote Host IP address."
        ::= { commonSysLevelNotifEventVarObjects 11 }

    commonRemotePTAddress OBJECT-TYPE
        SYNTAX              InetAddress
        MAX-ACCESS          accessible-for-notify
        STATUS              current
        DESCRIPTION         "(U//FOUO) The remote PT IP address."
        ::= { commonSysLevelNotifEventVarObjects 12 }

    commonStationID OBJECT-TYPE
        SYNTAX              OCTET STRING (SIZE(14))
        MAX-ACCESS          accessible-for-notify
        STATUS              current
        DESCRIPTION         "(U//FOUO) The ASCII-encoded station identifier
                            of this device.
                            
                            (U//FOUO) Note that the commonStationID is not
                            required to match the chassis serial number."
        ::= { commonSysLevelNotifEventVarObjects 13 }

    commonStatus OBJECT-TYPE
        SYNTAX              INTEGER {
                                success( 1 ),
                                fail( 2 )
                            }
        MAX-ACCESS          accessible-for-notify
        STATUS              current
        DESCRIPTION         "(U//FOUO) Identification of the status of an event."
        ::= { commonSysLevelNotifEventVarObjects 14 }

    commonSystemDate OBJECT-TYPE
        SYNTAX              DateAndTime
        MAX-ACCESS          accessible-for-notify
        STATUS              current
        DESCRIPTION         "(U//FOUO) The notion of the local date and time
                            of day."
        ::= { commonSysLevelNotifEventVarObjects 15 }

    commonName OBJECT-TYPE
        SYNTAX              SnmpAdminString (SIZE(1..32))
        MAX-ACCESS          accessible-for-notify
        STATUS              current
        DESCRIPTION         "(U//FOUO) The name of an object."
        ::= { commonSysLevelNotifEventVarObjects 16 }

    commonErrDetail OBJECT-TYPE
        SYNTAX              OCTET STRING (SIZE(0..255))
        MAX-ACCESS          accessible-for-notify
        STATUS              current
        DESCRIPTION         "(U//FOUO) The string detailing an error condition."
        ::= { commonSysLevelNotifEventVarObjects 17 }

    commonURI OBJECT-TYPE
        SYNTAX              SnmpAdminString (SIZE(1..255))
        MAX-ACCESS          accessible-for-notify
        STATUS              current
        DESCRIPTION         "(U//FOUO) The URI for an object."
        ::= { commonSysLevelNotifEventVarObjects 18 }

    commonConformance OBJECT IDENTIFIER
        ::= { gdc4sEncryptionProductsCommonMIB 3 }

    commonNotifGroup OBJECT IDENTIFIER ::= { commonConformance 6 }

    --Deleted from commonSecurityNotifs Notification-Group per MIB00116: commonSanitize.
    --DRN00134 20081003 Added commonKeyFilled to commonSecurityNotifs Notification-Group.
    commonSecurityNotifs NOTIFICATION-GROUP
        NOTIFICATIONS       {
                                commonTamper,
                                commonZeroize,
                                commonSsoPinActivity,
                                commonRealTimeClockSet,
                                commonHWSecurCriticalFault,
                                commonSWSecurCriticalFault,
                                commonPrivilegItemModToggle,
                                commonPrivilegItemValue,
                                commonEspBipError,
                                commonKEKUpdated,
                                commonConfigurationReset,
                                commonDiagnosticFailed,
                                commonConfigConflict,
                                commonHWSecurCriticalFault2,
                                commonSWSecurCriticalFault2,
                                commonKeyFilled,
                                commonUnIdentifiedKeyFillError,
                                commonKEKCreated
                            }
        STATUS		    current
        DESCRIPTION         "(U//FOUO) Security Audit Log Events related to
                            security administration of the device."
        ::= { commonNotifGroup 1 }

    commonCIKEventNotifs NOTIFICATION-GROUP
        NOTIFICATIONS       {
                                commonCikActive,
                                commonCIKCreated,
                                commonCIKDeleted,
                                commonCikFailed,
                                commonFTRKSDCreated
                            }
        STATUS		    current
        DESCRIPTION         "(U//FOUO) Security Audit Log events relating to
                            CIK administration."
        ::= { commonNotifGroup 2 }

    commonFFVSEventNotifs NOTIFICATION-GROUP
        NOTIFICATIONS       {
                                commonFFVSFillOK,
                                commonFFVSFillFailed,
                                commonFFVSDeleted,
                                commonFFVSExpired,
                                commonFFNegotiationFailure,
                                commonACLUpdated,
                                commonLocalCKLUpdated,
                                commonFFSPDTemplateActivated,
                                commonFFSPDTemplateDestroyed,
                                commonFFTEKCreated,
                                commonFFTEKDeleted,
                                commonFFVSFillOK2,
                                commonFFNegotiationFailure2,
								commonACLUpdated3
                            }
        STATUS		    current
        DESCRIPTION         "(U//FOUO) The notifications associated with a
                            FFVS administration."
        ::= { commonNotifGroup 3 }

    commonPPKEventNotifs NOTIFICATION-GROUP
        NOTIFICATIONS       {
                                commonPPKFillOK,
                                commonPPKFillFail,
                                commonPPKDeleted,
                                commonExpiredPPK,
                                commonPPKUseConfig,
                                commonPPKSACreationBlocked,
                                commonPPKSADInEntryActivated,
                                commonPPKSADInEntryDestroyed,
                                commonPPKSADOutEntryActivated,
                                commonPPKSADOutEntryDestroyed,
                                commonPPKTrafficUseConfig,
                                commonPPKEKUseConfig
                            }
        STATUS		    current
        DESCRIPTION         "(U//FOUO) The Security Audit Log events associated
                            with PPK use and administration."
        ::= { commonNotifGroup 4 }

    commonSNMPEventNotifs NOTIFICATION-GROUP
        NOTIFICATIONS       {
                                commonSNMPUserConfig,
                                commonSNMPAuthError,
                                commonSNMPUserUpdate
                            }
        STATUS		    current
        DESCRIPTION         "(U//FOUO) The Security Audit Log Events associated
                            with SNMP management of the device."
        ::= { commonNotifGroup 5 }

    commonIPEventNotifs NOTIFICATION-GROUP
        NOTIFICATIONS       {
                                commonPSEQNError,
                                commonRateLimitOverflow,
                                commonIPv6FavoredAddrChanged,
                                commonIPv4AddrChanged,
                                commonAutoAddressConfigFail,
                                commonPSEQNError2
                            }
        STATUS		    current
        DESCRIPTION         "(U//FOUO) The Security Audit Log Events associated
                            with IP."
        ::= { commonNotifGroup 6 }

    commonIFEventGroup NOTIFICATION-GROUP
        NOTIFICATIONS       {
                                commonIFSpeedModeMismatch,
                                commonIFSpeedNegotiationFailure
                            }
        STATUS		    current
        DESCRIPTION         "(U//FOUO) Notifications reporting interface events
                            to be placed in the log."
        ::= { commonNotifGroup 7 }

    environmentalFaults NOTIFICATION-GROUP
        NOTIFICATIONS       {
                                commonOvertemperatureFault,
                                commonFanFault
                            }
        STATUS		    current
        DESCRIPTION         "(U//FOUO) Notifications reporting environmental
                            faults."
        ::= { commonNotifGroup 8 }

    commonPACEventNotifs NOTIFICATION-GROUP
        NOTIFICATIONS       {
                                commonPACFilledOK,
                                commonPACFillFailed,
                                commonPACDeleted,
                                commonPACInstalled,
                                commonPACDeleteFail
                            }
        STATUS		    current
        DESCRIPTION         "(U//FOUO) Notifications reporting Uninstalled
                            PAC moduli and Installed DePAC Moduli management
                            activities"
        ::= { commonNotifGroup 9 }

    commonKeyTransferNotifications NOTIFICATION-GROUP
        NOTIFICATIONS       {
                                commonKeyIssueOK,
                                commonKeyIssueFailed,
                                commonIssuedKeyDeleted,
                                commonOOBXmitOK,
                                commonOOBRcvdOK,
                                commonOOBXmitFailed,
                                commonOOBFileEntryDeleted,
                                commonOOBRcvFailed,
                                commonKTIBRcvOK,
                                commonKTIBLocalOK,
                                commonKTIBLocalFailed,
                                commonKTIBRcvFailed,
                                commonKTIBXmitFailed,
                                commonKTIBClientEntryDeleted
                            }
        STATUS		    current
        DESCRIPTION         "(U//FOUO) The notification supporting HAIPE Out-of-Band
                            and In-Band Key Transfer management."
        ::= { commonNotifGroup 10 }

    commonQkeyEventNotifs NOTIFICATION-GROUP
        NOTIFICATIONS       {
                                commonQkeyFilled,
                                commonQkeyFillFailed,
                                commonQkeyDeleted,
                                commonQkeyDeleteFailed,
                                commonQkeyInstalled,
                                commonQkeyInstallFailed
                            }
        STATUS		    current
        DESCRIPTION         "(U//FOUO) Notifications reporting Uninstalled
                            Q-key and Installed APPK Trust Anchor management
                            activities"
        ::= { commonNotifGroup 11 }

    commonAuditLogEventVariables OBJECT IDENTIFIER ::= { commonConformance 7 }

    commonSecurityEventVariables OBJECT-GROUP
        OBJECTS	{
        		commonZeroizeReason,
        		commonPinActivity,
        		commonUpdateSystemDate,
        		commonSecurCritFltType,
        		commonSecCritPrimeFirstReg,
        		commonSecCritPrimeSumReg,
        		commonSecCritSubFirstReg,
        		commonSecCritSubSumReg,
        		commonSWFltAddressID,
        		commonSWFltFileName,
        		commonSWFltLineNum,
        		commonSWFltArg1,
        		commonSWFltArg2,
        		commonSWFltArg3,
        		commonSWFltArg4,
        		commonSWFltStackDump,
        		commonOrigEnableValue,
        		commonNewEnableValue,
        		commonOrigConfigDataValue,
        		commonNewConfigDataValue,
        		commonPrivModItemName,
        		commonBIPErrorCount,
        		commonConfigurationResetType,
        		commonAuditLogInitializeReason,
        		commonDiagnosticId,
        		commonDiagFailArg1,
        		commonDiagFailArg2,
        		commonDiagFailArg3,
        		commonDiagFailArg4,
        		commonKEKId,
        		commonConfigConflictDescription,
        		commonHWFltArg1,
        		commonHWFltArg2,
        		commonHWFltArg3,
        		commonHWFltArg4,
        		commonUnIdentifiedKeyFillErrorReason
        	}
        STATUS		    current
        DESCRIPTION         "(U//FOUO) Notification variables supporting Security
                            Audit Log Events related to device security."
        ::= { commonAuditLogEventVariables 1 }

    commonCIKEventVariables OBJECT-GROUP
        OBJECTS	{
        		commonCIKCreateReason,
        		commonFailedCikReason,
        		commonFailedCikOperation
        	}
        STATUS		    current
        DESCRIPTION         "(U//FOUO) Notification variables supporting Security
                            Audit Log Events related to CIK management."
        ::= { commonAuditLogEventVariables 2 }

    commonFFVSEventVariables OBJECT-GROUP
        OBJECTS	{
        		commonFFFailedFillReason,
        		commonFFVSDeleteReason,
        		commonFFSARole,
        		commonFFNegotiaFailureReason,
        		commonACLUpdateAction,
        		commonCKLUpdateAction,
        		commonRemoteFFKMID,
        		commonFFTEKDeletedReason,
        		commonFFNextVectorPresent,
        		commonRemoteSAspi,
        		commonLastIkePduSent
        	}
        STATUS		    current
        DESCRIPTION         "(U//FOUO) Notification variables supporting Security
                            Audit Log Events related to FFVS administration."
        ::= { commonAuditLogEventVariables 3 }

    commonPPKEventVariables OBJECT-GROUP
        OBJECTS	{
        		commonPPKFailedFillReason,
        		commonPPKDeleteReason
        	}
        STATUS		    current
        DESCRIPTION         "(U//FOUO) Notification variables supporting Security
                            Audit Log Events related to PPK administration."
        ::= { commonAuditLogEventVariables 4 }

    commonSNMPEventVariables OBJECT-GROUP
        OBJECTS	{
        		commonSNMPUserName,
        		commonUpdateUserAction,
        		commonSNMPUserTableChanged,
        		commonSNMPUserTableOperation,
        		commonSNMPTableRowName
        	}
        STATUS		    current
        DESCRIPTION         "(U//FOUO) Notification variables supporting Security
                            Audit Log Events related to SNMP management administration."
        ::= { commonAuditLogEventVariables 5 }

    commonIPEventVariables OBJECT-GROUP
        OBJECTS	{
        		commonRejectedPSEQN,
        		commonPSEQNRejectCount,
        		commonRateLimitId,
        		commonOverflowCount,
        		commonIPv6FavoredAddress,
        		commonIPv6Address,
        		commonIPv4Address,
        		commonAutoconfigurationFailure
        	}
        STATUS		    current
        DESCRIPTION         "(U//FOUO) Notification variables supporting Security
                            Audit Log Events related to IP."
        ::= { commonAuditLogEventVariables 6 }

    commonIFEventVariables OBJECT-GROUP
        OBJECTS	{
        		commonPTSpeedMode,
        		commonCTSpeedMode
        	}
        STATUS		    current
        DESCRIPTION         "(U//FOUO) Notification variables supporting notifications
                            related to interface events."
        ::= { commonAuditLogEventVariables 7 }

    commonSAEventVariables OBJECT-GROUP
        OBJECTS	{
        		commonSAIndex,
        		commonSAspi,
        		commonAddressType,
        		commonRemoteCTAddress
        	}
        STATUS		    current
        DESCRIPTION         "(U//FOUO) The notification variables supporting
                            Security Association (SA) events."
        ::= { commonAuditLogEventVariables 9 }

    commonPACEventVariables OBJECT-GROUP
        OBJECTS	{
        		commonPACFailedFillReason,
        		commonPACDeleteReason,
        		commonPACDeleteFailureReason,
        		commonPACState
        	}
        STATUS		    current
        DESCRIPTION         "(U//FOUO) The notification variables supporting
                            PAC management"
        ::= { commonAuditLogEventVariables 10 }

    commonKeyTransferVariables OBJECT-GROUP
        OBJECTS	{
        		commonKeyIssueFailReason,
        		commonIssuedKeyDeleteReason,
        		commonOOBIssueFailReason,
        		commonOOBRecvdFailReason,
        		commonKTIBRcvdFailReason,
        		commonKTIBXmitFailReason,
        		commonOOBClientPath
        	}
        STATUS		    current
        DESCRIPTION         "(U//FOUO) The notification variables supporting
                            Out-of-Band and In-Band Key Transfer management"
        ::= { commonAuditLogEventVariables 11 }

    commonQkeyEventVariables OBJECT-GROUP
        OBJECTS	{
        		commonQkeyFillFailureReason,
        		commonQkeyDeleteReason,
        		commonQkeyDeleteFailureReason,
        		commonQkeyState,
        		commonQkeyInstallFailureReason
        	}
        STATUS		    current
        DESCRIPTION         "(U//FOUO) The notification variables supporting
                            Q-key management."
        ::= { commonAuditLogEventVariables 12 }

    commonSysLevelEventVariables OBJECT-GROUP
        OBJECTS	{
        		commonUserName
        	}
        STATUS		    current
        DESCRIPTION         "(U//FOUO) Event variable objects used by notifications
                            in multiple categories."
        ::= { commonAuditLogEventVariables 13 }

    commonNotifEventsGroup OBJECT IDENTIFIER ::= { commonConformance 8 }

    commonSecurityNotifEventsGroup NOTIFICATION-GROUP
        NOTIFICATIONS       {
                                commonAudLogInitialized,
                                commonAudLogStatusChanged,
                                commonBatteryStatusChanged,
                                commonConfigConflict2,
                                commonConfigurationReset,
                                commonDiagnosticFailed,
                                commonHWSecurCriticalFault2,
                                commonKEKUpdated,
                                commonKeyFilled2,
                                commonPrivilegItemValue2,
                                commonRealTimeClockSet2,
                                commonSsoPinActivity,
                                commonSWSecurCriticalFault2,
                                commonTamper,
                                commonUnIdentifiedKeyFillError2,
                                commonZeroize2
                            }
        STATUS		    current
        DESCRIPTION         "(U//FOUO) The notifications associated with security
                            administration of the device."
        ::= { commonNotifEventsGroup 1 }

    commonCIKNotifEventsGroup NOTIFICATION-GROUP
        NOTIFICATIONS       {
                                commonCikActive,
                                commonCikCreated2,
                                commonCikDeleted2,
                                commonCikFailed,
                                commonFTRKSDCreated
                            }
        STATUS		    current
        DESCRIPTION         "(U//FOUO) The notifications associated with CIK
                            use and administration."
        ::= { commonNotifEventsGroup 2 }

    commonFFNotifEventsGroup NOTIFICATION-GROUP
        NOTIFICATIONS       {
                                commonACLUpdated2,
                                commonChildSATEKCreated,
                                commonChildSATEKDeleted,
                                commonFFKeyExpirationWarning,
                                commonFFTEKCreated2,
                                commonFFTEKDeleted2,
                                commonFFVSDeleted2,
                                commonFFVSExpired2,
                                commonFFVSFillFailed2,
                                commonFFVSFillOK3,
                                commonIKESACreated,
                                commonIKESADeleted,
                                commonIKEv1NegotiationFailure,
                                commonIKEv2NegotiationFailure
                            }
        STATUS		    current
        DESCRIPTION         "(U//FOUO) The notifications associated with FFVS
                            use and administration."
        ::= { commonNotifEventsGroup 3 }

    commonPPKNotifEventsGroup NOTIFICATION-GROUP
        NOTIFICATIONS       {
                                commonDGSKCreated,
                                commonDGSKDeleted,
                                commonDGSKExpired,
                                commonDGSKFillFail,
                                commonEKExpiredIKEv1,
                                commonEKExpiredIKEv2,
                                commonEKUseDGSK,
                                commonEKUsePPK,
                                commonManualSAUsePPK,
                                commonPPKDeleted2,
                                commonPPKExpired2,
                                commonPPKFillFail2,
                                commonPPKFillOK2,
                                commonPPKKeyExpirationWarning,
                                commonPPKSADInEntryOperation,
                                commonPPKSADOutEntryOperation,
                                commonSharedSecretExpired,
                                commonSharedSecretExpiringDGSK,
                                commonSharedSecretExpiringPPK,
                                commonSharedSecretUseDGSK,
                                commonSharedSecretUsePPK
                            }
        STATUS		    current
        DESCRIPTION         "(U//FOUO) The notifications associated with PPK
                            use and administration."
        ::= { commonNotifEventsGroup 4 }

    commonSNMPNotifEventsGroup NOTIFICATION-GROUP
        NOTIFICATIONS       {
                                commonSNMPUserUpdate2
                            }
        STATUS		    current
        DESCRIPTION         "(U//FOUO) The notifications associated with SNMP
                            administration."
        ::= { commonNotifEventsGroup 5 }

    commonIPNotifEventsGroup NOTIFICATION-GROUP
        NOTIFICATIONS       {
                                commonAutoAddressConfigFail2,
                                commonIPAddrChanged,
                                commonNetDuplicateAddressDetected,
                                commonPSEQNError3,
                                commonRateLimitOverflow
                            }
        STATUS		    current
        DESCRIPTION         "(U//FOUO) The notifications associated with IP
                            administration."
        ::= { commonNotifEventsGroup 6 }

    commonIFNotifEventsGroup NOTIFICATION-GROUP
        NOTIFICATIONS       {
                                commonIFSpeedModeMismatch2,
                                commonIFSpeedNegotiationFailure2,
                                commonLinkStatusChanged,
                                commonDhcpStateChanged
                            }
        STATUS		    current
        DESCRIPTION         "(U//FOUO) The notifications associated with interface
                            configuration."
        ::= { commonNotifEventsGroup 7 }

    commonPACNotifEventsGroup NOTIFICATION-GROUP
        NOTIFICATIONS       {
                                commonPACOperation,
                                commonPACOperationFailed
                            }
        STATUS		    current
        DESCRIPTION         "(U//FOUO) The notifications associated with PAC
                            moduli administration."
        ::= { commonNotifEventsGroup 8 }

    commonKTNotifEventsGroup NOTIFICATION-GROUP
        NOTIFICATIONS       {
                                commonIssuedKeyDeleted2,
                                commonKeyIssueFailed2,
                                commonKeyIssueOK2,
                                commonKTIBClientEntryDeleted2,
                                commonKTIBLocalOperation,
                                commonKTIBRcvFailed2,
                                commonKTIBRcvOK2,
                                commonKTIBXmitFailed2,
                                commonOOBFileEntryDeleted2,
                                commonOOBRcvOperation,
                                commonOOBXmitOperation
                            }
        STATUS		    current
        DESCRIPTION         "(U//FOUO) The notifications associated with In-Band
                            and Out-Of-Band key administration."
        ::= { commonNotifEventsGroup 9 }

    commonQKeyNotifEventsGroup NOTIFICATION-GROUP
        NOTIFICATIONS       {
                                commonQkeyOperation,
                                commonQkeyOperationFailed
                            }
        STATUS		    current
        DESCRIPTION         "(U//FOUO) The notifications associated with Q-Key
                            administration."
        ::= { commonNotifEventsGroup 10 }

    commonSWDLNotifEventsGroup NOTIFICATION-GROUP
        NOTIFICATIONS       {
                                commonFirmwareOperation,
                                commonFirmwareOperationFailed,
                                commonFileTransferSucceeded,
                                commonFileTransferFailed
                            }
        STATUS		    current
        DESCRIPTION         "(U//FOUO) The notifications associated with SWDL
                            administration."
        ::= { commonNotifEventsGroup 11 }

    commonAuditUploadNotifEventsGroup NOTIFICATION-GROUP
        NOTIFICATIONS       {
                                commonAuditUploadRequested,
                                commonAuditUploadOperation,
                                commonAuditUploadKeyPairGen
                            }
        STATUS		    current
        DESCRIPTION         "(U//FOUO) The notifications associated with Audit
                            Upload operations."
        ::= { commonNotifEventsGroup 12 }

    commonNotifEventVariableObjectsGroup
        OBJECT IDENTIFIER ::= { commonConformance 9 }

    commonSecurityNotifEventVarObjectsGroup OBJECT-GROUP
        OBJECTS	{
        		commonAuditLogInitializeReason,
        		commonAudLogStatus,
        		commonBatteryStatus,
        		commonConfigConflictDescription,
        		commonConfigurationResetType,
        		commonDiagFailArg1,
        		commonDiagFailArg2,
        		commonDiagFailArg3,
        		commonDiagFailArg4,
        		commonDiagnosticId,
        		commonHWFltArg1,
        		commonHWFltArg2,
        		commonHWFltArg3,
        		commonHWFltArg4,
        		commonKEKId,
        		commonNewConfigDataValue,
        		commonOrigConfigDataValue,
        		commonPinActivity,
        		commonPrivModItemName,
        		commonSecCritPrimeFirstReg,
        		commonSecCritPrimeSumReg,
        		commonSecCritSubFirstReg,
        		commonSecCritSubSumReg,
        		commonSWFltAddressID,
        		commonSWFltArg1,
        		commonSWFltArg2,
        		commonSWFltArg3,
        		commonSWFltArg4,
        		commonSWFltFileName,
        		commonSWFltLineNum,
        		commonSWFltStackDump,
        		commonUnIdentifiedKeyFillErrorReason,
        		commonUpdateSystemDate,
        		commonZeroizeReason
        	}
        STATUS		    current
        DESCRIPTION         "(U//FOUO) The notification objects associated
                            with security administration of the device."
        ::= { commonNotifEventVariableObjectsGroup 1 }

    commonCIKNotifEventVarObjectsGroup OBJECT-GROUP
        OBJECTS	{
        		commonCIKCreateReason,
        		commonFailedCikOperation,
        		commonFailedCikReason
        	}
        STATUS		    current
        DESCRIPTION         "(U//FOUO) The notification objects associated
                            with CIK use and administration."
        ::= { commonNotifEventVariableObjectsGroup 2 }

    commonFFNotifEventVarObjectsGroup OBJECT-GROUP
        OBJECTS	{
        		commonACLUpdateAction,
        		commonFFFailedFillReason,
        		commonFFNegotiaFailureReason,
        		commonFFSARole,
        		commonFFTEKDeletedReason,
        		commonFFVSDeleteReason,
        		commonFireFlyKeyType,
        		commonFireFlyMaterialType,
        		commonFireFlyPartitionCode,
        		commonFireFlyVectorType,
        		commonIKEv1DeletedReason,
        		commonIKEv2DeletedReason,
        		commonIKEv2ExchangeType,
        		commonIKEv2NegotiaFailureReason,
        		commonInitiatorSAspi,
        		commonKMID,
        		commonLastIkePduSent,
        		commonRemoteFFKMID,
        		commonRemoteSAspi,
        		commonResponderSAspi,
        		commonUniversalEdition,
        		commonUniversalID
        	}
        STATUS		    current
        DESCRIPTION         "(U//FOUO) The notification objects associated
                            with FFVS use and administration."
        ::= { commonNotifEventVariableObjectsGroup 3 }

    commonPPKNotifEventVarObjectsGroup OBJECT-GROUP
        OBJECTS	{
        		commonChainName,
        		commonChainOrder,
        		commonDGSKDeleteReason,
        		commonDGSKFailedFillReason,
        		commonDGSKIndex,
        		commonEdition,
        		commonEffectiveDate,
        		commonEKType,
        		commonKeyMode,
        		commonPPKDeleteReason,
        		commonPPKFailedFillReason,
        		commonSegment,
        		commonShortTitle,
        		commonUsageType
        	}
        STATUS		    current
        DESCRIPTION         "(U//FOUO) The notification objects associated
                            with PPK use and administration."
        ::= { commonNotifEventVariableObjectsGroup 4 }

    commonSANotifEventVarObjectsGroup OBJECT-GROUP
        OBJECTS	{
        		commonDFBitSetting,
        		commonDSCPSetting,
        		commonDSCPValue,
        		commonECNSetting,
        		commonSAIndex,
        		commonSAChildIndex,
        		commonSAspi,
        		commonSPIChainReference,
        		commonTransformSuite,
        		commonBankNum
        	}
        STATUS		    current
        DESCRIPTION         "(U//FOUO) The notification objects associated
                            with PPK use and administration."
        ::= { commonNotifEventVariableObjectsGroup 5 }

    commonSNMPNotifEventVarObjectsGroup OBJECT-GROUP
        OBJECTS	{
        		commonSNMPTableRowName,
        		commonSNMPUserName,
        		commonSNMPUserTableChanged,
        		commonSNMPUserTableOperation
        	}
        STATUS		    current
        DESCRIPTION         "(U//FOUO) The notification objects associated
                            with SNMP administration."
        ::= { commonNotifEventVariableObjectsGroup 6 }

    commonIPNotifEventVarObjectsGroup OBJECT-GROUP
        OBJECTS	{
        		commonAutoconfigurationFailure,
        		commonOverflowCount,
        		commonPSEQNRejectCount,
        		commonRateLimitId,
        		commonRejectedPSEQN
        	}
        STATUS		    current
        DESCRIPTION         "(U//FOUO) The notification objects associated
                            with IP administration."
        ::= { commonNotifEventVariableObjectsGroup 7 }

    commonIFNotifEventVarObjectsGroup OBJECT-GROUP
        OBJECTS	{
        		commonIfAdminStatus,
        		commonIfOperStatus,
        		commonIfSpeedModeCT,
        		commonIfSpeedModePT,
        		commonLinkStatus,
        		commonDhcpState
        	}
        STATUS		    current
        DESCRIPTION         "(U//FOUO) The notification objects associated
                            with interface configuration."
        ::= { commonNotifEventVariableObjectsGroup 8 }

    commonPACNotifEventVarObjectsGroup OBJECT-GROUP
        OBJECTS	{
        		commonPACAction,
        		commonPACFailedReason,
        		commonPACReason,
        		commonPACState
        	}
        STATUS		    current
        DESCRIPTION         "(U//FOUO) The notification objects associated
                            with PAC moduli administration."
        ::= { commonNotifEventVariableObjectsGroup 9 }

    commonKTNotifEventVarObjectsGroup OBJECT-GROUP
        OBJECTS	{
        		commonIssuedKeyDeleteReason,
        		commonKeyFile,
        		commonKeyIndex,
        		commonKeyIssueFailReason,
        		commonKeyUse,
        		commonKTIBLocalReason,
        		commonKTIBRcvdFailReason,
        		commonKTIBXmitFailReason,
        		commonOOBClientPath,
        		commonOOBIssueReason,
        		commonOOBRcvdReason,
        		commonRegister
        	}
        STATUS		    current
        DESCRIPTION         "(U//FOUO) The notification objects associated
                            with In-Band and Out-Of-Band key administration."
        ::= { commonNotifEventVariableObjectsGroup 10 }

    commonQKeyNotifEventVarObjectsGroup OBJECT-GROUP
        OBJECTS	{
        		commonQkeyAction,
        		commonQkeyFailedReason,
        		commonQkeyReason,
        		commonQkeyState
        	}
        STATUS		    current
        DESCRIPTION         "(U//FOUO) The notification objects associated
                            with Q-Key administration."
        ::= { commonNotifEventVariableObjectsGroup 11 }

    commonSWDLNotifEventVarObjectsGroup OBJECT-GROUP
        OBJECTS	{
        		commonFdErrCode,
        		commonFdErrDetail,
        		commonFdsURI,
        		commonFirmwareAction
        	}
        STATUS		    current
        DESCRIPTION         "(U//FOUO) The notification objects associated
                            with SWDL administration."
        ::= { commonNotifEventVariableObjectsGroup 12 }

    commonSysLevelNotifEventVarObjectsGroup OBJECT-GROUP
        OBJECTS	{
        		commonAction,
        		commonAddress,
        		commonAddressType,
        		commonClassification,
        		commonCryptoSuite,
        		commonExpirationDate,
        		commonIfIndex,
        		commonLocalCTAddress,
        		commonLocalHostAddress,
        		commonLocalPTAddress,
        		commonPort,
        		commonRemoteHostAddress,
        		commonRemoteCTAddress,
        		commonRemotePTAddress,
        		commonStationID,
        		commonStatus,
        		commonSystemDate,
        		commonUserName,
        		commonName,
        		commonErrDetail,
        		commonURI
        	}
        STATUS		    current
        DESCRIPTION         "(U//FOUO) The notification objects associated
                            with notifications in multiple categories."
        ::= { commonNotifEventVariableObjectsGroup 13 }


END
