--
--            UNCLASSIFIED//FOR OFFICIAL USE ONLY, PROPIN
--
-- This entire document, which defines ViaSat Proprietary MIB objects in the
-- SMIv2 language should be considered U//FOUO,PR.
--
-- The data that will be transmitted on the wire as a result of
-- accessing these MIB objects MUST NOT BE CONSIDERED U//FOUO and is
-- subject to separate classification.  The classification level of this
-- data is not defined or within the scope of this document.
--

ALTASEC-HAIPE-V4-MIB DEFINITIONS ::= BEGIN

IMPORTS
    OBJECT-TYPE, NOTIFICATION-TYPE,
    Integer32, Unsigned32,
    Counter64, MODULE-IDENTITY            FROM SNMPv2-SMI
    TEXTUAL-CONVENTION,
    RowStatus, DateAndTime, TruthValue,
    TimeStamp, DisplayString              FROM SNMPv2-TC
    IPAddressType,
    IPAddress,
    HaipeIKEv1SATransformSuites,
    HaipeDeviceSide,
    PreplacedKeyEdition,
    PreplacedKeySegment,
    DGSharedKeyShortTitle,
    PreplacedKeyShortTitle				  FROM HAIPE-V4-TEXTUAL-CONVENTIONS-MIB 
    SnmpAdminString                       FROM SNMP-FRAMEWORK-MIB
    hIKEv2CHILDSADTableEntry,
    hIKEv1NtwkParamsProfileTableEntry,
    hIKEv1SADTableEntry,
    hIKEv2IKESADTableEntry,
    hManualSADTableEntry                  FROM HAIPE-V4-TRAFFIC-PROTECTION-MIB
    hLEPTTableEntry,
    hPEPTTableEntry,
    hGDCSolicitDelivTableEntry,
    hLegacyDeliveryTableEntry,
    hRIPTableEntry,
    hGDCRegistrationTableEntry            FROM HAIPE-V4-DISCOVERY-MIB
    usmUserSecurityName                   FROM SNMP-USER-BASED-SM-MIB
    hIPv4IfaceTableEntry,
    hIPv6IfaceTableEntry,                  
    hAddressAssignTableEntry              FROM HAIPE-V4-NETWORKING-MIB
    hOOBKTClientsTableEntry,
    hIBKTClientsTableEntry,
    hLoadedKeyTableEntry                  FROM HAIPE-V4-KEY-TRANSFER-MIB
    hDGSharedKeyTableEntry,
    hAPPKTATableEntry,
    hManSAKeyChainTableEntry	            FROM HAIPE-V4-KEY-INFORMATION-MIB
    hFwDwnldServerTableEntry              FROM HAIPE-V4-MANAGEMENT-MIB
    altasecMIB                            FROM VIASAT-PRODUCT-MIB;


altasecHv4Mib MODULE-IDENTITY
    LAST-UPDATED "201506020000Z"
    ORGANIZATION "ViaSat"
    CONTACT-INFO
         "(U//FOUO) Not Available"
    DESCRIPTION
        "(U//FOUO) This MIB defines the ViaSat Proprietary MIB objects for HAIPEv4."
    REVISION "201506020000Z"
    DESCRIPTION "(U//FOUO//PROPIN) ViaSat Propritary MIB 2.0"
    REVISION "201112100000Z"
    DESCRIPTION "(U//FOUO//PROPIN) ViaSat Propritary MIB 1.0"
    ::= {  altasecMIB 100 }


--
-- ViaSat Information Segments
-- Note: These OIDs match the structure of the HAIPE MIBs where extensions are
--       present.
--

altasecHv4TrafficProtection  OBJECT IDENTIFIER ::= { altasecHv4Mib 3 }
altasecHv4Discovery          OBJECT IDENTIFIER ::= { altasecHv4Mib 4 }
altasecHv4Networking         OBJECT IDENTIFIER ::= { altasecHv4Mib 5 }
altasecHv4Mgmt               OBJECT IDENTIFIER ::= { altasecHv4Mib 6 }
altasecHv4BandwidthManagement OBJECT IDENTIFIER ::= { altasecHv4Mib 7 }

---
--- Traffic Protection Group
---

altasecHv4TP                 OBJECT IDENTIFIER ::= { altasecHv4TrafficProtection 1 }
altasecHv4TPGlobalScalars    OBJECT IDENTIFIER ::= { altasecHv4TP 2 }
altasecHv4PolicyEnforcement  OBJECT IDENTIFIER ::= { altasecHv4TP 3 }

altasecHv4SPD                OBJECT IDENTIFIER ::= { altasecHv4PolicyEnforcement 1 }
altasecHv4SADatabase         OBJECT IDENTIFIER ::= { altasecHv4PolicyEnforcement 2 }

altasecHv4EstTS              OBJECT IDENTIFIER ::= { altasecHv4SADatabase 1 }
altasecHv4ManualSAD          OBJECT IDENTIFIER ::= { altasecHv4SADatabase 2 }
altasecHv4IKEv1SAD           OBJECT IDENTIFIER ::= { altasecHv4SADatabase 3 }
altasecHv4IKEv2SAD           OBJECT IDENTIFIER ::= { altasecHv4SADatabase 4 }
altasecHv4SASummary          OBJECT IDENTIFIER ::= { altasecHv4SADatabase 5 }

altasecHv4EstTSIndex         OBJECT IDENTIFIER ::= { altasecHv4EstTS 3 }

altasecHv4SAProfiles         OBJECT IDENTIFIER ::= { altasecHv4SPD 3 }
altasecHv4IKEv1SAProfiles    OBJECT IDENTIFIER ::= { altasecHv4SAProfiles 2 }
altasecHv4NtwkParamsProfiles OBJECT IDENTIFIER ::= { altasecHv4IKEv1SAProfiles 2 }

altasecHv4IKEv2CHILDSAD      OBJECT IDENTIFIER ::= { altasecHv4IKEv2SAD 1 }
altasecHv4IKEv2IKESAD        OBJECT IDENTIFIER ::= { altasecHv4IKEv2SAD 2 }

---
--- Discovery Group
---

altasecHv4DiscoveryMib             OBJECT IDENTIFIER ::= { altasecHv4Discovery 1 }

altasecHv4PeerDiscovery            OBJECT IDENTIFIER ::= { altasecHv4DiscoveryMib 1 }
altasecHv4LocalDiscovery           OBJECT IDENTIFIER ::= { altasecHv4DiscoveryMib 2 }
altasecHv4LocalCtDiscovery         OBJECT IDENTIFIER ::= { altasecHv4DiscoveryMib 3 }
altasecHv4HD3Discovery             OBJECT IDENTIFIER ::= { altasecHv4DiscoveryMib 4 }

altasecHv4LEPT                     OBJECT IDENTIFIER ::= { altasecHv4LocalDiscovery 2 }
altasecHv4RIPConfig                OBJECT IDENTIFIER ::= { altasecHv4LocalDiscovery 3 }
altasecHv4LocCTRt                     OBJECT IDENTIFIER ::= { altasecHv4LocalCtDiscovery 2 }

altasecHv4PEPT                     OBJECT IDENTIFIER ::= { altasecHv4PeerDiscovery 1 }
altasecHv4LegacyDiscovery          OBJECT IDENTIFIER ::= { altasecHv4PeerDiscovery 4 }
altasecHv4GDC                      OBJECT IDENTIFIER ::= { altasecHv4PeerDiscovery 5 }

altasecHv4HD3Config                OBJECT IDENTIFIER ::= { altasecHv4HD3Discovery 1 }
altasecHv4HD3RuntimeInfo           OBJECT IDENTIFIER ::= { altasecHv4HD3Discovery 2 }
altasecHv4HD3ServerInfo            OBJECT IDENTIFIER ::= { altasecHv4HD3Discovery 3 }

---
--- Networking Group
---   
altasecHv4NetworkingExt      OBJECT IDENTIFIER ::= { altasecHv4Networking 1 } 
altasecHv4NetScalars         OBJECT IDENTIFIER ::= { altasecHv4NetworkingExt  1 } 
altasecHv4IPv4Augmentation   OBJECT IDENTIFIER ::= { altasecHv4NetworkingExt  2 } 
altasecHv4IPv6Augmentation   OBJECT IDENTIFIER ::= { altasecHv4NetworkingExt  3 }
altasecHv4AddrAssign         OBJECT IDENTIFIER ::= { altasecHv4NetworkingExt  4 }
altasecHv4Interface          OBJECT IDENTIFIER ::= { altasecHv4NetworkingExt  5 }
altasecHv4SFP                OBJECT IDENTIFIER ::= { altasecHv4NetworkingExt  6 }

altasecHv4VLAN               OBJECT IDENTIFIER ::= { altasecHv4NetworkingExt  10 }  

altasecHv4GDCRegistration          OBJECT IDENTIFIER ::= { altasecHv4GDC 1 }
altasecHv4GDCSolicitDelivery       OBJECT IDENTIFIER ::= { altasecHv4GDC 2 }
altasecHv4LegacyDiscoveryDelivery  OBJECT IDENTIFIER ::= { altasecHv4LegacyDiscovery 1 }
---
--- Management Group
--- 

altasecHv4MgmtRemote         OBJECT IDENTIFIER ::= { altasecHv4Mgmt 1 }
altasecHv4KeyTransfer        OBJECT IDENTIFIER ::= { altasecHv4Mgmt 2 }
altasecHv4MgmtSigDL          OBJECT IDENTIFIER ::= { altasecHv4Mgmt 3 }
altasecHv4MgmtAlert          OBJECT IDENTIFIER ::= { altasecHv4Mgmt 4 }
altasecHv4MgmtAudit          OBJECT IDENTIFIER ::= { altasecHv4Mgmt 5 }
altasecHv4MgmtTemps          OBJECT IDENTIFIER ::= { altasecHv4Mgmt 6 }

altasecHv4MgmtBattery        OBJECT IDENTIFIER ::= { altasecHv4Mgmt 8 }
altasecHv4MgmtSession        OBJECT IDENTIFIER ::= { altasecHv4Mgmt 9 }
altasecHv4MgmtCIK            OBJECT IDENTIFIER ::= { altasecHv4Mgmt 10 }
altasecHv4MgmtTFTP           OBJECT IDENTIFIER ::= { altasecHv4Mgmt 11 }
altasecHv4MgmtHB             OBJECT IDENTIFIER ::= { altasecHv4Mgmt 12 }
altasecHv4MgmtRestoreDefault OBJECT IDENTIFIER ::= { altasecHv4Mgmt 13 }
altasecHv4MgmtIwks           OBJECT IDENTIFIER ::= { altasecHv4Mgmt 14 }

---
--- Key Transfer Group
--- 

altasecHv4H2HKT                        OBJECT IDENTIFIER ::= { altasecHv4KeyTransfer 3 }
altasecHv4OutofBandKeyTransfer         OBJECT IDENTIFIER ::= { altasecHv4H2HKT 1 }
altasecHv4OutofBandKeyTransferClients  OBJECT IDENTIFIER ::= { altasecHv4OutofBandKeyTransfer 1 }
altasecHv4InBandKeyTransfer            OBJECT IDENTIFIER ::= { altasecHv4H2HKT 2 }
altasecHv4InBandKeyTransferClients     OBJECT IDENTIFIER ::= { altasecHv4InBandKeyTransfer 1 }
altasecHv4LoadedKeys                   OBJECT IDENTIFIER ::= { altasecHv4H2HKT 3 }
--
-- ViaSat Traffic Protection Information Segments
--
	
altasecHv4TPCryptography       	 	OBJECT IDENTIFIER ::= { altasecHv4TrafficProtection 2 }
altasecHv4TPPolicyObjects      	 	OBJECT IDENTIFIER ::= { altasecHv4TrafficProtection 5 }

altasecHv4CryptoControl        	 	OBJECT IDENTIFIER ::= { altasecHv4TPCryptography 1 }
altasecHv4ChainInformation       	OBJECT IDENTIFIER ::= { altasecHv4TPCryptography 3 }
altasecHv4KeyInformation       	 	OBJECT IDENTIFIER ::= { altasecHv4TPCryptography 4 }

altasecHv4PPKInformation       	 	OBJECT IDENTIFIER ::= { altasecHv4KeyInformation 1 }

altasecHv4APPKKeyInformation    	OBJECT IDENTIFIER ::= { altasecHv4PPKInformation 1 }
altasecHv4PPKKeyInformation    	 	OBJECT IDENTIFIER ::= { altasecHv4PPKInformation 2 }
altasecHv4DGSharedKeyInformation	OBJECT IDENTIFIER ::= { altasecHv4PPKInformation 8 }

-- **********************************************************************
-- Textual conventions
-- **********************************************************************

AltasecEncryptionAlgorithm ::= TEXTUAL-CONVENTION
        STATUS  current
        DESCRIPTION
            "(U//FOUO) An encryption algorithm."
        SYNTAX   INTEGER { unassigned(0),
                           baton(1), 
                           medley(2),
                           aes(3)
                         }

AltasecIntegrityAlgorithm ::= TEXTUAL-CONVENTION
        STATUS  current
        DESCRIPTION
            "(U//FOUO) A data integrity algorithm.  It is possible
            that in some situations it will not be possible to
            determine the correct algorithm to return since more than
            one are in use for a given key (for example).  For these
            cases the multiple(7) value should be returned."
        SYNTAX   INTEGER { unassigned(0),
                           gcm0(1), 
                           gcm32(2),
                           gcm64(3),
                           gcm96(4),
                           gcm128(5),
                           bip32(6),
                           multiple(7)
                         }
                         
AltasecHv4DiscoveryStatus ::= TEXTUAL-CONVENTION
        STATUS  current
        DESCRIPTION
            "(U//FOUO) The current status of a Discovery entry."
        SYNTAX   INTEGER { active(1),
                           inactive(2)
                         }
                         
-- *************************************************
-- Peer Discovery.

altasecHv4DiscoveryEnabled OBJECT-TYPE
    SYNTAX      TruthValue
    MAX-ACCESS  read-write
    STATUS      current
    DESCRIPTION
        "(U//FOUO) The indication of whether the HAIPE will
        dynamically discover remote HAIPEs and establish an SA using
        the services listed in the hDiscoveryDeliveryTable."
    DEFVAL { true }
    ::= { altasecHv4PeerDiscovery 2 }
                      
-- ***********************************************************
-- Proprietary HD3 Configuration Objects
--

-- =======================
-- HD3 Configuration Scalars
-- =======================

altasecHv4HD3ConfigRole         OBJECT-TYPE
        SYNTAX               SnmpAdminString
        MAX-ACCESS           read-write
        STATUS               current
        DESCRIPTION
            "(U//FOUO,PR) The role of the current HD3 server: dedicated, 
        willing, or disabled."
        ::= { altasecHv4HD3Config 1 }

altasecHv4HD3ConfigMinSrv       OBJECT-TYPE
        SYNTAX               Unsigned32
        MAX-ACCESS           read-write
        STATUS               current
        DESCRIPTION
            "(U//FOUO,PR) HD3 Minimum Server Count"
        ::= { altasecHv4HD3Config 2 }

altasecHv4HD3ConfigMaxSrv       OBJECT-TYPE
        SYNTAX               Unsigned32
        MAX-ACCESS           read-write
        STATUS               current
        DESCRIPTION
            "(U//FOUO,PR) HD3 Maximum Server Count"
        ::= { altasecHv4HD3Config 3 }

altasecHv4HD3ConfigHelloIvl       OBJECT-TYPE
        SYNTAX               Unsigned32
        MAX-ACCESS           read-write
        STATUS               current
        DESCRIPTION
            "(U//FOUO,PR) HD3 Hello message interval"
        ::= { altasecHv4HD3Config 4 }

altasecHv4HD3ConfigDeadIvl       OBJECT-TYPE
        SYNTAX               Unsigned32
        MAX-ACCESS           read-write
        STATUS               current
        DESCRIPTION
            "(U//FOUO,PR) HD3 Dead message interval"
        ::= { altasecHv4HD3Config 5 }

altasecHv4HD3ConfigDataRetryIvl       OBJECT-TYPE
        SYNTAX               Unsigned32
        MAX-ACCESS           read-write
        STATUS               current
        DESCRIPTION
            "(U//FOUO,PR) HD3 Data Sync Retry Interval"
        ::= { altasecHv4HD3Config 6 }

altasecHv4HD3ConfigRoleRetryIvl       OBJECT-TYPE
        SYNTAX               Unsigned32
        MAX-ACCESS           read-write
        STATUS               current
        DESCRIPTION
            "(U//FOUO,PR) HD3 Role Request Retry Interval"
        ::= { altasecHv4HD3Config 7 }

altasecHv4HD3ConfigMaxRoleReqs        OBJECT-TYPE
        SYNTAX               Unsigned32
        MAX-ACCESS           read-write
        STATUS               current
        DESCRIPTION
            "(U//FOUO,PR) HD3 Maximum Role Request Retries"
        ::= { altasecHv4HD3Config 8 }

altasecHv4HD3ConfigHelloVersion       OBJECT-TYPE
        SYNTAX               Unsigned32
        MAX-ACCESS           read-write
        STATUS               current
        DESCRIPTION
            "(U//FOUO,PR) HD3 Hello Version (1-2)"
        ::= { altasecHv4HD3Config 9 }

altasecHv4HD3ConfigGDCShareEn         OBJECT-TYPE
        SYNTAX               Unsigned32
        MAX-ACCESS           read-write
        STATUS               current
        DESCRIPTION
            "(U//FOUO,PR) HD3 GDC Share Enabled"
        ::= { altasecHv4HD3Config 10 }

altasecHv4HD3ConfigSrvQuality         OBJECT-TYPE
        SYNTAX               Unsigned32
        MAX-ACCESS           read-write
        STATUS               current
        DESCRIPTION
            "(U//FOUO,PR) HD3 Server Quality"
        ::= { altasecHv4HD3Config 11 }

altasecHv4HD3ConfigP2PEnabled         OBJECT-TYPE
        SYNTAX               Unsigned32
        MAX-ACCESS           read-write
        STATUS               current
        DESCRIPTION
            "(U//FOUO,PR) HD3 P2P Enabled"
        ::= { altasecHv4HD3Config 12 }

altasecHv4HD3ConfigMaxP2PEnt          OBJECT-TYPE
        SYNTAX               Unsigned32
        MAX-ACCESS           read-write
        STATUS               current
        DESCRIPTION
            "(U//FOUO,PR) HD3 Max P2P Entries"
        ::= { altasecHv4HD3Config 13 }

-- =======================
-- HD3 Runtime Scalars
-- =======================

altasecHv4HD3RuntimeNodeID OBJECT-TYPE
        SYNTAX          Unsigned32
        MAX-ACCESS      read-only
        STATUS          current
        DESCRIPTION
            "(U//FOUO,PR) The HD3's node ID"
        ::= { altasecHv4HD3RuntimeInfo 1 }

altasecHv4HD3RuntimeState  OBJECT-TYPE
        SYNTAX          SnmpAdminString
        MAX-ACCESS      read-only
        STATUS          current
        DESCRIPTION
            "(U//FOUO,PR) The HD3's state: Master, Up, Idle or Down"
        ::= { altasecHv4HD3RuntimeInfo 2 }

altasecHv4HD3RuntimeRole   OBJECT-TYPE
        SYNTAX          SnmpAdminString
        MAX-ACCESS      read-only
        STATUS          current
        DESCRIPTION
            "(U//FOUO,PR) The HD3's Role: Dedicated, Nominated, Revoked,
             or None"
        ::= { altasecHv4HD3RuntimeInfo 3 }

altasecHv4HD3RuntimeNumSrvs OBJECT-TYPE
        SYNTAX           Unsigned32
        MAX-ACCESS       read-only
        STATUS           current
        DESCRIPTION
            "(U//FOUO,PR) The HD3's number of known servers"
        ::= { altasecHv4HD3RuntimeInfo 4 }

-- =======================
-- HD3 Server Table
-- =======================

altasecHv4HD3SrvInfoTable OBJECT-TYPE
        SYNTAX         SEQUENCE OF AltasecHv4HD3SrvInfoEntry
        MAX-ACCESS     not-accessible
        STATUS         current
        DESCRIPTION
            "(U//FOUO,PR) The table containing HD3 server information"
        ::= { altasecHv4HD3ServerInfo 1 }

altasecHv4HD3SrvInfoEntry OBJECT-TYPE
        SYNTAX         AltasecHv4HD3SrvInfoEntry
        MAX-ACCESS     not-accessible
        STATUS         current
        DESCRIPTION
            "(U//FOUO,PR) The table entry containing HD3 server information"
        INDEX { altasecHv4HD3SrvInfoNum }
        ::= { altasecHv4HD3SrvInfoTable 1 }

AltasecHv4HD3SrvInfoEntry ::= SEQUENCE
    {
       altasecHv4HD3SrvInfoNum    Unsigned32,
       altasecHv4HD3SrvInfoNode   Unsigned32,
       altasecHv4HD3SrvInfoCTIP   IPAddress,
       altasecHv4HD3SrvInfoPTIP   IPAddress,
       altasecHv4HD3SrvInfoState  SnmpAdminString,
       altasecHv4HD3SrvInfoRole   SnmpAdminString,
       altasecHv4HD3SrvInfoMethod SnmpAdminString,
       altasecHv4HD3SrvRowStatus  RowStatus
    }

altasecHv4HD3SrvInfoNum       OBJECT-TYPE
        SYNTAX             Unsigned32
        MAX-ACCESS         read-only
        STATUS             current
        DESCRIPTION
            "(U//FOUO,PR) The HD3 Server Number associated with this row."
        ::= { altasecHv4HD3SrvInfoEntry 1 }

altasecHv4HD3SrvInfoNode      OBJECT-TYPE
        SYNTAX             Unsigned32
        MAX-ACCESS         read-only
        STATUS             current
        DESCRIPTION
            "(U//FOUO,PR) The HD3 Server Node ID associated with this row."
        ::= { altasecHv4HD3SrvInfoEntry 2 }

altasecHv4HD3SrvInfoCTIP      OBJECT-TYPE
        SYNTAX             IPAddress
        MAX-ACCESS         read-create
        STATUS             current
        DESCRIPTION
            "(U//FOUO,PR) The HD3 Server CT IP associated with this row."
        ::= { altasecHv4HD3SrvInfoEntry 3 }

altasecHv4HD3SrvInfoPTIP      OBJECT-TYPE
        SYNTAX             IPAddress
        MAX-ACCESS         read-create
        STATUS             current
        DESCRIPTION
            "(U//FOUO,PR) The HD3 Server PT IP associated with this row."
        ::= { altasecHv4HD3SrvInfoEntry 4 }

altasecHv4HD3SrvInfoState     OBJECT-TYPE
        SYNTAX             SnmpAdminString
        MAX-ACCESS         read-only
        STATUS             current
        DESCRIPTION
            "(U//FOUO,PR) The HD3 Server State associated with this row."
        ::= { altasecHv4HD3SrvInfoEntry 5 }

altasecHv4HD3SrvInfoRole      OBJECT-TYPE
        SYNTAX             SnmpAdminString
        MAX-ACCESS         read-only
        STATUS             current
        DESCRIPTION
            "(U//FOUO,PR) The HD3 Server Role associated with this row."
        ::= { altasecHv4HD3SrvInfoEntry 6 }

altasecHv4HD3SrvInfoMethod    OBJECT-TYPE
        SYNTAX             SnmpAdminString
        MAX-ACCESS         read-only
        STATUS             current
        DESCRIPTION
            "(U//FOUO,PR) The HD3 Server Discovery Method associated with 
            this row."
        ::= { altasecHv4HD3SrvInfoEntry 7 }

altasecHv4HD3SrvRowStatus  OBJECT-TYPE
        SYNTAX             RowStatus
        MAX-ACCESS         read-create
        STATUS             current
        DESCRIPTION
            "(U//FOUO,PR) RowStatus for HD3 Server Interface."
        ::= { altasecHv4HD3SrvInfoEntry 8 }       
        
-- *************************************************
-- Remote Management.

-- added old syntax values to description (CHIMERA Team)
altasecHv4MgmtRemoteSetting OBJECT-TYPE
        SYNTAX              INTEGER 
                            { 
                               disabled(0), 
                               everyone(1), 
                               ipTable(2) }
        MAX-ACCESS          read-write
        STATUS              current
        DESCRIPTION
            "(U//FOUO,PR) The setting for how remote management shoudl be
             handled. Disabled indicates that remote management is disabled.
             everyone indicates that everyone is able to remotely manage
             this device. ipTable indicates that the 
             altsecHv4MgmtRemoteAddressTable is used to filter who is remotely
             able to manage this device.

             (U//FOUO,PR) Old values: enabled(0), disabled(1), single(2)."
        ::= { altasecHv4MgmtRemote 1 }

altasecHv4MgmtRemoteAddress4 OBJECT-TYPE
        SYNTAX               IPAddress
        MAX-ACCESS           read-write
        STATUS               current
        DESCRIPTION
            "(U//FOUO,PR) Remote Management IPv4 address."
        ::= { altasecHv4MgmtRemote 2 }

altasecHv4MgmtRemoteAddress6 OBJECT-TYPE
        SYNTAX               IPAddress
        MAX-ACCESS           read-write
        STATUS               current
        DESCRIPTION
            "(U//FOUO,PR) Remote Management IPv6 address."
        ::= { altasecHv4MgmtRemote 3 }
        
altasecHv4MgmtUDPZeroizeInterval  OBJECT-TYPE
        SYNTAX                    Unsigned32(10..600)
        MAX-ACCESS                read-write
        STATUS                    current
        DESCRIPTION
            "(U//FOUO,PR) UDP Management interval before a zeroize executes."
        DEFVAL { 50 }
        ::= { altasecHv4MgmtRemote 4 }

altasecHv4MgmtUDPZeroize OBJECT-TYPE
        SYNTAX           TruthValue
        MAX-ACCESS       read-write
        STATUS           current
        DESCRIPTION
            "(U//FOUO,PR) UDP Management zeroize flag."
        ::= { altasecHv4MgmtRemote 5 }

altasecHv4MgmtUDPPort    OBJECT-TYPE
        SYNTAX           Unsigned32(0..65535)
        MAX-ACCESS       read-write
        STATUS           current
        DESCRIPTION
            "(U//FOUO,PR) UDP Management IP port. Setting this value to
            0 disables UDP Management."
        DEFVAL { 3000 }
        ::= { altasecHv4MgmtRemote 6 }
        
altasecHv4MgmtUDPRememberHbt    OBJECT-TYPE
        SYNTAX           TruthValue
        MAX-ACCESS       read-write
        STATUS           current
        DESCRIPTION
            "(U//FOUO,PR) UDP Management Remember Heartbeat flag. Setting this
            flag causes the INE to remember if a Heartbeat has been previously
            received across reboots."
        ::= { altasecHv4MgmtRemote 7 }
        
-- *************************************************
-- Remote Management Address Table.

altasecHv4MgmtRemoteAddressTableCount       OBJECT-TYPE
        SYNTAX              Unsigned32
        MAX-ACCESS          read-only
        STATUS              current
        DESCRIPTION
            "(U//FOUO,PR) The number of rows in the altasecHv4MgmtRemoteAddressTable."
        ::= { altasecHv4MgmtRemote 8 }

altasecHv4MgmtRemoteAddressTableTableLastChanged OBJECT-TYPE
        SYNTAX              TimeStamp
        MAX-ACCESS          read-only
        STATUS              current
        DESCRIPTION
            "(U//FOUO,PR) The value of sysUpTime the last time any entry in
             the altasecHv4MgmtRemoteAddressTable was modified, created, or deleted by
             either SNMP or other management method (e.g., via an HMI).

             (U//FOUO,PR) Managers can use this object to ensure that no
             changes to configuration of this table have happened since the
             last time it examined the table.

             (U//FOUO,PR) A value of 0 indicates that no entry has been
             changed since the agent initialized."
        ::= { altasecHv4MgmtRemote 9 }

altasecHv4MgmtRemoteAddressTable OBJECT-TYPE
        SYNTAX          SEQUENCE OF AltasecHv4MgmtRemoteAddressEntry
        MAX-ACCESS      not-accessible
        STATUS          current
        DESCRIPTION
            "(U//FOUO,PR) A table containing a list of networks that are 
             allowed to remotely manage this HAIPE. Note that networks 
             must be distinct (i.e. An Entry within this table cannot be 
             a sub net of another entry)."
        ::= { altasecHv4MgmtRemote 10 }

altasecHv4MgmtRemoteAddressEntry OBJECT-TYPE
        SYNTAX          AltasecHv4MgmtRemoteAddressEntry
        MAX-ACCESS      not-accessible
        STATUS          current
        DESCRIPTION
            "(U//FOUO,PR) A row defining the IP configuration for a remote management
             network."
        INDEX   { altasecHv4MgmtRemoteAddressType,
                  altasecHv4MgmtRemoteAddressStart }
        ::= { altasecHv4MgmtRemoteAddressTable 1 }

AltasecHv4MgmtRemoteAddressEntry ::= SEQUENCE
    {
        altasecHv4MgmtRemoteAddressType            IPAddressType,
        altasecHv4MgmtRemoteAddressStart           IPAddress,
        altasecHv4MgmtRemoteAddressPrefixLength    Unsigned32,
        altasecHv4MgmtRemoteAddressLabel           OCTET STRING,
        altasecHv4MgmtRemoteAddressRowStatus       RowStatus
    }

altasecHv4MgmtRemoteAddressType     OBJECT-TYPE
        SYNTAX             IPAddressType
        MAX-ACCESS         read-create
        STATUS             current
        DESCRIPTION
            "(U//FOUO,PR) The Internet address type for this remote management 
             network."
        DEFVAL { ipv4 }
        ::= { altasecHv4MgmtRemoteAddressEntry 1 }

altasecHv4MgmtRemoteAddressStart         OBJECT-TYPE
        SYNTAX             IPAddress (SIZE (4|16))
        MAX-ACCESS         read-create
        STATUS             current
        DESCRIPTION
            "(U//FOUO,PR) The starting IP address for the remote management 
             network."
        ::= { altasecHv4MgmtRemoteAddressEntry 2 }
        
altasecHv4MgmtRemoteAddressPrefixLength         OBJECT-TYPE
        SYNTAX             Unsigned32 (0..128)
        MAX-ACCESS         read-create
        STATUS             current
        DESCRIPTION
            "(U//FOUO,PR) The prefix length for this remote network."
        ::= { altasecHv4MgmtRemoteAddressEntry 3 }

altasecHv4MgmtRemoteAddressLabel              OBJECT-TYPE
        SYNTAX             OCTET STRING (SIZE(1..32))
        MAX-ACCESS         read-create
        STATUS             current
        DESCRIPTION
            "(U//FOUO,PR) An administratively assigned label identifying 
             this entry."
        ::= { altasecHv4MgmtRemoteAddressEntry 4 }
        
altasecHv4MgmtRemoteAddressRowStatus         OBJECT-TYPE
        SYNTAX             RowStatus
        MAX-ACCESS         read-create
        STATUS             current
        DESCRIPTION
            "(U//FOUO,PR) Row status for the Remote Management entry."
        ::= { altasecHv4MgmtRemoteAddressEntry 5 }

-- *************************************************
-- Chassis Temperatures.

altasecHv4Temperature1           OBJECT-TYPE
        SYNTAX                   Integer32(-1289..1279)
        UNITS                    "tenths of degrees Celsius"
        MAX-ACCESS               read-only
        STATUS                   current
        DESCRIPTION
            "(U//FOUO,PR) Chassis Temperature - top front, in tenths of degrees
             centigrade."
        ::= { altasecHv4MgmtTemps 1 }

altasecHv4Temperature2           OBJECT-TYPE
        SYNTAX                   Integer32(-1289..1279)
        UNITS                    "tenths of degrees Celsius"
        MAX-ACCESS               read-only
        STATUS                   current
        DESCRIPTION
            "(U//FOUO,PR) Chassis Temperature - top back, in tenths of degrees
             Celsius."
        ::= { altasecHv4MgmtTemps 2 }

altasecHv4Temperature3           OBJECT-TYPE
        SYNTAX                   Integer32(-1289..1279)
        UNITS                    "tenths of degrees Celsius"
        MAX-ACCESS               read-only
        STATUS                   current
        DESCRIPTION
            "(U//FOUO,PR) Chassis Temperature - bottom front, in tenths of
             degrees Celsius."
        ::= { altasecHv4MgmtTemps 3 }

altasecHv4Temperature4           OBJECT-TYPE
        SYNTAX                   Integer32(-1289..1279)
        UNITS                    "tenths of degrees Celsius"
        MAX-ACCESS               read-only
        STATUS                   current
        DESCRIPTION
            "(U//FOUO,PR) Chassis Temperature - bottom back, in tenths of
             degrees Celsius."
        ::= { altasecHv4MgmtTemps 4 }
        
altasecHv4TempAutoShutdown       OBJECT-TYPE
        SYNTAX                   TruthValue
        MAX-ACCESS               read-write
        STATUS                   current
        DESCRIPTION
            "(U//FOUO,PR) If enabled, the KG-250X will automatically shut itself
             down when reaching the maximum operating temperature for one of its 
             four temperature sensors. This is a safety feature to prevent extreme 
             temperature conditions from possibly causing permanent damage to the 
             device.  The maximum operating temperatures for the four sensors are 
             93C, 97C, 95C, and 95C respectively."
        DEFVAL { true }             
        ::= { altasecHv4MgmtTemps 5 }     

-- *************************************************
-- Signature Download.

altasecHv4SoftwareSignatureDownloadAdminStatus OBJECT-TYPE
        SYNTAX          INTEGER
                        {
                           downloadSignature(1),
                           executeSignature(2),
                           deleteSignature(3),
                           allowSignatureDownloadAction(4)
                        }
        MAX-ACCESS      read-write
        STATUS          current
        DESCRIPTION
            "(U//FOUO,PR) Software Signature File Download Admin State. It
             mirrors the purpose of hFirmwareDownloadAdminStatus in the HAIPE
             Management MIB which is used to control Firmware Download."
        ::= { altasecHv4MgmtSigDL 1 }

altasecHv4SoftwareSignatureDownloadOperStatus  OBJECT-TYPE
        SYNTAX          INTEGER
                        {
                           noPendingOperation(0),
                           downloadInProgress(1),
                           downloadComplete(2),
                           downloadFailed(3),
                           executeInProgress(4),
                           executeComplete(5),
                           executeFailed(6),
                           deleteInProgress(7),
                           deleteComplete(8),
                           deleteFailed(9)
                        }
        MAX-ACCESS      read-only
        STATUS          current
        DESCRIPTION
            "(U//FOUO,PR) Software Signature File Download Operational State. It
             mirrors the purpose of hFirmwareDownloadOperStatus in the HAIPE
             Management MIB which is used to check the status of a Firmware
             Download."
        ::= { altasecHv4MgmtSigDL 2 }

altasecHv4SoftwareSignatureDownloadResidentId  OBJECT-TYPE
        SYNTAX                                 OCTET STRING (SIZE(1..256))
        MAX-ACCESS                             read-only
        STATUS                                 current
        DESCRIPTION
            "(U//FOUO,PR) Software Signature currently loaded."
        ::= { altasecHv4MgmtSigDL 3 }

-- *************************************************
-- Software Download (SWDL)

altasecHv4FwDwnldServerTable  OBJECT-TYPE
    SYNTAX                    SEQUENCE OF AltasecHv4FwDwnldServerTableEntry
    MAX-ACCESS                not-accessible
    STATUS                    current
    DESCRIPTION
        "(U//FOUO) The table contains information about the software download (SWDL) IWKS file.  
        This table augments the HAIPE Download Server Table "
    ::= { altasecHv4MgmtIwks 1 }

altasecHv4FwDwnldServerTableEntry  OBJECT-TYPE
    SYNTAX            AltasecHv4FwDwnldServerTableEntry
    MAX-ACCESS        not-accessible
    STATUS            current
    DESCRIPTION
        "(U//FOUO) A row describing the particular information associated with
         the SWDL IWKS file."
        AUGMENTS   { hFwDwnldServerTableEntry }
    ::= { altasecHv4FwDwnldServerTable 1 }

AltasecHv4FwDwnldServerTableEntry ::= SEQUENCE
    {
        altasecHv4IwksDwnldFileName          SnmpAdminString, 
        altasecHv4IwksDwnldFilePath          SnmpAdminString                       
    }

altasecHv4IwksDwnldFileName  OBJECT-TYPE
    SYNTAX            SnmpAdminString
    MAX-ACCESS        read-write
    STATUS            current
    DESCRIPTION         
        "(U//FOUO) The filename of the IWKS file associated with an image."             
        ::= { altasecHv4FwDwnldServerTableEntry 2 }
        
 altasecHv4IwksDwnldFilePath  OBJECT-TYPE
    SYNTAX            SnmpAdminString
    MAX-ACCESS        read-write
    STATUS            current
    DESCRIPTION         
        "(U//FOUO) The URI to the path of the IWKS file associated with an image.
         (U//FOUO) At this time, devices only support URIs containing IP addresses."              
        ::= { altasecHv4FwDwnldServerTableEntry 3 }


-- *************************************************
-- Session Management.

altasecHv4MgmtMaxSessions OBJECT-TYPE
        SYNTAX            Unsigned32(1..5)
        MAX-ACCESS        read-write
        STATUS            current
        DESCRIPTION
            "(U//FOUO,PR) The maximum allowed open HMI sessions.  
            0 is unlimited."
        ::= { altasecHv4MgmtSession 1 }
      
altasecHv4MgmtOneSessionPerUser OBJECT-TYPE
        SYNTAX                  TruthValue
        MAX-ACCESS              read-write
        STATUS                  current
        DESCRIPTION
            "(U//FOUO,PR) Only allow one open HMI session per user."
        ::= { altasecHv4MgmtSession 2 }

altasecHv4MgmtInactiveSeconds   OBJECT-TYPE
        SYNTAX                  Unsigned32(60..7200)
        MAX-ACCESS              read-write
        STATUS                  current
        DESCRIPTION
            "(U//FOUO,PR) Inactivity session timeout in seconds."
        ::= { altasecHv4MgmtSession 3 }

    
-- *************************************************
-- CIK Management.

altasecHv4MgmtSuiteOfOperation  OBJECT-TYPE
        SYNTAX                  BITS { unknown(0),
                                       suiteA(1),
                                       suiteB(2)
                                        }
        MAX-ACCESS              read-only
        STATUS                  current
        DESCRIPTION
            "(U//FOUO,PR) The current Suite of Operation. If an operational CIK
             is not inserted, the value of this object is unknown(0)."
        ::= { altasecHv4MgmtCIK 1 }

altasecHv4SecurityLevels  OBJECT-TYPE
        SYNTAX BITS { unclassified(0), restricted(1),
                      confidential(2), secret(3), topSecret(4) }
        MAX-ACCESS              read-only
        STATUS                  current
        DESCRIPTION
            "(U//FOUO,PR) The security levels that this device is currently 
             operating at."
        ::= { altasecHv4MgmtCIK 2 }

altasecHv4CIKTable OBJECT-TYPE
        SYNTAX                  SEQUENCE OF AltasecHv4CIKTableEntry
        MAX-ACCESS              not-accessible
        STATUS                  current
        DESCRIPTION
            "(U//FOUO,PR) Manage the currently inserted CIK"
        ::= { altasecHv4MgmtCIK 3 }

altasecHv4CIKTableEntry OBJECT-TYPE
        SYNTAX                  AltasecHv4CIKTableEntry
        MAX-ACCESS              not-accessible
        STATUS                  current
        DESCRIPTION
            "(U//FOUO,PR) A row describing a particular CIK."
        INDEX { altasecHv4CIKTableIndex }
        ::= { altasecHv4CIKTable 1 }

AltasecHv4CIKTableEntry ::= SEQUENCE
    {
       altasecHv4CIKTableIndex               Unsigned32,
       altasecHv4CIKTableLabel               SnmpAdminString,
       altasecHv4CIKTableClassification      INTEGER,
       altasecHv4CIKTableCOI                 OCTET STRING,
       altasecHv4CIKTableSuite               INTEGER, 
       altasecHv4CIKTableIwksServer          SnmpAdminString,
       altasecHv4CIKTableIwksFile            SnmpAdminString,
       altasecHv4CIKTableProvisionCIK        TruthValue
    }

altasecHv4CIKTableIndex OBJECT-TYPE
       SYNTAX                   Unsigned32
       MAX-ACCESS               not-accessible
       STATUS                   current
       DESCRIPTION
           "(U//FOUO) A unique numeric index that identifies this CIK."
       ::= { altasecHv4CIKTableEntry 1 }

altasecHv4CIKTableLabel OBJECT-TYPE
       SYNTAX                   SnmpAdminString
       MAX-ACCESS               read-create
       STATUS                   current
       DESCRIPTION
           "(U//FOUO) The label for the CIK to be provisioned"
       ::= { altasecHv4CIKTableEntry 2 }

altasecHv4CIKTableClassification OBJECT-TYPE
       SYNTAX                    INTEGER  { unclassified(0), restricted(1),
                      confidential(2), secret(3), topSecret(4) }
       MAX-ACCESS                read-create
       STATUS                    current
       DESCRIPTION
           "(U//FOUO) The classification for which the CIK will be valid. Implementations
            may restrict values for this column to classifications that are allowed by the
            security doctrine of the device.

            (U//FOUO) Agents not supporting the assignment of a particular usage type should
            return a wrongValue SNMP exception"
       ::= { altasecHv4CIKTableEntry 3 }


altasecHv4CIKTableCOI OBJECT-TYPE
       SYNTAX                     OCTET STRING
       MAX-ACCESS                 read-create
       STATUS                     current
       DESCRIPTION
           "(U//FOUO) The Modulus ID of the DePAC/COI to use for this CIK"
       ::= { altasecHv4CIKTableEntry 4 }

altasecHv4CIKTableSuite OBJECT-TYPE
       SYNTAX                     INTEGER { unknown(0),
                                            suiteA(1),
                                            suiteB(2)
                                          }

       MAX-ACCESS                 read-create
       STATUS                     current
       DESCRIPTION
           "(U//FOUO) The Suite to use for this CIK"
       ::= { altasecHv4CIKTableEntry 5 }

altasecHv4CIKTableIwksServer OBJECT-TYPE
       SYNTAX                    SnmpAdminString
       MAX-ACCESS                read-create
       STATUS                    current
       DESCRIPTION
           "(U//FOUO) The transfer method and server IP URI of the IWKS file with which
            the CIK will be provisioned.

            (U//FOUO) Agents not supporting the assignment of a particular usage
            type should return a wrongValue SNMP exception"
       ::= { altasecHv4CIKTableEntry 6 }

altasecHv4CIKTableIwksFile OBJECT-TYPE
       SYNTAX                    SnmpAdminString
       MAX-ACCESS                read-create
       STATUS                    current
       DESCRIPTION
           "(U//FOUO) The file path and filename of the IWKS file with which
            the CIK will be provisioned.

            (U//FOUO) Agents not supporting the assignment of a particular usage
            type should return a wrongValue SNMP exception"
       ::= { altasecHv4CIKTableEntry 7 }

altasecHv4CIKTableProvisionCIK OBJECT-TYPE
       SYNTAX                     TruthValue
       MAX-ACCESS                 read-create
       STATUS                     current
       DESCRIPTION
            "(U//FOUO) The status of the row by which new entries may be created"
       ::= { altasecHv4CIKTableEntry 8 }
        
-- *************************************************
-- TFTP Management.

altasecHv4TFTPMaximumFileTransferSize    OBJECT-TYPE
       SYNTAX                            Unsigned32(0..16777216)
       UNITS                             "kilobytes"
       MAX-ACCESS                        read-write
       STATUS                            current 
       DESCRIPTION
           "(U//FOUO) The maximum file transfer size allowed for
           firmware TFTP downloads."
       REFERENCE "RFC 2349"
       ::= { altasecHv4MgmtTFTP 1 }

-- *************************************************
-- Heartbeat Management.

altasecHv4MgmtHbLastIP          OBJECT-TYPE
       SYNTAX                   OCTET STRING
       MAX-ACCESS               read-only
       STATUS                   current 
       DESCRIPTION
           "(U//FOUO) The IP address of the last remote manager that
           sent a heartbeat to this device."
       ::= { altasecHv4MgmtHB 1 }
       
altasecHv4MgmtHbTimeFirst       OBJECT-TYPE
       SYNTAX                   DateAndTime
       MAX-ACCESS               read-only
       STATUS                   current 
       DESCRIPTION
           "(U//FOUO) The Date and time the first heartbeat was
           received by by this device."
       ::= { altasecHv4MgmtHB 2 }
       
altasecHv4MgmtHbTimeSinceLast	OBJECT-TYPE
       SYNTAX                   Unsigned32
       UNITS					"seconds"
       MAX-ACCESS               read-only
       STATUS                   current 
       DESCRIPTION
           "(U//FOUO) The amount of time that has elapsed since 
           the last heartbeat message was received."
       ::= { altasecHv4MgmtHB 3 }
       
altasecHv4MgmtHbTotalCount      OBJECT-TYPE
       SYNTAX                   Unsigned32
       MAX-ACCESS               read-only
       STATUS                   current 
       DESCRIPTION
           "(U//FOUO) The total number of heartbeats that have been
           received since the time given in altasecHv4MgmtHbTimeFirst."
       ::= { altasecHv4MgmtHB 4 }
       
altasecHv4MgmtHbAvgTimeBtwn     OBJECT-TYPE
       SYNTAX                   Unsigned32
       UNITS					"seconds"
       MAX-ACCESS               read-only
       STATUS                   current 
       DESCRIPTION
           "(U//FOUO) The average amount of time elapsed between 2 
           heartbeat messages."
       ::= { altasecHv4MgmtHB 5 }
       
altasecHv4MgmtHbMaxTimeBtwn     OBJECT-TYPE
       SYNTAX                   Unsigned32
       UNITS					"seconds"
       MAX-ACCESS               read-only
       STATUS                   current 
       DESCRIPTION
           "(U//FOUO) The largest amount of time elapsed between any 
           2 heartbeat messages."
       ::= { altasecHv4MgmtHB 6 }
       
-- *************************************************
-- Restore Default Settings Scalars.

altasecHv4RDICMP            OBJECT-TYPE
    SYNTAX                  TruthValue
    MAX-ACCESS              read-write
    STATUS                  current
    DESCRIPTION
        "(U//FOUO,PR) Restore default ICMP Settings."
        ::= { altasecHv4MgmtRestoreDefault 1 }

altasecHv4RDNeighborDisc    OBJECT-TYPE
    SYNTAX                  TruthValue
    MAX-ACCESS              read-write
    STATUS                  current
    DESCRIPTION
        "(U//FOUO,PR) Restore default Neighbor Discovery Settings."
        ::= { altasecHv4MgmtRestoreDefault 2 }

altasecHv4RDTrafficSettings OBJECT-TYPE
    SYNTAX                  TruthValue
    MAX-ACCESS              read-write
    STATUS                  current
    DESCRIPTION
        "(U//FOUO,PR) Restore default Traffic Settings."
        ::= { altasecHv4MgmtRestoreDefault 3 }

altasecHv4RDSASettings      OBJECT-TYPE
    SYNTAX                  TruthValue
    MAX-ACCESS              read-write
    STATUS                  current
    DESCRIPTION
        "(U//FOUO,PR) Restore default SA Settings."
        ::= { altasecHv4MgmtRestoreDefault 4 }
        
altasecHv4RDAutoSAExSettings OBJECT-TYPE
    SYNTAX                   TruthValue
    MAX-ACCESS               read-write
    STATUS                   current
    DESCRIPTION
        "(U//FOUO,PR) Restore default Automated SA Exchange Settings."
        ::= { altasecHv4MgmtRestoreDefault 5 }
        
-- **********************************************************************
-- Traffic Protection
-- **********************************************************************
       
-- =======================
-- Global Traffic Protection Scalars
-- =======================

altasecHv4ESPv1PSEQNMultiplier OBJECT-TYPE
    SYNTAX                     OCTET STRING (SIZE(8))
    MAX-ACCESS                 read-write
    STATUS                     current
    DESCRIPTION
        "(U//FOUO,PR) Global SA setting that allows the ESPv1 PSEQN multiplier
         to change to a user-desired value.  This value is a 64-bit unsigned
         integer represented here as an 8-octet string.  This serves as a
         straightforward way to meet requirements while still keeping
         operability with older ViaSat INEs."
        ::= { altasecHv4TPGlobalScalars 1 }

altasecHv4ESPv3PSEQNMultiplier OBJECT-TYPE
    SYNTAX                     OCTET STRING (SIZE(8))
    MAX-ACCESS                 read-write
    STATUS                     current
    DESCRIPTION
        "(U//FOUO,PR) Global SA setting that allows the ESPv3 PSEQN multiplier
         to change to a user-desired value.  This value is a 64-bit unsigned
         integer represented here as an 8-octet string.  This serves as a
         straightforward way to meet requirements while still keeping
         operability with older ViaSat INEs."
        ::= { altasecHv4TPGlobalScalars 2 }
        
altasecHv4GCM0Support       OBJECT-TYPE
    SYNTAX                  TruthValue
    MAX-ACCESS              read-write
    STATUS                  current
    DESCRIPTION
        "(U//FOUO,PR) Global SA setting that enables or disables support for
         GCM0 including key sequences, tranform and security policy for use
         with Transport SAs."
        ::= { altasecHv4TPGlobalScalars 3 }
        
altasecHv4VendorModeSupport OBJECT-TYPE
    SYNTAX                  TruthValue
    MAX-ACCESS              read-write
    STATUS                  current
    DESCRIPTION
        "(U//FOUO,PR) Global SA setting that, when enabled, the KG-250 will 
         send an AltaSec Vendor Payload during the IKE exchange with another 
         HAIPE device. The payload contains the ViaSat product type, software 
         version, and features or capabilities. The payload is sent in IKE 
         messages 1 and 2. The vendor information received by the KG-250 during 
         an IKE negotiation is displayed on the Security Associations page."
        ::= { altasecHv4TPGlobalScalars 4 }
        
altasecHv4TunnelPreferredFragmentationSide  OBJECT-TYPE
        SYNTAX                              HaipeDeviceSide
        MAX-ACCESS                          read-write
        STATUS                              current
        DESCRIPTION
            "(U//FOUO,PR) The desired Fragmentation Side Setting (pt(1) or
             ct(2)) for SAs.

             (U//FOUO,PR) Note: This object is always writeable and contains the
             user setting to be applied should FPL be disabled."
        ::= { altasecHv4TPGlobalScalars 5 }   
        
altasecHv4BMEnabled OBJECT-TYPE
    SYNTAX                  TruthValue
    MAX-ACCESS              read-write
    STATUS                  current
    DESCRIPTION
        "(U//FOUO,PR) Global SA setting that enables disables global bandwidth
         management."
        ::= { altasecHv4TPGlobalScalars 6 }
        
altasecHv4ManSaNextIndex  OBJECT-TYPE
        SYNTAX            Unsigned32
        MAX-ACCESS        read-only
        STATUS            current
        DESCRIPTION
            "(U//FOUO,PR) Index at which next Manual SA entry can be added."
        ::= { altasecHv4TPGlobalScalars 7 }
                
-- =======================
-- Table of Manual SA Management
-- =======================

altasecHv4ManualSADTable   OBJECT-TYPE
        SYNTAX             SEQUENCE OF AltasecHv4ManualSADEntry
        MAX-ACCESS         not-accessible
        STATUS             current
        DESCRIPTION
            "(U//FOUO,PR) This table supplements the information provided in the
             corresponding hTPSATable in the HAIPE-TRAFFIC-PROTECTION-MIB
             with additional proprietary values. The hTPSAIndex column is
             the only index for this table and references its parent
             entry in the aforementioned hTPSATable.

             (U//FOUO,PR) As part of the proprietary extension, configuration
             items that affect the behavior of the SAs may be modified, even
             if the SA is currently active."
        ::= { altasecHv4ManualSAD 3 }

altasecHv4ManualSADEntry        OBJECT-TYPE
        SYNTAX          AltasecHv4ManualSADEntry
        MAX-ACCESS      not-accessible
        STATUS          current
        DESCRIPTION
            "(U//FOUO,PR) A row describing the additional proprietary
             information about current Security Associations (SA's) that
             are not included in the HAIPE hTPSATable."
        AUGMENTS   { hManualSADTableEntry }
        ::= { altasecHv4ManualSADTable 1 }

AltasecHv4ManualSADEntry ::= SEQUENCE
    {
        altasecHv4ManualSADSCPCopyValue                      OCTET STRING,
        altasecHv4ManualSAECNValue                           OCTET STRING,
        altasecHv4ManualSAECNCopyValue                       OCTET STRING,
        altasecHv4ManualSATTLHopLimit                        INTEGER,
        altasecHv4ManualSAName                               SnmpAdminString,
        altasecHv4ManualSAMulticastBypassMode                TruthValue,
        altasecHv4ManualSAMulticastResetSource               TruthValue,
        altasecHv4ManualSAConnectionStatus                   INTEGER,
        altasecHv4ManualSAPMTU                               Unsigned32,
        altasecHv4ManualSATransportPacketsDropped            Counter64,
        altasecHv4ManualSATransportFragmentedPacketsDropped  Counter64,
        altasecHv4ManualSATransportSourceAddress             IPAddress
    }

altasecHv4ManualSADSCPCopyValue  OBJECT-TYPE
    SYNTAX                OCTET STRING (SIZE (1))
    MAX-ACCESS            read-write
    STATUS                current
    DESCRIPTION
        "(U//FOUO,PR) The Differentiated Service Code Points (DSCP)
         value for this SA.

         (U//FOUO,PR) The use of this value is dependent on the value
         of the hTPSADSCP column in its parent hTPSATable row being
         set to set(1). Any other values (acceptlist(3)) will result in
         this value being ignored.

         (U//FOUO,PR) If the hTPSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hTPSADSCPValue column."
    DEFVAL { '00'h }
    ::= { altasecHv4ManualSADEntry 2 }

altasecHv4ManualSAECNValue  OBJECT-TYPE
    SYNTAX           OCTET STRING (SIZE (1))
    MAX-ACCESS       read-write
    STATUS           current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  The
         ECN value garnered from these lower/right-most 2 of the octet
         are placed within the outgoing packet's Explicit Congestion
         Notification (ECN) header value."
    DEFVAL { '00'h }
    ::= { altasecHv4ManualSADEntry 3 }

altasecHv4ManualSAECNCopyValue  OBJECT-TYPE
    SYNTAX               OCTET STRING (SIZE (1))
    MAX-ACCESS           read-write
    STATUS               current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  Any
         bits set in these lower/right-most 2 of the octet will indicate
         that those bits be copied from the incoming packet's Explicit
         Congestion Notification (ECN) header value to the outgoing
         packet. Any bits set for this value effectively overrides, to
         copy, those set in the above altaTPSAECNValue column."
    DEFVAL { '00'h }
    ::= { altasecHv4ManualSADEntry 4 }

altasecHv4ManualSATTLHopLimit  OBJECT-TYPE
    SYNTAX              INTEGER (0..255)
    MAX-ACCESS          read-write
    STATUS              current
    DESCRIPTION
        "(U//FOUO,PR) The TTL or Hop Limit value for a packet associated with
         this SA. If this value has not been set when an internal SA goes
         active, it will be overridden with the current box-level default for
         the appropriate address type, from either the hIfv4TTL or hIfv6HopLimit
         objects in the HAIPE-NETWORKING-MIB.
         
         If this value is set to 0, the TTL or Hop Limit will be copied
         from the PT packet header into the CT packet header and
         decremented by one."
    ::= { altasecHv4ManualSADEntry 5 }

altasecHv4ManualSAName      OBJECT-TYPE
    SYNTAX           SnmpAdminString
    MAX-ACCESS       read-only
    STATUS           current
    DESCRIPTION
        "(U//FOUO,PR) The device name given to the internal SA device, logically
         grouping two or four entries in the table. If the SA is not currently
         active, it will not have a device name and return a zero length
         string. Device names themselves are unique to the logically linked
         SPI values they identify."
    ::= { altasecHv4ManualSADEntry 6 }

altasecHv4ManualSAMulticastBypassMode  OBJECT-TYPE
    SYNTAX                      TruthValue
    MAX-ACCESS                  read-write
    STATUS                      current
    DESCRIPTION
        "(U//FOUO,PR) The Multicast Bypass/Host support method for this specific
          SA. This value is only available should the SA be multicast."
    DEFVAL { false }
    ::= { altasecHv4ManualSADEntry 7 }

altasecHv4ManualSAMulticastResetSource  OBJECT-TYPE
    SYNTAX                       TruthValue
    MAX-ACCESS                   read-write
    STATUS                       current
    DESCRIPTION
        "(U//FOUO,PR) Causes decrypted multicast traffic to have the HAIPE's PT
         IP address as its source address, instead of the multicast sender's
         original IP address."
    DEFVAL { false }
    ::= { altasecHv4ManualSADEntry 8 }

altasecHv4ManualSAConnectionStatus  OBJECT-TYPE
    SYNTAX                   INTEGER { unknown(0), up(1), down(2),
                                       noKey(3), noRoute(4), noPolicy(5),
                                       notReachable(6), needSuiteA(7),
                                       needSuiteB(8), invalidKey(9),
                                       noSPI(10), noGCM0(11) }
    MAX-ACCESS               read-write
    STATUS                   current
    DESCRIPTION
        "(U//FOUO,PR) The status of this SA with regards to its ability to
         pass traffic.

         (U//FOUO,PR) This object may be used to manually initiate HIKE, for
         HIKE SAs, by setting this object to 'up'. Similarly a connected HIKE SA
         can be disconnected by setting this object to 'down'. Any other setting
         will result in a wrongValue error. An attempt to modify this setting
         for an Inactive or non-HIKE SA will result in an inconsistentValue
         error.

         (U//FOUO,PR) If FPL is enabled, all Transport SAs for that respective
         interface (IPv4 and/or IPv6) will have a value of 'down', unless the
         Transport's Transform is not supported in the current suite."
    ::= { altasecHv4ManualSADEntry 9 }

altasecHv4ManualSAPMTU             OBJECT-TYPE
    SYNTAX                                     Unsigned32
    MAX-ACCESS                                 read-only
    STATUS		                       current
    DESCRIPTION
        "(U//FOUO) The PMTU value for this SA."
    ::= { altasecHv4ManualSADEntry 10 }

altasecHv4ManualSATransportPacketsDropped      OBJECT-TYPE
    SYNTAX                                     Counter64
    MAX-ACCESS                                 read-only
    STATUS                                     current
    DESCRIPTION
        "(U//FOUO,PR) For Transport SAs, if the PT packet length is greater than
         the CT MTU then the packet will be dropped since fragmentation cannot
         occur. This object serves as a counter to indicate the number of
         packets that have been dropped on this SA (the grouped set of SA
         entries by altasecHv4ManualSAName) due to packet length since the last reboot.
         Tunnel SAs and non-active Transport SAs do not have this object."
    ::= { altasecHv4ManualSADEntry 11 }

altasecHv4ManualSATransportFragmentedPacketsDropped OBJECT-TYPE
    SYNTAX                                          Counter64
    MAX-ACCESS                                      read-only
    STATUS                                          current
    DESCRIPTION
        "(U//FOUO,PR) For Transport SAs, packets that have already been
         fragmented on the PT network cannot be sent to the CT network. This
         object serves as a counter to indicate the number of packets that have
         been dropped on this SA (the grouped set of SA entries by
         altasecHv4ManualSAName) due to PT-side fragmentation since the last reboot.
         Tunnel SAs and non-active Transport SAs do not have this object."
    ::= { altasecHv4ManualSADEntry 12 }
    
altasecHv4ManualSATransportSourceAddress       OBJECT-TYPE
    SYNTAX                                     IPAddress
    MAX-ACCESS                                 read-write
    STATUS                                     current
    DESCRIPTION
        "(U//FOUO,PR) For Transport SAs, this provides the Unicast PT Source 
         Address."
    ::= { altasecHv4ManualSADEntry 13 }

-- =======================
-- Table of IKEv1 SA Management
-- =======================

altasecHv4IKEv1SADTable      OBJECT-TYPE
        SYNTAX             SEQUENCE OF AltasecHv4IKEv1SADEntry
        MAX-ACCESS         not-accessible
        STATUS             current
        DESCRIPTION
            "(U//FOUO,PR) This table supplements the information provided in the
             corresponding hTPSATable in the HAIPE-TRAFFIC-PROTECTION-MIB
             with additional proprietary values. The hTPSAIndex column is
             the only index for this table and references its parent
             entry in the aforementioned hTPSATable.

             (U//FOUO,PR) As part of the proprietary extension, configuration
             items that affect the behavior of the SAs may be modified, even
             if the SA is currently active."
        ::= { altasecHv4IKEv1SAD 3 }

altasecHv4IKEv1SADEntry        OBJECT-TYPE
        SYNTAX          AltasecHv4IKEv1SADEntry
        MAX-ACCESS      not-accessible
        STATUS          current
        DESCRIPTION
            "(U//FOUO,PR) A row describing the additional proprietary
             information about current Security Associations (SA's) that
             are not included in the HAIPE hTPSATable."
        AUGMENTS   { hIKEv1SADTableEntry }
        ::= { altasecHv4IKEv1SADTable 1 }

AltasecHv4IKEv1SADEntry ::= SEQUENCE
    {
        altasecHv4IKEv1SADSCPCopyValue                      OCTET STRING,
        altasecHv4IKEv1SAECNValue                           OCTET STRING,
        altasecHv4IKEv1SAECNCopyValue                       OCTET STRING,
        altasecHv4IKEv1SATTLHopLimit                        INTEGER,
        altasecHv4IKEv1SAName                               SnmpAdminString,
        altasecHv4IKEv1SAMulticastBypassMode                TruthValue,
        altasecHv4IKEv1SAMulticastResetSource               TruthValue,
        altasecHv4IKEv1SAConnectionStatus                   INTEGER,
        altasecHv4IKEv1SAPMTU                               Unsigned32,
        altasecHv4IKEv1SATransportPacketsDropped            Counter64,
        altasecHv4IKEv1SATransportFragmentedPacketsDropped  Counter64,
        altasecHv4IKEv1SATransportSourceAddress             IPAddress
    }

altasecHv4IKEv1SADSCPCopyValue  OBJECT-TYPE
    SYNTAX                OCTET STRING (SIZE (1))
    MAX-ACCESS            read-write
    STATUS                current
    DESCRIPTION
        "(U//FOUO,PR) The Differentiated Service Code Points (DSCP)
         value for this SA.

         (U//FOUO,PR) The use of this value is dependent on the value
         of the hTPSADSCP column in its parent hTPSATable row being
         set to set(1). Any other values (acceptlist(3)) will result in
         this value being ignored.

         (U//FOUO,PR) If the hTPSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hTPSADSCPValue column."
    DEFVAL { '00'h }
    ::= { altasecHv4IKEv1SADEntry 2 }

altasecHv4IKEv1SAECNValue  OBJECT-TYPE
    SYNTAX           OCTET STRING (SIZE (1))
    MAX-ACCESS       read-write
    STATUS           current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  The
         ECN value garnered from these lower/right-most 2 of the octet
         are placed within the outgoing packet's Explicit Congestion
         Notification (ECN) header value."
    DEFVAL { '00'h }
    ::= { altasecHv4IKEv1SADEntry 3 }

altasecHv4IKEv1SAECNCopyValue  OBJECT-TYPE
    SYNTAX               OCTET STRING (SIZE (1))
    MAX-ACCESS           read-write
    STATUS               current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  Any
         bits set in these lower/right-most 2 of the octet will indicate
         that those bits be copied from the incoming packet's Explicit
         Congestion Notification (ECN) header value to the outgoing
         packet. Any bits set for this value effectively overrides, to
         copy, those set in the above altaTPSAECNValue column."
    DEFVAL { '00'h }
    ::= { altasecHv4IKEv1SADEntry 4 }

altasecHv4IKEv1SATTLHopLimit  OBJECT-TYPE
    SYNTAX              INTEGER (0..255)
    MAX-ACCESS          read-write
    STATUS              current
    DESCRIPTION
        "(U//FOUO,PR) The TTL or Hop Limit value for a packet associated with
         this SA. If this value has not been set when an internal SA goes
         active, it will be overridden with the current box-level default for
         the appropriate address type, from either the hIfv4TTL or hIfv6HopLimit
         objects in the HAIPE-NETWORKING-MIB.
         
         If this value is set to 0, the TTL or Hop Limit will be copied
         from the PT packet header into the CT packet header and
         decremented by one."
    ::= { altasecHv4IKEv1SADEntry 5 }

altasecHv4IKEv1SAName      OBJECT-TYPE
    SYNTAX           SnmpAdminString
    MAX-ACCESS       read-only
    STATUS           current
    DESCRIPTION
        "(U//FOUO,PR) The device name given to the internal SA device, logically
         grouping two or four entries in the table. If the SA is not currently
         active, it will not have a device name and return a zero length
         string. Device names themselves are unique to the logically linked
         SPI values they identify."
    ::= { altasecHv4IKEv1SADEntry 6 }

altasecHv4IKEv1SAMulticastBypassMode  OBJECT-TYPE
    SYNTAX                      TruthValue
    MAX-ACCESS                  read-write
    STATUS                      current
    DESCRIPTION
        "(U//FOUO,PR) The Multicast Bypass/Host support method for this specific
          SA. This value is only available should the SA be multicast."
    DEFVAL { false }
    ::= { altasecHv4IKEv1SADEntry 7 }

altasecHv4IKEv1SAMulticastResetSource  OBJECT-TYPE
    SYNTAX                       TruthValue
    MAX-ACCESS                   read-write
    STATUS                       current
    DESCRIPTION
        "(U//FOUO,PR) Causes decrypted multicast traffic to have the HAIPE's PT
         IP address as its source address, instead of the multicast sender's
         original IP address."
    DEFVAL { false }
    ::= { altasecHv4IKEv1SADEntry 8 }

altasecHv4IKEv1SAConnectionStatus  OBJECT-TYPE
    SYNTAX                   INTEGER { unknown(0), up(1), down(2),
                                       noKey(3), noRoute(4), noPolicy(5),
                                       notReachable(6), needSuiteA(7),
                                       needSuiteB(8), invalidKey(9),
                                       noSPI(10), noGCM0(11) }
    MAX-ACCESS               read-write
    STATUS                   current
    DESCRIPTION
        "(U//FOUO,PR) The status of this SA with regards to its ability to
         pass traffic.
         
         (U//FOUO,PR) If FPL is enabled, all Transport SAs for that respective
         interface (IPv4 and/or IPv6) will have a value of 'down', unless the
         Transport's Transform is not supported in the current suite."
    ::= { altasecHv4IKEv1SADEntry 9 }

altasecHv4IKEv1SAPMTU             OBJECT-TYPE
    SYNTAX                                     Unsigned32
    MAX-ACCESS                                 read-only
    STATUS		                       current
    DESCRIPTION
        "(U//FOUO) The PMTU value for this SA."
    ::= { altasecHv4IKEv1SADEntry 10 }

altasecHv4IKEv1SATransportPacketsDropped             OBJECT-TYPE
    SYNTAX                                     Counter64
    MAX-ACCESS                                 read-only
    STATUS                                     current
    DESCRIPTION
        "(U//FOUO,PR) For Transport SAs, if the PT packet length is greater than
         the CT MTU then the packet will be dropped since fragmentation cannot
         occur. This object serves as a counter to indicate the number of
         packets that have been dropped on this SA (the grouped set of SA
         entries by altasecHv4IKEv1SAName) due to packet length since the last reboot.
         Tunnel SAs and non-active Transport SAs do not have this object."
    ::= { altasecHv4IKEv1SADEntry 11 }

altasecHv4IKEv1SATransportFragmentedPacketsDropped   OBJECT-TYPE
    SYNTAX                                     Counter64
    MAX-ACCESS                                 read-only
    STATUS                                     current
    DESCRIPTION
        "(U//FOUO,PR) For Transport SAs, packets that have already been
         fragmented on the PT network cannot be sent to the CT network. This
         object serves as a counter to indicate the number of packets that have
         been dropped on this SA (the grouped set of SA entries by
         altasecHv4IKEv1SAName) due to PT-side fragmentation since the last reboot.
         Tunnel SAs and non-active Transport SAs do not have this object."
    ::= { altasecHv4IKEv1SADEntry 12 }
    
altasecHv4IKEv1SATransportSourceAddress        OBJECT-TYPE
    SYNTAX                                     IPAddress
    MAX-ACCESS                                 read-write
    STATUS                                     current
    DESCRIPTION
        "(U//FOUO,PR) For Transport SAs, this provides the Unicast PT Source 
         Address."
    ::= { altasecHv4IKEv1SADEntry 13 }

-- =======================
-- Table of IKEv2CHILD SA Management
-- =======================

altasecHv4IKEv2CHILDSADTable      OBJECT-TYPE
        SYNTAX             SEQUENCE OF AltasecHv4IKEv2CHILDSADEntry
        MAX-ACCESS         not-accessible
        STATUS             current
        DESCRIPTION
            "(U//FOUO,PR) This table supplements the information provided in the
             corresponding hTPSATable in the HAIPE-TRAFFIC-PROTECTION-MIB
             with additional proprietary values. The hTPSAIndex column is
             the only index for this table and references its parent
             entry in the aforementioned hTPSATable.

             (U//FOUO,PR) As part of the proprietary extension, configuration
             items that affect the behavior of the SAs may be modified, even
             if the SA is currently active."
        ::= { altasecHv4IKEv2CHILDSAD 3 }

altasecHv4IKEv2CHILDSADEntry        OBJECT-TYPE
        SYNTAX          AltasecHv4IKEv2CHILDSADEntry
        MAX-ACCESS      not-accessible
        STATUS          current
        DESCRIPTION
            "(U//FOUO,PR) A row describing the additional proprietary
             information about current Security Associations (SA's) that
             are not included in the HAIPE hTPSATable."
        AUGMENTS   { hIKEv2CHILDSADTableEntry }
        ::= { altasecHv4IKEv2CHILDSADTable 1 }

AltasecHv4IKEv2CHILDSADEntry ::= SEQUENCE
    {
        altasecHv4IKEv2CHILDSADSCPCopyValue                      OCTET STRING,
        altasecHv4IKEv2CHILDSAECNValue                           OCTET STRING,
        altasecHv4IKEv2CHILDSAECNCopyValue                       OCTET STRING,
        altasecHv4IKEv2CHILDSATTLHopLimit                        INTEGER,
        altasecHv4IKEv2CHILDSAName                               SnmpAdminString,
        altasecHv4IKEv2CHILDSAMulticastBypassMode                TruthValue,
        altasecHv4IKEv2CHILDSAMulticastResetSource               TruthValue,
        altasecHv4IKEv2CHILDSAConnectionStatus                   INTEGER,
        altasecHv4IKEv2CHILDSAPMTU                               Unsigned32,
        altasecHv4IKEv2CHILDSATransportPacketsDropped            Counter64,
        altasecHv4IKEv2CHILDSATransportFragmentedPacketsDropped  Counter64,
        altasecHv4IKEv2CHILDSATransportSourceAddress             IPAddress,
        altasecHv4IKEv2CHILDSAPHRDRate                           Unsigned32,
        altasecHv4IKEv2CHILDSAPHRDLimit                          Unsigned32
    }

altasecHv4IKEv2CHILDSADSCPCopyValue  OBJECT-TYPE
    SYNTAX                OCTET STRING (SIZE (1))
    MAX-ACCESS            read-write
    STATUS                current
    DESCRIPTION
        "(U//FOUO,PR) The Differentiated Service Code Points (DSCP)
         value for this SA.

         (U//FOUO,PR) The use of this value is dependent on the value
         of the hTPSADSCP column in its parent hTPSATable row being
         set to set(1). Any other values (acceptlist(3)) will result in
         this value being ignored.

         (U//FOUO,PR) If the hTPSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hTPSADSCPValue column."
    DEFVAL { '00'h }
    ::= { altasecHv4IKEv2CHILDSADEntry 2 }

altasecHv4IKEv2CHILDSAECNValue  OBJECT-TYPE
    SYNTAX           OCTET STRING (SIZE (1))
    MAX-ACCESS       read-write
    STATUS           current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  The
         ECN value garnered from these lower/right-most 2 of the octet
         are placed within the outgoing packet's Explicit Congestion
         Notification (ECN) header value."
    DEFVAL { '00'h }
    ::= { altasecHv4IKEv2CHILDSADEntry 3 }

altasecHv4IKEv2CHILDSAECNCopyValue  OBJECT-TYPE
    SYNTAX               OCTET STRING (SIZE (1))
    MAX-ACCESS           read-write
    STATUS               current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  Any
         bits set in these lower/right-most 2 of the octet will indicate
         that those bits be copied from the incoming packet's Explicit
         Congestion Notification (ECN) header value to the outgoing
         packet. Any bits set for this value effectively overrides, to
         copy, those set in the above altaTPSAECNValue column."
    DEFVAL { '00'h }
    ::= { altasecHv4IKEv2CHILDSADEntry 4 }

altasecHv4IKEv2CHILDSATTLHopLimit  OBJECT-TYPE
    SYNTAX              INTEGER (0..255)
    MAX-ACCESS          read-write
    STATUS              current
    DESCRIPTION
        "(U//FOUO,PR) The TTL or Hop Limit value for a packet associated with
         this SA. If this value has not been set when an internal SA goes
         active, it will be overridden with the current box-level default for
         the appropriate address type, from either the hIfv4TTL or hIfv6HopLimit
         objects in the HAIPE-NETWORKING-MIB.
         
         If this value is set to 0, the TTL or Hop Limit will be copied
         from the PT packet header into the CT packet header and
         decremented by one."
    ::= { altasecHv4IKEv2CHILDSADEntry 5 }

altasecHv4IKEv2CHILDSAName      OBJECT-TYPE
    SYNTAX           SnmpAdminString
    MAX-ACCESS       read-only
    STATUS           current
    DESCRIPTION
        "(U//FOUO,PR) The device name given to the internal SA device, logically
         grouping two or four entries in the table. If the SA is not currently
         active, it will not have a device name and return a zero length
         string. Device names themselves are unique to the logically linked
         SPI values they identify."
    ::= { altasecHv4IKEv2CHILDSADEntry 6 }

altasecHv4IKEv2CHILDSAMulticastBypassMode  OBJECT-TYPE
    SYNTAX                      TruthValue
    MAX-ACCESS                  read-write
    STATUS                      current
    DESCRIPTION
        "(U//FOUO,PR) The Multicast Bypass/Host support method for this specific
          SA. This value is only available should the SA be multicast."
    DEFVAL { false }
    ::= { altasecHv4IKEv2CHILDSADEntry 7 }

altasecHv4IKEv2CHILDSAMulticastResetSource  OBJECT-TYPE
    SYNTAX                       TruthValue
    MAX-ACCESS                   read-write
    STATUS                       current
    DESCRIPTION
        "(U//FOUO,PR) Causes decrypted multicast traffic to have the HAIPE's PT
         IP address as its source address, instead of the multicast sender's
         original IP address."
    DEFVAL { false }
    ::= { altasecHv4IKEv2CHILDSADEntry 8 }

altasecHv4IKEv2CHILDSAConnectionStatus  OBJECT-TYPE
    SYNTAX                   INTEGER { unknown(0), up(1), down(2),
                                       noKey(3), noRoute(4), noPolicy(5),
                                       notReachable(6), needSuiteA(7),
                                       needSuiteB(8), invalidKey(9),
                                       noSPI(10), noGCM0(11) }
    MAX-ACCESS               read-write
    STATUS                   current
    DESCRIPTION
        "(U//FOUO,PR) The status of this SA with regards to its ability to
         pass traffic.

         (U//FOUO,PR) If FPL is enabled, all Transport SAs for that respective
         interface (IPv4 and/or IPv6) will have a value of 'down', unless the
         Transport's Transform is not supported in the current suite."
    ::= { altasecHv4IKEv2CHILDSADEntry 9 }

altasecHv4IKEv2CHILDSAPMTU             OBJECT-TYPE
    SYNTAX                                     Unsigned32
    MAX-ACCESS                                 read-only
    STATUS		                       current
    DESCRIPTION
        "(U//FOUO) The PMTU value for this SA."
    ::= { altasecHv4IKEv2CHILDSADEntry 10 }

altasecHv4IKEv2CHILDSATransportPacketsDropped             OBJECT-TYPE
    SYNTAX                                     Counter64
    MAX-ACCESS                                 read-only
    STATUS                                     current
    DESCRIPTION
        "(U//FOUO,PR) For Transport SAs, if the PT packet length is greater than
         the CT MTU then the packet will be dropped since fragmentation cannot
         occur. This object serves as a counter to indicate the number of
         packets that have been dropped on this SA (the grouped set of SA
         entries by altasecHv4IKEv2CHILDSAName) due to packet length since the last reboot.
         Tunnel SAs and non-active Transport SAs do not have this object."
    ::= { altasecHv4IKEv2CHILDSADEntry 11 }

altasecHv4IKEv2CHILDSATransportFragmentedPacketsDropped   OBJECT-TYPE
    SYNTAX                                     Counter64
    MAX-ACCESS                                 read-only
    STATUS                                     current
    DESCRIPTION
        "(U//FOUO,PR) For Transport SAs, packets that have already been
         fragmented on the PT network cannot be sent to the CT network. This
         object serves as a counter to indicate the number of packets that have
         been dropped on this SA (the grouped set of SA entries by
         altasecHv4IKEv2CHILDSAName) due to PT-side fragmentation since the last reboot.
         Tunnel SAs and non-active Transport SAs do not have this object."
    ::= { altasecHv4IKEv2CHILDSADEntry 12 }
    
altasecHv4IKEv2CHILDSATransportSourceAddress       OBJECT-TYPE
    SYNTAX                                     IPAddress
    MAX-ACCESS                                 read-write
    STATUS                                     current
    DESCRIPTION
        "(U//FOUO,PR) For Transport SAs, this provides the Unicast PT Source 
         Address."
    ::= { altasecHv4IKEv2CHILDSADEntry 13 }

altasecHv4IKEv2CHILDSAPHRDRate OBJECT-TYPE
    SYNTAX     Unsigned32
    MAX-ACCESS read-create
    STATUS     current
    DESCRIPTION
        "(U//FOUO) The setting that determines the rate (in seconds) at which
         Peer HAIPE Reachability Detection (PHRD) messages are transmitted on
         the IKEv2 Child SA; the default value is 0 (decimal).  A value of zero
         (decimal) indicates the disabled PHRD Setting, meaning that PHRD
         messages will not be transmitted."
    DEFVAL{0}
    ::= { altasecHv4IKEv2CHILDSADEntry 14 }

altasecHv4IKEv2CHILDSAPHRDLimit OBJECT-TYPE
    SYNTAX     Unsigned32
    MAX-ACCESS read-create
    STATUS     current
    DESCRIPTION
        "(U//FOUO) Setting that determines the number of successive missed Peer
         HAIPE Reachability Detection (PHRD) responses that will trigger the
         HAIPE to mark the IKEv2 Child SA as UNREACHABLE.  A PHRD response or any
         inbound traffic received on an Inbound IKEv1 SA established with the
         remote HAIPE resets the internal PHRD successive missed counter to its
         initial state.  Note, this column must only exist when the
         hIKEv1ProfilePHRDRate column is set to a non-zero value (decimal)."
    ::= { altasecHv4IKEv2CHILDSADEntry 15 }
    

-- =======================
-- Table of IKEv2IKE SA Management
-- =======================

altasecHv4IKEv2IKESADTable      OBJECT-TYPE
        SYNTAX             SEQUENCE OF AltasecHv4IKEv2IKESADEntry
        MAX-ACCESS         not-accessible
        STATUS             current
        DESCRIPTION
            "(U//FOUO,PR) This table supplements the information provided in the
             corresponding hTPSATable in the HAIPE-TRAFFIC-PROTECTION-MIB
             with additional proprietary values. The hTPSAIndex column is
             the only index for this table and references its parent
             entry in the aforementioned hTPSATable.

             (U//FOUO,PR) As part of the proprietary extension, configuration
             items that affect the behavior of the SAs may be modified, even
             if the SA is currently active."
        ::= { altasecHv4IKEv2IKESAD 3 }

altasecHv4IKEv2IKESADEntry        OBJECT-TYPE
        SYNTAX          AltasecHv4IKEv2IKESADEntry
        MAX-ACCESS      not-accessible
        STATUS          current
        DESCRIPTION
            "(U//FOUO,PR) A row describing the additional proprietary
             information about current Security Associations (SA's) that
             are not included in the HAIPE hTPSATable."
        AUGMENTS   { hIKEv2IKESADTableEntry }
        ::= { altasecHv4IKEv2IKESADTable 1 }

AltasecHv4IKEv2IKESADEntry ::= SEQUENCE
    {
        altasecHv4IKEv2IKESADConnectionStatus                   INTEGER
    }

altasecHv4IKEv2IKESADConnectionStatus  OBJECT-TYPE
    SYNTAX                   INTEGER { unknown(0), up(1), notReachable(2) }
    MAX-ACCESS               read-write
    STATUS                   current
    DESCRIPTION
        "(U//FOUO,PR) The status of this SA with regards to its ability to
         pass traffic."
    ::= { altasecHv4IKEv2IKESADEntry 2 }
    
-- =======================
-- Table Providing Summary of SA Management
-- =======================

altasecHv4SASummaryTable   OBJECT-TYPE
        SYNTAX             SEQUENCE OF AltasecHv4SASummaryEntry
        MAX-ACCESS         not-accessible
        STATUS             current
        DESCRIPTION
            "(U//FOUO,PR) This table supplements the information provided in 
             the SA tables of the HAIPE-V4-TRAFFIC-PROTECTION-MIB."
        ::= { altasecHv4SASummary 1 }

altasecHv4SASummaryEntry OBJECT-TYPE
        SYNTAX           AltasecHv4SASummaryEntry
        MAX-ACCESS       not-accessible
        STATUS           current
        DESCRIPTION
            "(U//FOUO,PR) A row providing summary information about current 
             Security Associations (SA's)."
        INDEX   { altasecHv4SASummaryName }
        ::= { altasecHv4SASummaryTable 1 }

AltasecHv4SASummaryEntry ::= SEQUENCE
    {
        altasecHv4SASummaryName              OCTET STRING,
        altasecHv4SASummaryStatus            INTEGER,
        altasecHv4SASummaryEncapType         INTEGER,
        altasecHv4SASummaryKeyType           INTEGER,
        altasecHv4SASummaryInboundIndex      Unsigned32,
        altasecHv4SASummaryOutboundIndex     Unsigned32,
        altasecHv4SASummaryKeyChainName      OCTET STRING,
        altasecHv4SASummaryRowStatus         RowStatus
    }

altasecHv4SASummaryName    OBJECT-TYPE
        SYNTAX             OCTET STRING (SIZE (1..16))
        MAX-ACCESS         read-only
        STATUS             current
        DESCRIPTION
            "(U//FOUO,PR) Name of SA."
        ::= { altasecHv4SASummaryEntry 1 }

altasecHv4SASummaryStatus  OBJECT-TYPE
        SYNTAX             INTEGER { unknown(0), up(1), down(2),
                                     noKey(3), noRoute(4), noPolicy(5),
                                     notReachable(6), needSuiteA(7),
                                     needSuiteB(8), invalidKey(9),
                                     noSPI(10), noGCM0(11) }
        MAX-ACCESS         read-only
        STATUS             current
        DESCRIPTION
            "(U//FOUO,PR) Status of the SA."
        ::= { altasecHv4SASummaryEntry 2 }

altasecHv4SASummaryEncapType  OBJECT-TYPE
        SYNTAX             INTEGER { unknown(0), tunnel(1), transport(2) }
        MAX-ACCESS         read-only
        STATUS             current
        DESCRIPTION
            "(U//FOUO,PR) Encapsulation of the SA."
        ::= { altasecHv4SASummaryEntry 3 }

altasecHv4SASummaryKeyType OBJECT-TYPE
        SYNTAX             INTEGER { ppk(1), hike(2), ikev2(3) }
        MAX-ACCESS         read-only
        STATUS             current
        DESCRIPTION
            "(U//FOUO,PR) Key type of the SA."
        ::= { altasecHv4SASummaryEntry 4 }

altasecHv4SASummaryInboundIndex OBJECT-TYPE
        SYNTAX             Unsigned32
        MAX-ACCESS         read-only
        STATUS             current
        DESCRIPTION
            "(U//FOUO,PR) Inbound SNMP index of the SA."
        ::= { altasecHv4SASummaryEntry 5 }

altasecHv4SASummaryOutboundIndex OBJECT-TYPE
        SYNTAX             Unsigned32
        MAX-ACCESS         read-only
        STATUS             current
        DESCRIPTION
            "(U//FOUO,PR) Outbound SNMP index of the SA."
        ::= { altasecHv4SASummaryEntry 6 }

altasecHv4SASummaryKeyChainName OBJECT-TYPE
        SYNTAX             OCTET STRING
        MAX-ACCESS         read-only
        STATUS             current
        DESCRIPTION
            "(U//FOUO,PR) Key chain name of the SA.  
             Only applicable for PPK SAs"
        ::= { altasecHv4SASummaryEntry 7 }

altasecHv4SASummaryRowStatus OBJECT-TYPE
        SYNTAX             RowStatus
        MAX-ACCESS         read-create
        STATUS             current
        DESCRIPTION
            "(U//FOUO,PR) RowStatus for VLAN Interface."
        ::= { altasecHv4SASummaryEntry 8 }       
          
-- =======================
-- Table Providing Established Traffic Selector Index
-- =======================

altasecHv4EstTSIndexTable  OBJECT-TYPE
        SYNTAX             SEQUENCE OF AltasecHv4EstTSIndexEntry
        MAX-ACCESS         not-accessible
        STATUS             current
        DESCRIPTION
            "(U//FOUO,PR) This table supplements the information provided in 
             the SA tables of the HAIPE-V4-TRAFFIC-PROTECTION-MIB."
        ::= { altasecHv4EstTSIndex 1 }

altasecHv4EstTSIndexEntry OBJECT-TYPE
        SYNTAX           AltasecHv4EstTSIndexEntry
        MAX-ACCESS       not-accessible
        STATUS           current
        DESCRIPTION
            "(U//FOUO,PR) A row providing summary information about current 
             Established Traffic Selector Indexes."
        INDEX   { altasecHv4EstTSIndexName }
        ::= { altasecHv4EstTSIndexTable 1 }

AltasecHv4EstTSIndexEntry ::= SEQUENCE
    {
        altasecHv4EstTSIndexName            OCTET STRING,
        altasecHv4EstLocalTSFirstIndex      INTEGER,
        altasecHv4EstLocalTSNextIndex       Unsigned32,
        altasecHv4EstRemoteTSFirstIndex     INTEGER,
        altasecHv4EstRemoteTSNextIndex      Unsigned32,
        altasecHv4EstTSIndexRowStatus       RowStatus
    }

altasecHv4EstTSIndexName   OBJECT-TYPE
        SYNTAX             OCTET STRING (SIZE (1..32))
        MAX-ACCESS         read-only
        STATUS             current
        DESCRIPTION
            "(U//FOUO,PR) Name of Established Traffic Selector."
        ::= { altasecHv4EstTSIndexEntry 1 }

altasecHv4EstLocalTSFirstIndex OBJECT-TYPE
        SYNTAX             INTEGER
        MAX-ACCESS         read-only
        STATUS             current
        DESCRIPTION
            "(U//FOUO,PR) First index at which an entry can be found for 
             Local Established Traffic Selector.  -1 if no entry found."
        ::= { altasecHv4EstTSIndexEntry 2 }

altasecHv4EstLocalTSNextIndex  OBJECT-TYPE
        SYNTAX             Unsigned32
        MAX-ACCESS         read-only
        STATUS             current
        DESCRIPTION
            "(U//FOUO,PR) Index at which next entry can be added
             Local Established Traffic Selector."
        ::= { altasecHv4EstTSIndexEntry 3 }

altasecHv4EstRemoteTSFirstIndex OBJECT-TYPE
        SYNTAX             INTEGER
        MAX-ACCESS         read-only
        STATUS             current
        DESCRIPTION
            "(U//FOUO,PR) First index at which an entry can be found for 
             Remote Established Traffic Selector. -1 if no entry found."
        ::= { altasecHv4EstTSIndexEntry 4 }

altasecHv4EstRemoteTSNextIndex  OBJECT-TYPE
        SYNTAX             Unsigned32
        MAX-ACCESS         read-only
        STATUS             current
        DESCRIPTION
            "(U//FOUO,PR) Index at which next entry can be added
             Remote Established Traffic Selector."
        ::= { altasecHv4EstTSIndexEntry 5 }

altasecHv4EstTSIndexRowStatus OBJECT-TYPE
        SYNTAX             RowStatus
        MAX-ACCESS         read-create
        STATUS             current
        DESCRIPTION
            "(U//FOUO,PR) RowStatus for VLAN Interface."
        ::= { altasecHv4EstTSIndexEntry 6 }       
        
-- =======================
-- Table Providing SAs for PEPT entries
-- =======================

altasecHv4SaForPeptTable   OBJECT-TYPE
        SYNTAX             SEQUENCE OF AltasecHv4SaForPeptEntry
        MAX-ACCESS         not-accessible
        STATUS             current
        DESCRIPTION
            "(U//FOUO,PR) This table provides information about SAs for pept 
             entries."
        ::= { altasecHv4SASummary 2 }

altasecHv4SaForPeptEntry OBJECT-TYPE
        SYNTAX           AltasecHv4SaForPeptEntry
        MAX-ACCESS       not-accessible
        STATUS           current
        DESCRIPTION
            "(U//FOUO,PR) A row providing summary information about current 
             Security Associations (SA's)."
        INDEX   { altasecHv4SAForPeptRemoteDestHostAddressType, 
                  altasecHv4SAForPeptRemoteDestHostAddress, 
                  altasecHv4SAForPeptPrefixLength,
                  altasecHv4SAForPeptPeerCTAddress,
                  altasecHv4SAForPeptPeerPTAddress,
                  altasecHv4SAForPeptName  }
        ::= { altasecHv4SaForPeptTable 1 }

AltasecHv4SaForPeptEntry ::= SEQUENCE
    {
        altasecHv4SAForPeptRemoteDestHostAddressType IPAddressType,
        altasecHv4SAForPeptRemoteDestHostAddress     IPAddress,
        altasecHv4SAForPeptPrefixLength              Unsigned32,
        altasecHv4SAForPeptPeerCTAddress             IPAddress,
        altasecHv4SAForPeptPeerPTAddress             IPAddress,
        altasecHv4SAForPeptName                      OCTET STRING,
        altasecHv4SAForPeptStatus                    INTEGER,
        altasecHv4SAForPeptEncapType                 INTEGER,
        altasecHv4SAForPeptKeyType                   INTEGER,
        altasecHv4SAForPeptKeyChainName              OCTET STRING,
        altasecHv4SAForPeptTransformSuite            INTEGER,
        altasecHv4SAForPeptLabel                     OCTET STRING,
        altasecHv4SAForPeptRowStatus                 RowStatus
    }

altasecHv4SAForPeptRemoteDestHostAddressType  OBJECT-TYPE
    SYNTAX     IPAddressType
    MAX-ACCESS not-accessible
    STATUS     current
    DESCRIPTION
        "(U//FOUO) The Internet Protocol version, IPv4 or IPv6, of the remote PT
         enclave. Specifically, the value of this property determines the size and
         format of the altasecHv4SAForPeptRemoteDestHostAddress, altasecHv4SAForPeptPeerCTAddress,
         altasecHv4SAForPeptPeerPTAddress, and altasecHv4SAForPeptNATAddress."
    ::= { altasecHv4SaForPeptEntry 1 }

altasecHv4SAForPeptRemoteDestHostAddress  OBJECT-TYPE
    SYNTAX     IPAddress
    MAX-ACCESS not-accessible
    STATUS     current
    DESCRIPTION
        "(U//FOUO) The Internet Protocol addressing information for the
         remote destination host. The size and format of this column is 
         determined by the altasecHv4SAForPeptRemoteDestHostAddressType."
    ::= { altasecHv4SaForPeptEntry 2 }

altasecHv4SAForPeptPrefixLength  OBJECT-TYPE
    SYNTAX     Unsigned32 (0..128)
    MAX-ACCESS not-accessible
    STATUS     current
    DESCRIPTION
        "(U//FOUO) The prefix length of the address stored in
         altasecHv4SAForPeptRemoteDestHostAddress (e.g., the network mask)."
    ::= { altasecHv4SaForPeptEntry 3 }

altasecHv4SAForPeptPeerCTAddress OBJECT-TYPE
    SYNTAX     IPAddress
    MAX-ACCESS not-accessible
    STATUS     current
    DESCRIPTION
        "(U//FOUO) The Internet Protocol addressing information for the
         remote HAIPE CT address. The size and format of this column is
         determined by the altasecHv4SAForPeptRemoteDestHostAddressType."
    ::= { altasecHv4SaForPeptEntry 4 }

altasecHv4SAForPeptPeerPTAddress OBJECT-TYPE
    SYNTAX     IPAddress
    MAX-ACCESS not-accessible
    STATUS     current
    DESCRIPTION
        "(U//FOUO) The Internet Protocol addressing information for the
         remote HAIPE PT address. The size and format of this column is
         determined by the altasecHv4SAForPeptRemoteDestHostAddressType."
    ::= { altasecHv4SaForPeptEntry 5 }

altasecHv4SAForPeptName    OBJECT-TYPE
        SYNTAX             OCTET STRING (SIZE (1..16))
        MAX-ACCESS         not-accessible
        STATUS             current
        DESCRIPTION
            "(U//FOUO,PR) Name of SA."
        ::= { altasecHv4SaForPeptEntry 6 }

altasecHv4SAForPeptStatus  OBJECT-TYPE
        SYNTAX             INTEGER { unknown(0), up(1), down(2),
                                     noKey(3), noRoute(4), noPolicy(5),
                                     notReachable(6), needSuiteA(7),
                                     needSuiteB(8), invalidKey(9),
                                     noSPI(10), noGCM0(11) }
        MAX-ACCESS         read-only
        STATUS             current
        DESCRIPTION
            "(U//FOUO,PR) Status of the SA."
        ::= { altasecHv4SaForPeptEntry 7 }

altasecHv4SAForPeptEncapType  OBJECT-TYPE
        SYNTAX             INTEGER { unknown(0), tunnel(1), transport(2) }
        MAX-ACCESS         read-only
        STATUS             current
        DESCRIPTION
            "(U//FOUO,PR) Encapsulation of the SA."
        ::= { altasecHv4SaForPeptEntry 8 }

altasecHv4SAForPeptKeyType OBJECT-TYPE
        SYNTAX             INTEGER { ppk(1), hike(2), ikev2(3) }
        MAX-ACCESS         read-only
        STATUS             current
        DESCRIPTION
            "(U//FOUO,PR) Key type of the SA."
        ::= { altasecHv4SaForPeptEntry 9 }

altasecHv4SAForPeptKeyChainName OBJECT-TYPE
        SYNTAX             OCTET STRING
        MAX-ACCESS         read-only
        STATUS             current
        DESCRIPTION
            "(U//FOUO,PR) Key chain name of the SA.  
             Only applicable for PPK SAs"
        ::= { altasecHv4SaForPeptEntry 10 }

altasecHv4SAForPeptTransformSuite OBJECT-TYPE
    SYNTAX     HaipeIKEv1SATransformSuites
    MAX-ACCESS read-only
    STATUS     current
    DESCRIPTION
        "(U//FOUO,PR) A set of cryptographic attributes respective to SA."
    ::= { altasecHv4SaForPeptEntry 11 }

altasecHv4SAForPeptLabel   OBJECT-TYPE
        SYNTAX             OCTET STRING
        MAX-ACCESS         read-only
        STATUS             current
        DESCRIPTION
            "(U//FOUO,PR) Label associated with remote route."
        ::= { altasecHv4SaForPeptEntry 12 }

altasecHv4SAForPeptRowStatus OBJECT-TYPE
        SYNTAX             RowStatus
        MAX-ACCESS         read-create
        STATUS             current
        DESCRIPTION
            "(U//FOUO,PR) RowStatus for VLAN Interface."
        ::= { altasecHv4SaForPeptEntry 13 }       
    
-- =======================
-- Table of Network Parameters
-- =======================

altasecHv4NtwkParamsProfileTable      OBJECT-TYPE
        SYNTAX             SEQUENCE OF AltasecHv4NtwkParamsProfileEntry
        MAX-ACCESS         not-accessible
        STATUS             current
        DESCRIPTION
            "(U//FOUO,PR) This table supplements the information provided in 
             the corresponding hIKEv1NtwkParamsProfileTable in the
             HAIPE-TRAFFIC-PROTECTION-MIB with additional proprietary values.
             The hIKEv1NtwkParamsProfileName column is the only index for this
             table and references its parent entry in the aforementioned 
             hIKEv1NtwkParamsProfileTable."
        ::= { altasecHv4NtwkParamsProfiles 3 }

altasecHv4NtwkParamsProfileEntry        OBJECT-TYPE
        SYNTAX          AltasecHv4NtwkParamsProfileEntry
        MAX-ACCESS      not-accessible
        STATUS          current
        DESCRIPTION
            "(U//FOUO,PR) A row describing the additional proprietary 
             information about current Network Parameters that are not included
             in the HAIPE hIKEv1NtwkParamsProfileTable."
        AUGMENTS   { hIKEv1NtwkParamsProfileTableEntry }
        ::= { altasecHv4NtwkParamsProfileTable 1 }

AltasecHv4NtwkParamsProfileEntry ::= SEQUENCE
    {
        altasecHv4NPSADSCPCopyValue                      OCTET STRING,
        altasecHv4NPSAECNValue                           OCTET STRING,
        altasecHv4NPSAECNCopyValue                       OCTET STRING,
        altasecHv4NPMcastBypassMode                      TruthValue,
        altasecHv4NPMcastResetIpSource                   TruthValue
    }

altasecHv4NPSADSCPCopyValue  OBJECT-TYPE
    SYNTAX                OCTET STRING (SIZE (1))
    MAX-ACCESS            read-write
    STATUS                current
    DESCRIPTION
        "(U//FOUO,PR) The Differentiated Service Code Points (DSCP)
         value for the network parameters.

         (U//FOUO,PR) The use of this value is dependent on the value
         of the hTPSADSCP column in its parent hTPSATable row being
         set to set(1). Any other values (acceptlist(3)) will result in
         this value being ignored.

         (U//FOUO,PR) If the hTPSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hTPSADSCPValue column."
    DEFVAL { '00'h }
    ::= { altasecHv4NtwkParamsProfileEntry 2 }

altasecHv4NPSAECNValue  OBJECT-TYPE
    SYNTAX           OCTET STRING (SIZE (1))
    MAX-ACCESS       read-write
    STATUS           current
    DESCRIPTION
        "(U//FOUO,PR) The indication of how the Explicit Congestion
         Notification (ECN) bits should be treated within the network
         parameters.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  The
         ECN value garnered from these lower/right-most 2 of the octet
         are placed within the outgoing packet's Explicit Congestion
         Notification (ECN) header value."
    DEFVAL { '00'h }
    ::= { altasecHv4NtwkParamsProfileEntry 3 }

altasecHv4NPSAECNCopyValue  OBJECT-TYPE
    SYNTAX               OCTET STRING (SIZE (1))
    MAX-ACCESS           read-write
    STATUS               current
    DESCRIPTION
        "(U//FOUO,PR) The indication of how the Explicit Congestion
         Notification (ECN) bits should be treated within the network
         parameters.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  Any
         bits set in these lower/right-most 2 of the octet will indicate
         that those bits be copied from the incoming packet's Explicit
         Congestion Notification (ECN) header value to the outgoing
         packet. Any bits set for this value effectively overrides, to
         copy, those set in the above altaTPSAECNValue column."
    DEFVAL { '00'h }
    ::= { altasecHv4NtwkParamsProfileEntry 4 }

altasecHv4NPMcastBypassMode OBJECT-TYPE
    SYNTAX                TruthValue
    MAX-ACCESS            read-write
    STATUS                current
    DESCRIPTION
        "(U//FOUO,PR) Enables or disables Multicast Bypass."
    ::= { altasecHv4NtwkParamsProfileEntry 5 }

altasecHv4NPMcastResetIpSource OBJECT-TYPE
    SYNTAX                   TruthValue
    MAX-ACCESS               read-write
    STATUS                   current
    DESCRIPTION
        "(U//FOUO,PR) Resets the source address to the device's PT IP address
         instead of the original multicast address."
    ::= { altasecHv4NtwkParamsProfileEntry 6 }

-- **********************************************************************
-- Key Transfer MIB
-- **********************************************************************
      
-- =======================
-- OBKT Clients Table
-- =======================

altasecHv4OOBKTClientsTable OBJECT-TYPE
    SYNTAX     SEQUENCE OF AltasecHv4OOBKTClientsEntry
    MAX-ACCESS not-accessible
    STATUS     current
    DESCRIPTION
        "(U//FOUO) ViaSat table augmenting the table for configuring a list of
        a HAIPE's Out-of-Band Transfer Clients.."
    ::= { altasecHv4OutofBandKeyTransferClients 3 }

altasecHv4OOBKTClientsEntry OBJECT-TYPE
    SYNTAX     AltasecHv4OOBKTClientsEntry
    MAX-ACCESS not-accessible
    STATUS     current
    DESCRIPTION
            "(U//FOUO,PR) A row describing the additional proprietary
             information about current OOBKT Clients that is not included
             in the HAIPE hOOBKTClientsTable."
    AUGMENTS { hOOBKTClientsTableEntry }
    ::= { altasecHv4OOBKTClientsTable 1 }

AltasecHv4OOBKTClientsEntry ::= SEQUENCE
{
   altasecHv4OOBKTClientStatus                            INTEGER
}

altasecHv4OOBKTClientStatus OBJECT-TYPE
    SYNTAX     INTEGER { pending(0), inprogress(1), connecting(2),
                         connectionpending(3), complete(4), failed(5),
                         canceled(6) }
    MAX-ACCESS read-only
    STATUS     current
    DESCRIPTION
        "(U//FOUO) Status of OOBKT Client."
    ::= { altasecHv4OOBKTClientsEntry 2 }
    
-- =======================
-- IBKT Clients Table
-- =======================

altasecHv4IBKTClientsTable OBJECT-TYPE
    SYNTAX     SEQUENCE OF AltasecHv4IBKTClientsEntry
    MAX-ACCESS not-accessible
    STATUS     current
    DESCRIPTION
        "(U//FOUO) ViaSat table augmenting the table for configuring a list of
        a HAIPE's Out-of-Band Transfer Clients.."
    ::= { altasecHv4InBandKeyTransferClients 3 }

altasecHv4IBKTClientsEntry OBJECT-TYPE
    SYNTAX     AltasecHv4IBKTClientsEntry
    MAX-ACCESS not-accessible
    STATUS     current
    DESCRIPTION
            "(U//FOUO,PR) A row describing the additional proprietary
             information about current OOBKT Clients that is not included
             in the HAIPE hIBKTClientsTable."
    AUGMENTS { hIBKTClientsTableEntry }
    ::= { altasecHv4IBKTClientsTable 1 }

AltasecHv4IBKTClientsEntry ::= SEQUENCE
{
   altasecHv4IBKTClientsStatus                            INTEGER
}

altasecHv4IBKTClientsStatus OBJECT-TYPE
    SYNTAX     INTEGER { pending(0), inProgress(1), connecting(2),
                         connectionPending(3), complete(4), failed(5),
                         canceled(6) }
    MAX-ACCESS read-only
    STATUS     current
    DESCRIPTION
        "(U//FOUO) Status of OOBKT Client."
    ::= { altasecHv4IBKTClientsEntry 4 }  
    
-- =======================
-- Loaded Key Table
-- =======================

altasecHv4LoadedKeyTable OBJECT-TYPE
    SYNTAX     SEQUENCE OF AltasecHv4LoadedKeyEntry
    MAX-ACCESS not-accessible
    STATUS     current
    DESCRIPTION
        "(U//FOUO) ViaSat table augmenting the table for configuring a list of
        a HAIPE's Issued keys."
    ::= { altasecHv4LoadedKeys 3 }

altasecHv4LoadedKeyEntry OBJECT-TYPE
    SYNTAX     AltasecHv4LoadedKeyEntry
    MAX-ACCESS not-accessible
    STATUS     current
    DESCRIPTION
            "(U//FOUO,PR) A row describing the additional proprietary
             information about current Loaded Keys that is not included
             in the HAIPE hLoadedKeyClientsTable."
    AUGMENTS { hLoadedKeyTableEntry }
    ::= { altasecHv4LoadedKeyTable 1 }

AltasecHv4LoadedKeyEntry ::= SEQUENCE
{
   altasecHv4LoadedKeyLabel                          SnmpAdminString,
   altasecHv4LoadedKeyMaterial                       OCTET STRING
}

altasecHv4LoadedKeyLabel OBJECT-TYPE
        SYNTAX     SnmpAdminString
        MAX-ACCESS read-write
        STATUS     current
        DESCRIPTION
            "(U//FOUO) If the loaded key is a DGSK, this field is a
             free text field allowing the user to tag a device-
             generated raw string with helpful information. For example, a label
             could indicate the intended usage of a device-generated raw
             string."
        ::= { altasecHv4LoadedKeyEntry 5 } 
        
altasecHv4LoadedKeyMaterial OBJECT-TYPE
        SYNTAX     OCTET STRING (SIZE(36))
        MAX-ACCESS read-only
        STATUS     current
        DESCRIPTION
            "(U//FOUO) If the loaded key is a DGSK, this field is 
            the 72 hexadecimal character representation of the
            device-generated raw string (CRC included). Implementations must 
            restrict the display of this value to four hex characters at a 
            time."
        ::= { altasecHv4LoadedKeyEntry 6 }
    
-- **********************************************************************
-- Discovery
-- **********************************************************************
      
-- =======================
-- Local Enclave Prefix Table
-- =======================
altasecHv4LEPTTable OBJECT-TYPE
    SYNTAX     SEQUENCE OF AltasecHv4LEPTEntry
    MAX-ACCESS not-accessible
    STATUS     current
    DESCRIPTION
        "(U//FOUO) ViaSat table augmenting the table containing a list of the
         known local PT address hosts and/or prefixes that this device is
         fronting.  The contents of this table can be populated by either
         manual assignment or through the use of discovery services (e.g.,
         RIP). It is used when routing post-decryption inbound packets to the
         PT enclave."
    ::= { altasecHv4LEPT 3 }

altasecHv4LEPTEntry OBJECT-TYPE
    SYNTAX     AltasecHv4LEPTEntry
    MAX-ACCESS not-accessible
    STATUS     current
    DESCRIPTION
            "(U//FOUO,PR) A row describing the additional proprietary
             information about current Local Routes that is not included
             in the HAIPE hLEPTTable."
    AUGMENTS { hLEPTTableEntry }
    ::= { altasecHv4LEPTTable 1 }

AltasecHv4LEPTEntry ::= SEQUENCE
{
   altasecHv4LEPTNextHopAddress                    IPAddress,
   altasecHv4LEPTMetric                            INTEGER,
   altasecHv4LEPTIsLocalEnclave                    TruthValue
}

altasecHv4LEPTNextHopAddress OBJECT-TYPE
    SYNTAX     IPAddress
    MAX-ACCESS read-write
    STATUS     current
    DESCRIPTION
        "(U//FOUO) The Next Hop Internet Protocol addressing information. The
         size and format of this column is determined by IPAddress."
    ::= { altasecHv4LEPTEntry 4 }
    
altasecHv4LEPTMetric OBJECT-TYPE
    SYNTAX     INTEGER
    MAX-ACCESS read-write
    STATUS     current
    DESCRIPTION
        "(U//FOUO) The primary routing metric for this route.  The semantics of
         this metric are determined by the routing protocol specified in the
         route's CIDR Route Table Route Protocol value."
    ::= { altasecHv4LEPTEntry 5 }   
    
altasecHv4LEPTIsLocalEnclave OBJECT-TYPE
    SYNTAX     TruthValue
    MAX-ACCESS read-only
    STATUS     current
    DESCRIPTION
        "(U//FOUO) True if this is a local enclave entry, false otherwise."
    ::= { altasecHv4LEPTEntry 6 }   
    
-- =======================
-- Local CT Route [LocCTRt]
-- =======================

altasecHv4LocCTRtTableCount OBJECT-TYPE
    SYNTAX     Unsigned32
    MAX-ACCESS read-only
    STATUS     current
    DESCRIPTION
        "(U//FOUO) The number of rows in the altasecHv4LocCTRtTable."
    ::= { altasecHv4LocCTRt 1 }

altasecHv4LocCTRtTableLastChanged OBJECT-TYPE
    SYNTAX     TimeStamp
    MAX-ACCESS read-only
    STATUS     current
    DESCRIPTION
        "(U//FOUO) The value of hSystemUpTime the last time any entry in the
         altasecHv4LocCTRtTable was modified, created, or deleted by either SNMP 
         or other management method (e.g. via an HMI).

         (U//FOUO) Managers can use this object to ensure that no changes to
         configuration of this table have happened since the last time it
         examined the table.

         (U//FOUO) A value of 0 indicates that no entry has been changed since
         the agent initialized."
    ::= { altasecHv4LocCTRt 2 }

altasecHv4LocCTRtTable OBJECT-TYPE
    SYNTAX     SEQUENCE OF AltasecHv4LocCTRtEntry
    MAX-ACCESS not-accessible
    STATUS     current
    DESCRIPTION
        "(U//FOUO) The table containing a list of the known local CT address
         hosts and/or prefixes that this device has configured.  The contents of
         this table can be populated by either manual assignment or through the
         use of discovery services (e.g., RIP). It is used when routing
         post-decryption inbound packets to the CT enclave."
    ::= { altasecHv4LocCTRt 3 }

altasecHv4LocCTRtEntry OBJECT-TYPE
    SYNTAX     AltasecHv4LocCTRtEntry
    MAX-ACCESS not-accessible
    STATUS     current
    DESCRIPTION
        "(U//FOUO) An entry identify a host or prefix that is on local CT 
         route."
    INDEX  { altasecHv4LocCTRtAddressType, altasecHv4LocCTRtAddress, 
             altasecHv4LocCTRtPrefixLength }
    ::= { altasecHv4LocCTRtTable 1 }

AltasecHv4LocCTRtEntry ::= SEQUENCE
{
   altasecHv4LocCTRtAddressType                IPAddressType,
   altasecHv4LocCTRtAddress                    IPAddress,
   altasecHv4LocCTRtPrefixLength               Unsigned32,
   altasecHv4LocCTRtAdminCost                  Unsigned32,
   altasecHv4LocCTRtRowConfigMethod            INTEGER,
   altasecHv4LocCTRtRowLifetime                DateAndTime,
   altasecHv4LocCTRtNextHopAddress             IPAddress,
   altasecHv4LocCTRtMetric                     INTEGER,
   altasecHv4LocCTRtRowStatus                  RowStatus
}

altasecHv4LocCTRtAddressType OBJECT-TYPE
    SYNTAX     IPAddressType
    MAX-ACCESS read-create
    STATUS     current
    DESCRIPTION
        "(U//FOUO) The Internet Protocol Version, IPv4 or IPv6, of the local CT
         host or enclave. Specifically, the value of this property determines 
         the size and format of the altasecHv4LocCTRtAddress."
    ::= { altasecHv4LocCTRtEntry 1 }

altasecHv4LocCTRtAddress OBJECT-TYPE
    SYNTAX     IPAddress
    MAX-ACCESS read-create
    STATUS     current
    DESCRIPTION
        "(U//FOUO) The Internet Protocol addressing information for the local
         CT Host or CT network prefix. The size and format of this column is 
         determined by the altasecHv4LocCTRtAddressType."
    ::= { altasecHv4LocCTRtEntry 2 }

altasecHv4LocCTRtPrefixLength OBJECT-TYPE
    SYNTAX     Unsigned32 (0..2040)
    MAX-ACCESS read-create
    STATUS     current
    DESCRIPTION
        "(U//FOUO) The prefix length of the address stored in 
         altasecHv4LocCTRtAddress object (e.g., the network mask)."
    ::= { altasecHv4LocCTRtEntry 3 }

altasecHv4LocCTRtAdminCost OBJECT-TYPE
    SYNTAX     Unsigned32 (0..255)
    MAX-ACCESS read-create
    STATUS     current
    DESCRIPTION
        "(U//FOUO) The administrative cost of reaching the 
         altasecHv4LocCTRtAddress (or subnet) via this device.

         (U//FOUO) For local prefix learned via automated discovery mechanisms,
         and for which no better metric is available, this object will be
         populated with learned cost/metric, hLearnedLocalPrefixAdminCost."
    ::= { altasecHv4LocCTRtEntry 4 }

altasecHv4LocCTRtRowConfigMethod OBJECT-TYPE
    SYNTAX     INTEGER{ manual(1), rip(2), other(3) }
    MAX-ACCESS read-only
    STATUS     current
    DESCRIPTION
        "(U//FOUO) The method by which this row was configured."
    ::= { altasecHv4LocCTRtEntry 5 }

altasecHv4LocCTRtRowLifetime OBJECT-TYPE
    SYNTAX     DateAndTime
    MAX-ACCESS read-create
    STATUS     current
    DESCRIPTION
        "(U//FOUO) The date and time that this particular entry will become
         invalid.  For local prefix learned via Discovery, this object will be
         populated with the associated Discovery lifetime learned.

         (U//FOUO) If this particular entry is configured through RIP, this
         object is configured with the value of the hRIPPrefixLifetime."
    ::= { altasecHv4LocCTRtEntry 6 }

altasecHv4LocCTRtNextHopAddress OBJECT-TYPE
    SYNTAX     IPAddress
    MAX-ACCESS read-create
    STATUS     current
    DESCRIPTION
        "(U//FOUO) The Next Hop Internet Protocol addressing information. The
         size and format of this column is determined by IPAddress."
    ::= { altasecHv4LocCTRtEntry 7 }

altasecHv4LocCTRtMetric OBJECT-TYPE
    SYNTAX     INTEGER
    MAX-ACCESS read-create
    STATUS     current
    DESCRIPTION
        "(U//FOUO) The primary routing metric for this route.  The semantics of
         this metric are determined by the routing protocol specified in the
         route's CIDR Route Table Route Protocol value."
    ::= { altasecHv4LocCTRtEntry 8 }
    
altasecHv4LocCTRtRowStatus OBJECT-TYPE
    SYNTAX     RowStatus
    MAX-ACCESS read-create
    STATUS     current
    DESCRIPTION
        "(U//FOUO) The status of the row, by which new entries may be created,
         or old entries deleted from this table.

         (U//FOUO) If an attempt to create a new row via createAndGo does not
         include values for columns for the new row, an inconsistentName
         error will be returned for this object.

         (U//FOUO) A row cannot be set to active while 
         altasecHv4LocCTRtAddressType, altasecHv4LocCTRtAddress, and 
         altasecHv4LocCTRtPrefixLength do not contain consistent values for the 
         row.  An inconsistentValue error will be returned for this object.

         (U//FOUO) If any column is set to an invalid or unsupported value
         (during row creation or any other time), a wrongValue error will be
         returned for that object.

         (U//FOUO) An active row may not be changed to an inconsistent state. 
         If such an attempt is made, an inconsistentValue error will be
         returned. In other words, any new values must be valid values for an 
         active row.

         (U//FOUO) At a minimum, implementations must support createAndGo and
         destroy management functions. Support for createAndWait, active,
         notInService, and notReady management functions is optional."
    ::= { altasecHv4LocCTRtEntry 9 }
    
-- =======================
-- Peer Enclave Prefix Table
-- =======================
altasecHv4PEPTTable OBJECT-TYPE
    SYNTAX     SEQUENCE OF AltasecHv4PEPTEntry
    MAX-ACCESS not-accessible
    STATUS     current
    DESCRIPTION
        "(U//FOUO) ViaSat table augmenting the table containing a list of the
         known Remote PT address hosts and/or prefixes that this device is
         fronting.  The contents of this table can be populated by either
         manual assignment or through the use of discovery services (e.g.,
         RIP). It is used when routing post-decryption inbound packets to the
         PT enclave."
    ::= { altasecHv4PEPT 3 }

altasecHv4PEPTEntry OBJECT-TYPE
    SYNTAX     AltasecHv4PEPTEntry
    MAX-ACCESS not-accessible
    STATUS     current
    DESCRIPTION
            "(U//FOUO,PR) A row describing the additional proprietary
             information about current Remote Routes that is not included
             in the HAIPE hPEPTTable."
    AUGMENTS { hPEPTTableEntry }
    ::= { altasecHv4PEPTTable 1 }

AltasecHv4PEPTEntry ::= SEQUENCE
{
   altasecHv4PEPTMetric                            INTEGER,
   altasecHv4PEPTLabel                             OCTET STRING,
   altasecHv4PEPTConnect                           TruthValue,
   altasecHv4PEPTTunnelAssociationName             SnmpAdminString
}

altasecHv4PEPTMetric OBJECT-TYPE
    SYNTAX     INTEGER
    MAX-ACCESS read-only
    STATUS     current
    DESCRIPTION
        "(U//FOUO) The primary routing metric for this route.  The semantics of
         this metric are determined by the routing protocol specified in the
         route's CIDR Route Table Route Protocol value. Warning: Changing the
         metric of an SA used by automated SAs could cause re-negotiation."
    ::= { altasecHv4PEPTEntry 6 }

altasecHv4PEPTLabel        OBJECT-TYPE
        SYNTAX             OCTET STRING
        MAX-ACCESS         read-write
        STATUS             current
        DESCRIPTION
            "(U//FOUO,PR) Label associated with remote route."
        ::= { altasecHv4PEPTEntry 7 }

altasecHv4PEPTConnect      OBJECT-TYPE
        SYNTAX             TruthValue
        MAX-ACCESS         read-write
        STATUS             current
        DESCRIPTION
            "(U//FOUO,PR) Set to true to attempt to connect remote route, false
             otherwise."
    ::= { altasecHv4PEPTEntry 8 }

altasecHv4PEPTTunnelAssociationName OBJECT-TYPE
        SYNTAX                      SnmpAdminString
        MAX-ACCESS                  read-write
        STATUS                      current
        DESCRIPTION
            "(U//FOUO,PR) The device name of the PPK Tunnel SA that is 
             currently associated with this entry. If the PEPT entry does not 
             have a Tunnel association, a zero length string is returned."
    ::= { altasecHv4PEPTEntry 9 }
    
-- *************************************************
-- PPK Information.
--

-- *************************************************
-- PPK Key Information.
--

altasecHv4PreplacedKeyTableCount OBJECT-TYPE
        SYNTAX          Unsigned32
        MAX-ACCESS      read-only
        STATUS          current
        DESCRIPTION
            "(U//FOUO,PR) The number of rows in the altasecPreplacedKeyTable."
        ::= { altasecHv4PPKKeyInformation 1 }

altasecHv4PreplacedKeyTableLastChanged OBJECT-TYPE
        SYNTAX      	TimeStamp
        MAX-ACCESS  	read-only
        STATUS      	current
        DESCRIPTION
            "(U//FOUO,PR) The value of sysUpTime the last time any entry
            in the altasecPreplacedKeyTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecHv4PPKKeyInformation 2 }

altasecHv4PreplacedKeyTable  OBJECT-TYPE
    SYNTAX            	     SEQUENCE OF AltasecHv4PreplacedKeyEntry
    MAX-ACCESS               not-accessible
    STATUS                   current
    DESCRIPTION
        "(U//FOUO,PR) The table containing information about the loaded
         pre-placed keys (PPK's). This proprietary table is necessary in that
         users may optionally load multiple copies of the same key. This table
         differs from the hPreplacedKeyTable in that the PPK SPIDs are used as
         an additional index into the table. In addition to the values provided
         in the hPreplacedKeyTable, the PPK Chain to which it is assigned (if
         any) is provided for added granularity."
    ::= { altasecHv4PPKKeyInformation 3 }

altasecHv4PreplacedKeyEntry  OBJECT-TYPE
    SYNTAX                AltasecHv4PreplacedKeyEntry
    MAX-ACCESS            not-accessible
    STATUS                current
    DESCRIPTION
        "(U//FOUO,PR) A row indicating a pre-placed key (PPK) within a
        chain of PPK's and the order that the PPK indicated will be
        used by the HAIPE device as part of that chain."
    INDEX  { hV4PPKShortTitleName, hV4PPKEdition, hV4PPKSegment, 
    altasecV4PPKSPID }
    ::= { altasecHv4PreplacedKeyTable 1 }

AltasecHv4PreplacedKeyEntry ::= SEQUENCE
    {
        hV4PPKShortTitleName               PreplacedKeyShortTitle,
        hV4PPKEdition                      PreplacedKeyEdition,
        hV4PPKSegment                      PreplacedKeySegment,
        altasecV4PPKSPID                   Unsigned32,
        hV4PPKisAuthenticated              TruthValue,
        hV4PPKIBKTSupersessionDisable      TruthValue,
        hV4PPKUsageType                    BITS,
        hV4PPKSecurityLevel                BITS,
        hV4PPKLabel                        SnmpAdminString,
        hV4PPKRowStatus                    RowStatus,
        hV4PPKEffectiveDate                DateAndTime,
        altasecHv4PPKChainID               SnmpAdminString,
        altasecHv4PPKIKEVersion            BITS,
        altasecHv4PPKEndDate               DateAndTime,
        altasecHv4PPKQKeyLabel             SnmpAdminString
    }

hV4PPKShortTitleName    OBJECT-TYPE
        SYNTAX          PreplacedKeyShortTitle
        MAX-ACCESS      not-accessible
        STATUS          current
        DESCRIPTION
            "(U//FOUO) The short title of the pre-placed key (PPK)."
        ::= { altasecHv4PreplacedKeyEntry 1 }

hV4PPKEdition           OBJECT-TYPE
        SYNTAX          PreplacedKeyEdition
        MAX-ACCESS      not-accessible
        STATUS          current
        DESCRIPTION
            "(U//FOUO) The edition of this pre-placed key (PPK)."
        ::= { altasecHv4PreplacedKeyEntry 2 }

hV4PPKSegment           OBJECT-TYPE
        SYNTAX          PreplacedKeySegment
        MAX-ACCESS      not-accessible
        STATUS          current
        DESCRIPTION
            "(U//FOUO) The segment number of this pre-placed key (PPK)."
        ::= { altasecHv4PreplacedKeyEntry 3 }

altasecV4PPKSPID        OBJECT-TYPE
        SYNTAX          Unsigned32
        MAX-ACCESS      not-accessible
        STATUS          current
        DESCRIPTION
            "(U//FOUO,PR) The SPID assigned to the pre-placed key (PPK)."
        ::= { altasecHv4PreplacedKeyEntry 4 }
        
hV4PPKisAuthenticated   OBJECT-TYPE
		SYNTAX          TruthValue
		MAX-ACCESS      read-only
		STATUS          current
		DESCRIPTION
		    "(U//FOUO) Indicates whether the key is an authenticated 
		   	pre-placed key (APPK). This column is provided for 
		   	informational purposes, specifically to indicate whether 
		   	this key is Suite A or Suite B. This information is taken 
		   	directly from the key material itself."
        ::= { altasecHv4PreplacedKeyEntry 5 }
        
hV4PPKIBKTSupersessionDisable   OBJECT-TYPE
		SYNTAX                  TruthValue
		MAX-ACCESS              read-write
		STATUS                  current
		DESCRIPTION
		    "(U//FOUO) Indicates whether supersession is allowed for 
		    this pre-placed key (PPK) via In-Band Key Transfer.

            (U//FOUO) [true] If this column is set to true, IBKT 
            supersession is disabled for this key.

            (U//FOUO) [false] If this column is set to false, IBKT 
            supersession is allowed for this key."
        ::= { altasecHv4PreplacedKeyEntry 6 }

hV4PPKUsageType         OBJECT-TYPE
        SYNTAX          BITS { manual-sa(0), ek(1), shared-secret(2) }
        MAX-ACCESS      read-only
        STATUS          current
        DESCRIPTION
            "(U//FOUO) Indicates how this key can be used.  Unlike the
            hPreplacedKeyTable, this value is read-only."
        ::= { altasecHv4PreplacedKeyEntry 7 }

hV4PPKSecurityLevel     OBJECT-TYPE
        SYNTAX          BITS { unclassified(0), restricted(1), confidential(2),
        					   secret(3), top-secret(4), nato-restricted(5), 
        					   nato-confidential(6), nato-secret (7), 
        					   cosmic-top-secret(8) }
        MAX-ACCESS      read-only
        STATUS          current
        DESCRIPTION
            "(U//FOUO) The security level usable with this
            pre-placed key (PPK)."
        ::= { altasecHv4PreplacedKeyEntry 8 }
        
hV4PPKLabel				OBJECT-TYPE
		SYNTAX			SnmpAdminString	
		MAX-ACCESS		read-write
		STATUS			current
		DESCRIPTION
			"(U//FOUO) This object is a free text field allowing the user
			to tag PPKs with helpful information. For example, a label
			could indicate the intended usage of a particular PPK."
		::= { altasecHv4PreplacedKeyEntry 9 }
        
hV4PPKRowStatus         OBJECT-TYPE
        SYNTAX          RowStatus
        MAX-ACCESS      read-create
        STATUS          current
        DESCRIPTION
            "(U//FOUO) The status of the row by which new entries may be
			created, existing entries enabled/disabled or existing entries
			deleted from this table.

			(U//FOUO) Entries created within this table may not become active
			unless all columns of this table have valid values. Entries may
			be active, however, even though they are currently not used to
			protect traffic. For example, a chain for future use may have an
			effective start date beyond the current time.

			(U//FOUO) At a minimum, implementations must support createAndGo
			and destroy management functions. Support for createAndWait,
			active, notInService, and notReady management functions is
			optional."
        ::= { altasecHv4PreplacedKeyEntry 10 } 

hV4PPKEffectiveDate     OBJECT-TYPE
        SYNTAX          DateAndTime
        MAX-ACCESS      read-write
        STATUS          current
        DESCRIPTION
            "(U//FOUO) The effective start date and time of this
            pre-placed key (PPK).  This object will be automatically
            set from the chain information once the spot in the chain
            is reached where this key becomes actively used."
        ::= { altasecHv4PreplacedKeyEntry 11 }

altasecHv4PPKChainID   OBJECT-TYPE
        SYNTAX      SnmpAdminString
        MAX-ACCESS  read-only
        STATUS      current
        DESCRIPTION
            "(U//FOUO,PR) An administratively assigned name to link a group
            of PPKs together.  This object may be referenced by the
            hIPhRuleActionIndex object in the hIPhRuleTable if it is not a
            zero-length string."
        ::= { altasecHv4PreplacedKeyEntry 12 }

        
altasecHv4PPKIKEVersion     OBJECT-TYPE
        SYNTAX        BITS { ikev1(0), ikev2(1) }
        MAX-ACCESS    read-write
        STATUS        current
        DESCRIPTION
            "(U//FOUO,PR) The version of IKE to use when assigning the key.
            Note that IKEv2 is only available if it has been enabled on the
            device."
        ::= { altasecHv4PreplacedKeyEntry 13 }
        
altasecHv4PPKEndDate     OBJECT-TYPE
        SYNTAX          DateAndTime
        MAX-ACCESS      read-only
        STATUS          current
        DESCRIPTION
            "(U//FOUO) The effective end date and time of this
            pre-placed key (PPK).  This object will be automatically
            set from the chain information once the spot in the chain
            is reached where this key becomes actively used. This column only
            exists if the key is assigned as a Shared Secret."
        ::= { altasecHv4PreplacedKeyEntry 14 }
        
altasecHv4PPKQKeyLabel   OBJECT-TYPE
        SYNTAX        SnmpAdminString
        MAX-ACCESS    read-only
        STATUS        current
        DESCRIPTION
            "(U//FOUO,PR) An administratively assigned name to identify
            the Q-key (trust anchor) used to authenticate an APPK.
            This object only exists when the INE is operating in Suite B,
            and Q-Key is enabled."
        ::= { altasecHv4PreplacedKeyEntry 15 }

        
-- *************************************************
-- PPK Chain Information.
--

altasecHv4ManSAKeyChainTableCount OBJECT-TYPE
        SYNTAX          Unsigned32
        MAX-ACCESS      read-only
        STATUS          current
        DESCRIPTION
            "(U//FOUO,PR) The number of rows in the 
            altasecHv4ManSAKeyChainTable."
        ::= { altasecHv4ChainInformation 1 }

altasecHv4ManSAKeyChainTableLastChanged OBJECT-TYPE
        SYNTAX      	TimeStamp
        MAX-ACCESS  	read-only
        STATUS      	current
        DESCRIPTION
            "(U//FOUO,PR) The value of sysUpTime the last time any entry
            in the altasecHv4ManSAKeyChainTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecHv4ChainInformation 2 }

altasecHv4ManSAKeyChainTable  OBJECT-TYPE
    SYNTAX                    SEQUENCE OF AltasecHv4ManSAKeyChainEntry
    MAX-ACCESS                not-accessible
    STATUS                    current
    DESCRIPTION
        "(U//FOUO,PR) The table containing proprietary information about
        pre-placed key (PPK) chains.  This table includes a column to
        set the integrity algorithm at creation time for the PPK Chain."
    ::= { altasecHv4ChainInformation 3 }

altasecHv4ManSAKeyChainEntry  OBJECT-TYPE
    SYNTAX            AltasecHv4ManSAKeyChainEntry
    MAX-ACCESS        not-accessible
    STATUS            current
    DESCRIPTION
        "(U//FOUO,PR) A row indicating a pre-placed key (PPK) within a
        chain of PPK's and the order that the PPK indicated will be
        used by the HAIPE device as part of that chain."
        AUGMENTS   { hManSAKeyChainTableEntry }
    ::= { altasecHv4ManSAKeyChainTable 1 }

AltasecHv4ManSAKeyChainEntry ::= SEQUENCE
    {
        altasecManSAKeyChainTransformSuite  		AltasecIntegrityAlgorithm,
        altasecManSAKeyChainEncryptionAlgorithm		AltasecEncryptionAlgorithm,
    	altasecManSAKeyChainPPKSPID					INTEGER					
    }

altasecManSAKeyChainTransformSuite  OBJECT-TYPE
    SYNTAX                          AltasecIntegrityAlgorithm
    MAX-ACCESS                      read-write
    STATUS                          current
    DESCRIPTION
        "(U//FOUO,PR) The integrity algorithm to be used by this key.
         This integrity algorithm should be manually configured for
         the first key assigned to the chain but later keys added to
         the same chain will have this integrity algorithm field set
         to the same integrity algorithm from the previous key in the
         chain."
    ::= { altasecHv4ManSAKeyChainEntry 1 }
    
altasecManSAKeyChainEncryptionAlgorithm  OBJECT-TYPE
    SYNTAX                          	 AltasecEncryptionAlgorithm
    MAX-ACCESS                      	 read-write
    STATUS                          	 current
    DESCRIPTION
        "(U//FOUO) The encryption algorithm to be used by this key.
		This encryption algorithm should be manually configured for
		the first key assigned to the chain but later keys added to
		the same chain will have this encryption algorithm field set
		to the same encryption algorithm from the previous key in the
		chain.  When a given key becomes active and is used to protect
		traffic, the hPPKTrafficEncryptAlgorithm column for this
		key in the chain will update to match the value in this
		column."
    ::= { altasecHv4ManSAKeyChainEntry 2 }
    
altasecManSAKeyChainPPKSPID				 OBJECT-TYPE
    SYNTAX                          	 INTEGER
    MAX-ACCESS                      	 read-only
    STATUS                          	 current
    DESCRIPTION
        "(U//FOUO) The SPID of the PrePlacedKey on this chain. "
    ::= { altasecHv4ManSAKeyChainEntry 3 }
    
-- *************************************************
-- DGSK Key Information.
--

altasecHv4DGSharedKeyTable  OBJECT-TYPE
    SYNTAX                    SEQUENCE OF AltasecHv4DGSharedKeyEntry
    MAX-ACCESS                not-accessible
    STATUS                    current
    DESCRIPTION
        "(U//FOUO,PR) The table containing proprietary information about
        HAIPE Device Generated Shared Keys (DGSKs)."
    ::= { altasecHv4DGSharedKeyInformation 3 }

altasecHv4DGSharedKeyEntry  OBJECT-TYPE
    SYNTAX            AltasecHv4DGSharedKeyEntry
    MAX-ACCESS        not-accessible
    STATUS            current
    DESCRIPTION
        "(U//FOUO,PR) A row corresponding to a Device Generated Shared Key (DGSK)"
        AUGMENTS   { hDGSharedKeyTableEntry }
    ::= { altasecHv4DGSharedKeyTable 1 }

AltasecHv4DGSharedKeyEntry ::= SEQUENCE
    {
      altasecHv4DGSKEdition         PreplacedKeyEdition,
      altasecHv4DGSKSegment         PreplacedKeySegment,
      altasecHv4DGSKEndDate         DateAndTime
    }
    
altasecHv4DGSKEdition           OBJECT-TYPE
        SYNTAX          PreplacedKeyEdition
        MAX-ACCESS      read-only
        STATUS          current
        DESCRIPTION
            "(U//FOUO) The edition of this Device Generated Shared 
            key (DGSK)."
        ::= { altasecHv4DGSharedKeyEntry 2 }

altasecHv4DGSKSegment           OBJECT-TYPE
        SYNTAX          PreplacedKeySegment
        MAX-ACCESS      read-only
        STATUS          current
        DESCRIPTION
            "(U//FOUO) The segment number of this Device Generated Shared 
            key (DGSK)."
        ::= { altasecHv4DGSharedKeyEntry 3 }
        
altasecHv4DGSKEndDate   OBJECT-TYPE
        SYNTAX          DateAndTime
        MAX-ACCESS      read-only
        STATUS          current
        DESCRIPTION
            "(U//FOUO) The effective end date and time of this
            Device Generated Shared Key (DGSK).  This object will be 
            automatically set from the chain information once the spot in 
            the chain is reached where this key becomes actively used. 
            This column only exists if the key is assigned as a Shared Secret."
        ::= { altasecHv4DGSharedKeyEntry 4 }   

-- NOTE: missing column 5: Integer32 (CHIMERA Team)

-- *************************************************
-- IPMEIR DGSK Key Information.
--
altasecHv4IpmeirGenerateSharedKey OBJECT-TYPE
        SYNTAX      TruthValue
        MAX-ACCESS  read-write
        STATUS      current
        DESCRIPTION
            "(U//FOUO) Setting this object to 'true' will force the generation 
             of a raw string (IPMEIR DGSK) to be used as key material. 
             Post-generation, the agent must create an entry in the 
             altasecHv4IpmeirDGSharedKeyTable that captures information on this
             DGSK.

             (U//FOUO) Note after being set to true, an agent should reset this 
             object to false once it has generated the DGSK and configured an 
             entry in the hDGSharedKeyTable." 
        ::= { altasecHv4DGSharedKeyInformation 4 }
        
altasecHv4IpmeirDGSharedKeyTableCount OBJECT-TYPE
        SYNTAX          Unsigned32
        MAX-ACCESS      read-only
        STATUS          current
        DESCRIPTION
            "(U//FOUO,PR) The number of rows in the altasecHv4IpmeirDGSharedKeyTable."
        ::= { altasecHv4DGSharedKeyInformation 5 }
        
altasecHv4IpmeirDGSharedKeyTableLastChanged OBJECT-TYPE
        SYNTAX      TimeStamp
        MAX-ACCESS  read-only
        STATUS      current
        DESCRIPTION
            "(U//FOUO,PR) The value of sysUpTime the last time any entry
            in the altasecHv4IpmeirDGSharedKeyTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecHv4DGSharedKeyInformation 6 }

altasecHv4IpmeirDGSharedKeyTable  OBJECT-TYPE
    SYNTAX                    SEQUENCE OF AltasecHv4IpmeirDGSharedKeyEntry
    MAX-ACCESS                not-accessible
    STATUS                    current   
    DESCRIPTION
        "(U//FOUO,PR) The table containing proprietary information about
        IPMEIR Device Generated Shared Keys (DGSKs) and IPMEIR sequences."
    ::= { altasecHv4DGSharedKeyInformation 7 }
    
altasecHv4IpmeirDGSharedKeyEntry  OBJECT-TYPE
    SYNTAX            AltasecHv4IpmeirDGSharedKeyEntry
    MAX-ACCESS        not-accessible
    STATUS            current
    DESCRIPTION
        "(U//FOUO,PR) A row corresponding to an IPMEIR Device Generated Shared 
        Key (DGSK)"
    INDEX  { altasecHv4IpmeirDGSKIndex }
    ::= { altasecHv4IpmeirDGSharedKeyTable 1 }

AltasecHv4IpmeirDGSharedKeyEntry ::= SEQUENCE
    {
      altasecHv4IpmeirDGSKIndex           Unsigned32,
      altasecHv4IpmeirDGSKShortTitle      DGSharedKeyShortTitle,
      altasecHv4IpmeirDGSKEdition         PreplacedKeyEdition,
      altasecHv4IpmeirDGSKSegment         PreplacedKeySegment,
      altasecHv4IpmeirDGSKEffectiveDate   DateAndTime,
      altasecHv4IpmeirDGSKEndDate         DateAndTime,
      altasecHv4IpmeirDGSKLabel           SnmpAdminString,
      altasecHv4IpmeirDGSKMaterial        OCTET STRING,
      altasecHv4IpmeirDGSKType            INTEGER,
      altasecHv4IpmeirDGSKString          OCTET STRING,
      altasecHv4IpmeirDGSKIpv4Begin       IPAddress,
      altasecHv4IpmeirDGSKIpv4End         IPAddress,
      altasecHv4IpmeirDGSKIpv6Begin       IPAddress,
      altasecHv4IpmeirDGSKIpv6End         IPAddress,
      altasecHv4IpmeirDGSKIsLocal         TruthValue,
      altasecHv4IpmeirDGSKRowStatus       RowStatus
    }
    
altasecHv4IpmeirDGSKIndex OBJECT-TYPE
        SYNTAX     Unsigned32 
        MAX-ACCESS not-accessible
        STATUS     current
        DESCRIPTION
            "(U//FOUO) A unique numeric index that identifies this IPMEIR DGSK 
             or sequence"
        ::= { altasecHv4IpmeirDGSharedKeyEntry 1 }

altasecHv4IpmeirDGSKShortTitle OBJECT-TYPE
        SYNTAX     DGSharedKeyShortTitle 
        MAX-ACCESS read-only
        STATUS     current
        DESCRIPTION
            "(U//FOUO) The device-generated short title identifying this DGSK.
            
             (U//FOUO) If this is a sequence entry this column must not exist."
        ::= { altasecHv4IpmeirDGSharedKeyEntry 2 }
        
altasecHv4IpmeirDGSKEdition           OBJECT-TYPE
        SYNTAX          PreplacedKeyEdition
        MAX-ACCESS      read-only
        STATUS          current
        DESCRIPTION
            "(U//FOUO) The edition of this Device Generated Shared 
            key (DGSK). This column does not exist for sequence
            entries."
        ::= { altasecHv4IpmeirDGSharedKeyEntry 3 }

altasecHv4IpmeirDGSKSegment           OBJECT-TYPE
        SYNTAX          PreplacedKeySegment
        MAX-ACCESS      read-only
        STATUS          current
        DESCRIPTION
            "(U//FOUO) The segment number of this Device Generated Shared 
            key (DGSK). This column does not exist for sequence
            entries."
        ::= { altasecHv4IpmeirDGSharedKeyEntry 4 }

altasecHv4IpmeirDGSKEffectiveDate OBJECT-TYPE
        SYNTAX     DateAndTime
        MAX-ACCESS read-create
        STATUS     current
        DESCRIPTION
            "(U//FOUO) The effective date of this device-generated raw string. 
            This column does not exist for sequence entries."
        ::= { altasecHv4IpmeirDGSharedKeyEntry 5 }
        
altasecHv4IpmeirDGSKEndDate   OBJECT-TYPE
        SYNTAX          DateAndTime
        MAX-ACCESS      read-only
        STATUS          current
        DESCRIPTION
            "(U//FOUO) The effective end date and time of this
            Device Generated Shared Key (DGSK).  This object will be 
            automatically set from the chain information once the spot in 
            the chain is reached where this key becomes actively used. 
            This column only exists if the key is assigned as a Shared Secret."
        ::= { altasecHv4IpmeirDGSharedKeyEntry 6 }
        
altasecHv4IpmeirDGSKLabel OBJECT-TYPE
        SYNTAX     SnmpAdminString
        MAX-ACCESS read-create
        STATUS     current
        DESCRIPTION
            "(U//FOUO) A free text field allowing the user to tag the device-
             generated raw string with helpful information. For example, a label
             could indicate the intended usage of the device-generated raw
             string.
             
             (U//FOUO) If this entry relates to an IPMEIR sequence, the name
             of the sequence is returned. The name of a sequenceis not writable"
        ::= { altasecHv4IpmeirDGSharedKeyEntry 7 } 
        
altasecHv4IpmeirDGSKMaterial OBJECT-TYPE
        SYNTAX     OCTET STRING (SIZE(36))
        MAX-ACCESS read-create
        STATUS     current
        DESCRIPTION
             "(U//FOUO) The 72 hexadecimal character representation of the
             device-generated raw string (CRC included). Implementations must 
             restrict the display of this value to four hex characters at a 
             time. This column does not exist for sequence
             entries."
        ::= { altasecHv4IpmeirDGSharedKeyEntry 8 }

altasecHv4IpmeirDGSKType   OBJECT-TYPE
        SYNTAX     INTEGER { none(0), ipv4(1), ipv6(2), ipv4AndIpv6(3), 
                             domainName(4), email(5), keyId(6) }    
        MAX-ACCESS read-create
        STATUS     current
        DESCRIPTION
            "(U//FOUO) The IPMEIR Device Generated Shared Key type.
             
             Note that setting this column to any value other than 'none'
             causes the key to be assigned as a Shared Secret as long as
             the appropriate columns are also entered.
             
             If this DGSK has not been assigned as a shared secret this column
             should return none."
            
        ::= { altasecHv4IpmeirDGSharedKeyEntry 9 }
        
altasecHv4IpmeirDGSKString   OBJECT-TYPE
        SYNTAX     OCTET STRING    
        MAX-ACCESS read-create
        STATUS     current
        DESCRIPTION
            "(U//FOUO) If the DGSK is assigned with a type of domainName, 
             email, or keyId this column contains the string to set the value 
             to.  If this key is not one of those types this column should not
             exist."
            
        ::= { altasecHv4IpmeirDGSharedKeyEntry 10 }
        
altasecHv4IpmeirDGSKIpv4Begin   OBJECT-TYPE
        SYNTAX     IPAddress    
        MAX-ACCESS read-create
        STATUS     current
        DESCRIPTION
            "(U//FOUO) If the DGSK is assigned with a type of ipv4 or 
             ipv4AndIpv6 this column contains the begin IPv4 address to use. 
             If this key is not one of those types this column should not 
             exist."
            
        ::= { altasecHv4IpmeirDGSharedKeyEntry 11 }
        
altasecHv4IpmeirDGSKIpv4End   OBJECT-TYPE
        SYNTAX     IPAddress    
        MAX-ACCESS read-create
        STATUS     current
        DESCRIPTION
            "(U//FOUO) If the DGSK is assigned with a type of ipv4 or 
             ipv4AndIpv6 this column contains the end IPv4 address to use. 
             If this key is not one of those types this column should not 
             exist."
            
        ::= { altasecHv4IpmeirDGSharedKeyEntry 12 }

altasecHv4IpmeirDGSKIpv6Begin   OBJECT-TYPE
        SYNTAX     IPAddress    
        MAX-ACCESS read-create
        STATUS     current
        DESCRIPTION
            "(U//FOUO) If the DGSK is assigned with a type of ipv6 or 
             ipv4AndIpv6 this column contains the begin IPv6 address to use. 
             If this key is not one of those types this column should not 
             exist."
            
        ::= { altasecHv4IpmeirDGSharedKeyEntry 13 }
        
altasecHv4IpmeirDGSKIpv6End   OBJECT-TYPE
        SYNTAX     IPAddress    
        MAX-ACCESS read-create
        STATUS     current
        DESCRIPTION
            "(U//FOUO) If the DGSK is assigned with a type of ipv6 or 
             ipv4AndIpv6 this column contains the end IPv6 address to use. 
             If this key is not one of those types this column should not 
             exist."
            
        ::= { altasecHv4IpmeirDGSharedKeyEntry 14 }
        
altasecHv4IpmeirDGSKIsLocal   OBJECT-TYPE
        SYNTAX     TruthValue    
        MAX-ACCESS read-create
        STATUS     current
        DESCRIPTION
            "(U//FOUO) This column specifies whether this key will be set as 
             the local key."
            
        ::= { altasecHv4IpmeirDGSharedKeyEntry 15 }
           
altasecHv4IpmeirDGSKRowStatus OBJECT-TYPE
        SYNTAX     RowStatus  
        MAX-ACCESS read-create
        STATUS     current
        DESCRIPTION
            "(U//FOUO) The status of the row by which new entries may be created,
             existing entries enabled/disabled or existing entries deleted from
             this table.
        
             (U//FOUO) Entries created within this table may not become active
             unless all read-create columns of this table have valid values, as
             detailed by each individual column's description. Entries may be
             active, however, even though they are currently not used to protect
             traffic. For example, a device-generated raw string intended for 
             future use would have an effective start date beyond the current 
             time.
             
             (U//FOUO) Setting this column to destroy is synonymous
             with zeroizing the device-generated raw string. Any reference(s) 
             to this object upon setting this RowStatus to 'destroy' should be
             destroyed as well.
              
             (U//FOUO) At a minimum, implementations must support the 
             createAndGo, active and destroy management functions. Support for 
             createAndWait, notInService and notReady management functions is 
             optional.

             (U//FOUO) Destroying a sequence entry also destroys all keys associated
             with that sequence. " 
        ::= { altasecHv4IpmeirDGSharedKeyEntry 16 }

-- =======================
-- DGSharedKey Scalars
-- =======================

altasecHv4DGSKCOIValue       OBJECT-TYPE
        SYNTAX               INTEGER { 	ca(1), 
                                        nz(2), 
                                        us(7), 
                                        usHighRisk(8), 
                                        cceb(9), 
                                        coalition(10), 
                                        chvp(11), 
                                        nato(12), 
                                        natoNations(13), 
                                        uk(14), 
                                        au(15)  }
        MAX-ACCESS           read-write
        STATUS               current
        DESCRIPTION
            "(U//FOUO,PR) The Community of Interest for newly created 
            DGSharedKeys, setting this value will cause newly created
            keys to have the selected COI."
        ::= { altasecHv4DGSharedKeyInformation 8}

-- *************************************************
-- Alert Log Information
--

altasecHv4AlertLogTableCount OBJECT-TYPE
        SYNTAX          Unsigned32
        MAX-ACCESS      read-only
        STATUS          current
        DESCRIPTION
            "(U//FOUO,PR) The number of rows in the altasecHv4AlertLogTable."
        ::= { altasecHv4MgmtAlert 1 }
        
altasecHv4AlertLogTableLastChanged OBJECT-TYPE
        SYNTAX      TimeStamp
        MAX-ACCESS  read-only
        STATUS      current
        DESCRIPTION
            "(U//FOUO,PR) The value of sysUpTime the last time any entry
            in the altasecHv4AlertLogTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecHv4MgmtAlert 2 }

altasecHv4AlertLogClearAlerts OBJECT-TYPE
        SYNTAX          TruthValue
        MAX-ACCESS      read-write
        STATUS          current
        DESCRIPTION
            "(U//FOUO,PR) This object will always return false(2). Setting this
             object to true(1) will clear the alert Log."
        ::= { altasecHv4MgmtAlert 3 }
        
altasecHv4AlertLogTable		  OBJECT-TYPE
    SYNTAX                    SEQUENCE OF AltasecHv4AlertLogEntry
    MAX-ACCESS                not-accessible
    STATUS                    current
    DESCRIPTION
        "(U//FOUO,PR) The table containing proprietary information about
        alert log entries."
    ::= { altasecHv4MgmtAlert 4 }

altasecHv4AlertLogEntry  OBJECT-TYPE
    SYNTAX            AltasecHv4AlertLogEntry
    MAX-ACCESS        not-accessible
    STATUS            current
    DESCRIPTION
        "(U//FOUO,PR) A row indicating an alert log entry."
    INDEX  { altasecHv4AlertLogIndex }
    ::= { altasecHv4AlertLogTable 1 }

AltasecHv4AlertLogEntry ::= SEQUENCE
    {
        altasecHv4AlertLogIndex  		Unsigned32,
        altasecHv4AlertLogInfo			OCTET STRING
    }

altasecHv4AlertLogIndex  			OBJECT-TYPE
    SYNTAX                          Unsigned32
    MAX-ACCESS                      read-only
    STATUS                          current
    DESCRIPTION
        "(U//FOUO,PR) A monotonically increasing integer for the sole 
        purpose of indexing entries within the alert log. When it reaches 
        the maximum value, an extremely unlikely event, the agent wraps the
		value back to 1."
    ::= { altasecHv4AlertLogEntry 1 }
    
altasecHv4AlertLogInfo  				 OBJECT-TYPE
    SYNTAX                          	 OCTET STRING
    MAX-ACCESS                      	 read-only
    STATUS                          	 current
    DESCRIPTION
        "(U//FOUO) The information pertaining to the alert log event."
    ::= { altasecHv4AlertLogEntry 2 }
    
-- *************************************************
-- Audit Log Information
--

altasecHv4AuditLogTableCount OBJECT-TYPE
        SYNTAX          Unsigned32
        MAX-ACCESS      read-only
        STATUS          current
        DESCRIPTION
            "(U//FOUO,PR) The number of rows in the altasecHv4AuditLogTable."
        ::= { altasecHv4MgmtAudit 1 }
        
altasecHv4AuditLogTableLastChanged OBJECT-TYPE
        SYNTAX      TimeStamp
        MAX-ACCESS  read-only
        STATUS      current
        DESCRIPTION
            "(U//FOUO,PR) The value of sysUpTime the last time any entry
            in the altasecHv4AuditLogTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecHv4MgmtAudit 2 }

altasecHv4AuditLogCompression OBJECT-TYPE
        SYNTAX          TruthValue
        MAX-ACCESS      read-write
        STATUS          current
        DESCRIPTION
            "(U//FOUO,PR) Audit Log Compression enabled flag."
        ::= { altasecHv4MgmtAudit 3 }

altasecHv4AuditLogAdminStatus OBJECT-TYPE
        SYNTAX          INTEGER
                        {
                           allowAction(0),
                           retrieve(1),
                           delete(2)
                        }
        MAX-ACCESS      read-write
        STATUS          current
        DESCRIPTION
            "(U//FOUO,PR) This scalar controls the audit log handling process.
             When read, it will return allowAction if the last action succeeded,
             or the last requested action, if an action failed or is still in
             progress."
        ::= { altasecHv4MgmtAudit 4 }

altasecHv4AuditLogOperStatus  OBJECT-TYPE
        SYNTAX          INTEGER
                        {
                           noPendingOperation(0),
                           retrievalInProgress(1),
                           retrievalComplete(2),
                           deletionInProgress(3),
                           deletionComplete(4),
                           retrievalFailed(5),
                           deletionFailed(6)
                        }
        MAX-ACCESS      read-only
        STATUS          current
        DESCRIPTION
            "(U//FOUO) This scalar indicates the current state of the audit log.
             retrievalInProgress(1) indicates that an audit log retrieval is
             underway. retrievalComplete(2) indicates that the most recent audit
             log has been successfully retrieved. deletionInProgress(3)
             indicates that an audit log deletion is underway.
             deletionComplete(4) indicates that the audit log has been deleted
             successfully. retrievalFailed(5) indicates that the retrieval of
             the audit log failed. deletionFailed(6) indicates that the deletion
             of the audit log failed."
        ::= { altasecHv4MgmtAudit 5 }

altasecHv4AuditLogWarningPercentage OBJECT-TYPE
        SYNTAX          INTEGER
        MAX-ACCESS      read-only
        STATUS          current
        DESCRIPTION
            "(U//FOUO) The percentage of capacity at which the
            altasecHv4AuditLogWarning notification will be generated. A
            value of zero indicates that the notification should never
            be sent.  HAIPEs with a fixed warning percentage will not
            support SET operations to this object."
        ::= { altasecHv4MgmtAudit 6 }
        
        
altasecHv4AuditLogCapacityPercentage OBJECT-TYPE
        SYNTAX          INTEGER
        MAX-ACCESS      read-only
        STATUS          current
        DESCRIPTION
            "(U//FOUO) The current utilized percentage
            of storage capacity for audit events. When the log reaches
            its full capacity, the hNotificationLogFull notification will
            be generated. The fate of new events will be determined by
            the hNotificationLogFullBehavior object."
        ::= { altasecHv4MgmtAudit 7 }
        
altasecHv4AuditLogFullBehavior OBJECT-TYPE
        SYNTAX          INTEGER
        				{
                           logWrap(1),
                           logDrop(2)
                        }
        MAX-ACCESS      read-only
        STATUS          current
        DESCRIPTION
            "(U//FOUO) The object used for determining the fate of new
            audit events when the audit log has reached its maximum
            capacity. If the value is logWrap, new events will overwrite
            the oldest events. If the value is logDrop, new events will
            be dropped. Notifications for the event, if configured will
            still be sent.
			
            (U//FOUO) HAIPEs with a fixed behavior will not support SET
            operations to this object."
			
        ::= { altasecHv4MgmtAudit 8 }

altasecHv4AuditLogReset OBJECT-TYPE
        SYNTAX          TruthValue
        MAX-ACCESS      read-only
        STATUS          current
        DESCRIPTION
            "(U//FOUO) The object used for clearing the audit logs.
            Setting this object to true will reset (clear) all audit
            logs. When read, this object will always return false.
			
            (U//FOUO) Note that this will also reset the
            hAudCfgLogCount and hAuditCfgLogThrottled Unsigned32
            counters in the hAuditConfigTable."
        ::= { altasecHv4MgmtAudit 9 }
        
altasecHv4AuditLogTable		  OBJECT-TYPE
    SYNTAX                    SEQUENCE OF AltasecHv4AuditLogEntry
    MAX-ACCESS                not-accessible
    STATUS                    current
    DESCRIPTION
        "(U//FOUO,PR) The table containing proprietary information about
        alert log entries."
    ::= { altasecHv4MgmtAudit 10 }

altasecHv4AuditLogEntry  OBJECT-TYPE
    SYNTAX            AltasecHv4AuditLogEntry
    MAX-ACCESS        not-accessible
    STATUS            current
    DESCRIPTION
        "(U//FOUO,PR) A row indicating an alert log entry."
    INDEX  { altasecHv4AuditLogIndex }
    ::= { altasecHv4AuditLogTable 1 }

AltasecHv4AuditLogEntry ::= SEQUENCE
    {
        altasecHv4AuditLogIndex  		Unsigned32,
        altasecHv4AuditLogTime			DateAndTime,
        altasecHv4AuditLogSource		OCTET STRING,
        altasecHv4AuditLogInfo			OCTET STRING
    }

altasecHv4AuditLogIndex  			OBJECT-TYPE
    SYNTAX                          Unsigned32
    MAX-ACCESS                      read-only
    STATUS                          current
    DESCRIPTION
        "(U//FOUO,PR) A monotonically increasing integer for the sole 
        purpose of indexing entries within the audit log. When it reaches 
        the maximum value, an extremely unlikely event, the agent wraps the
		value back to 1."
    ::= { altasecHv4AuditLogEntry 1 }
    
altasecHv4AuditLogTime  				 OBJECT-TYPE
    SYNTAX                          	 DateAndTime
    MAX-ACCESS                      	 read-only
    STATUS                          	 current
    DESCRIPTION
        "(U//FOUO) The value of sysUpTime when the entry was placed in the log. 
        If the entry occurred before the most recent management system
        initialization this object value MUST be set to zero."
    ::= { altasecHv4AuditLogEntry 2 }

altasecHv4AuditLogSource  				 OBJECT-TYPE
    SYNTAX                          	 OCTET STRING
    MAX-ACCESS                      	 read-only
    STATUS                          	 current
    DESCRIPTION
        "(U//FOUO) The source of the audit log event."
    ::= { altasecHv4AuditLogEntry 3 }
    
altasecHv4AuditLogInfo  				 OBJECT-TYPE
    SYNTAX                          	 OCTET STRING
    MAX-ACCESS                      	 read-only
    STATUS                          	 current
    DESCRIPTION
        "(U//FOUO) The information pertaining to the audit log event."
    ::= { altasecHv4AuditLogEntry 4 }
    
-- *************************************************
-- APPKTA information 
--

altasecHv4APPKTATableCount  OBJECT-TYPE
        SYNTAX              Unsigned32
        MAX-ACCESS          read-only
        STATUS              current
        DESCRIPTION
            "(U//FOUO) The number of rows in the altasecHv4APPKTATable."
        ::= { altasecHv4APPKKeyInformation 1 }

altasecHv4APPKTATableLastChanged  OBJECT-TYPE
        SYNTAX                    TimeStamp
        MAX-ACCESS                read-only
        STATUS                    current
        DESCRIPTION
            "(U//FOUO) The value of hSystemUpTime the last time any entry in
             the altasecHv4APPKTATable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4APPKKeyInformation 2 }
        
altasecHv4APPKTATable         OBJECT-TYPE
    SYNTAX                    SEQUENCE OF AltasecHv4APPKTAEntry
    MAX-ACCESS                not-accessible
    STATUS                    current
    DESCRIPTION
        "(U//FOUO,PR) The table containing proprietary information about
        authenticate pre-placed key (APPK) trust anchors. Trust anchors are 
        denoted as Q-Keys in the device. This table includes a column to get 
        and set the label for the APPK Trust Anchor and retrieve other fields 
        for use with the HMI."
    ::= { altasecHv4APPKKeyInformation 3 }

altasecHv4APPKTAEntry         OBJECT-TYPE
    SYNTAX                    AltasecHv4APPKTAEntry
    MAX-ACCESS                not-accessible
    STATUS                    current
    DESCRIPTION
        "(U//FOUO,PR) A row describing the information about a particular 
         authenticated pre-placed key trust anchor (APPKTA also known as 
        q-key)."
        
        AUGMENTS   { hAPPKTATableEntry }
    ::= { altasecHv4APPKTATable 1 }

AltasecHv4APPKTAEntry ::= SEQUENCE
    {
        altasecHv4APPKTALabel        SnmpAdminString,
        altasecHv4APPKTAKMID         OCTET STRING,
        altasecHv4APPKTADOI          OCTET STRING,
        altasecHv4APPKTACheck        INTEGER,
        altasecHv4APPKTARowStatus    RowStatus
    }
    
altasecHv4APPKTALabel       OBJECT-TYPE
    SYNTAX                  SnmpAdminString
    MAX-ACCESS              read-write
    STATUS                  current
    DESCRIPTION
        "(U//FOUO) This object is a free text field allowing the user
         to tag Authenticated Pre-Placed Key Trust Anchors with helpful 
         information. For  example, a label could indicate the intended 
         classification of a particular APPKTA."
    ::= { altasecHv4APPKTAEntry 2 }
    
altasecHv4APPKTAKMID        OBJECT-TYPE
    SYNTAX                  OCTET STRING
    MAX-ACCESS              read-only
    STATUS                  current
    DESCRIPTION
        "(U//FOUO) The Key Material ID of the APPK."
    ::= { altasecHv4APPKTAEntry 3 }
    
altasecHv4APPKTADOI         OBJECT-TYPE
    SYNTAX                  OCTET STRING
    MAX-ACCESS              read-only
    STATUS                  current
    DESCRIPTION
        "(U//FOUO) A string representing the Date of Issuance of the
        APPK. The format of the string that is returned is mm/dd/yyyy."
    ::= { altasecHv4APPKTAEntry 4 }
    
altasecHv4APPKTACheck       OBJECT-TYPE
    SYNTAX                  INTEGER
    MAX-ACCESS              read-only
    STATUS                  current
    DESCRIPTION
        "(U//FOUO) The check field of the Authenticated Pre-Placed Key Trust 
        Anchor (APPKTA)."
    ::= { altasecHv4APPKTAEntry 5 }

altasecHv4APPKTARowStatus   OBJECT-TYPE
    SYNTAX                  RowStatus
    MAX-ACCESS              read-create
    STATUS                  current
    DESCRIPTION
        "(U//FOUO) The row status of the APPKTA. This value can be used to delete
        the APPKTA."
    ::= { altasecHv4APPKTAEntry 6 }
 


-- ************************************************************
-- Battery information 
-- ************************************************************

altasecHv4BatteryTableCount  OBJECT-TYPE
        SYNTAX               Unsigned32
        MAX-ACCESS           read-only
        STATUS               current
        DESCRIPTION
            "(U//FOUO) The number of rows in the altasecHv4BatteryTable."
        ::= { altasecHv4MgmtBattery 1 }

altasecHv4BatteryTableLastChanged     OBJECT-TYPE
        SYNTAX                        TimeStamp
        MAX-ACCESS                    read-only
        STATUS                        current
        DESCRIPTION
            "(U//FOUO) The value of hSystemUpTime the last time any entry in
             the altasecHv4BatteryTable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4MgmtBattery 2 }
        
altasecHv4BatteryTable        OBJECT-TYPE
    SYNTAX                    SEQUENCE OF AltasecHv4BatteryEntry
    MAX-ACCESS                not-accessible
    STATUS                    current
    DESCRIPTION
        "(U//FOUO,PR) The table describing the status of the batteries in
		the HAIPE."
    ::= { altasecHv4MgmtBattery 3 }

altasecHv4BatteryEntry   OBJECT-TYPE
    SYNTAX                    AltasecHv4BatteryEntry
    MAX-ACCESS                not-accessible
    STATUS                    current
    DESCRIPTION
        "(U//FOUO,PR) A row describing a particular battery level
        indication within the HAIPE"
    INDEX  { altasecHv4BatteryNumber }
    ::= { altasecHv4BatteryTable 1 }

AltasecHv4BatteryEntry ::= SEQUENCE
    {
        altasecHv4BatteryNumber            Unsigned32,
        altasecHv4BatteryOperStatus        INTEGER,
        altasecHv4BatteryChangeDate        DateAndTime
    }
    
altasecHv4BatteryNumber    OBJECT-TYPE
    SYNTAX                 Unsigned32
    MAX-ACCESS             not-accessible
    STATUS                 current
    DESCRIPTION
        "(U//FOUO) The unique number enumerating a given battery."
    ::= { altasecHv4BatteryEntry 1 }

altasecHv4BatteryOperStatus      OBJECT-TYPE
    SYNTAX                       INTEGER { nominal(1), low(2) }
    MAX-ACCESS                   read-only
    STATUS                       current
    DESCRIPTION
        "(U//FOUO) This object indicates the current state of a given
        battery. If hBatteryLevelWarningPercentage is a supported
        object then this object will be low when
        hBatteryLevelPercentage <= hBatteryLevelWarningPercentage."
    ::= { altasecHv4BatteryEntry 2 }

altasecHv4BatteryChangeDate     OBJECT-TYPE
    SYNTAX                      DateAndTime
    MAX-ACCESS                  read-write
    STATUS                      current
    DESCRIPTION
        "(U//FOUO) The date and time a changeable battery was
        last replaced. If a battery is changeable, but has not 
        been changed or the last change time was lost then this 
        value should be composed with all 0 values."
    ::= { altasecHv4BatteryEntry 3 }

-- ==================================
-- Bandwidth Management Settings
-- ==================================

altasecHv4BMSetting         OBJECT-TYPE
    SYNTAX                    OCTET STRING
    MAX-ACCESS                read-write
    STATUS                    current
    DESCRIPTION
        "(U//FOUO) Enables BM functionality.  An string equal to 'none' indicates disabled.
	       Any non-empty string, other than 'none',  must be a valid BM profile name"
        
    ::= { altasecHv4BandwidthManagement 1 }

-- **********************************************************************
-- Networking 
-- **********************************************************************


-- =======================
-- Networking Scalars
-- =======================

altasecHv4IPMulticastEnable OBJECT-TYPE
        SYNTAX           TruthValue
        MAX-ACCESS       read-write
        STATUS           current
        DESCRIPTION
            "(U//FOUO,PR) Global multicast enable Truth Value."
        ::= { altasecHv4NetScalars 1 }

altasecHv4IPReplayWindowSize OBJECT-TYPE
        SYNTAX            Unsigned32(32..32768)
        MAX-ACCESS        read-write
        STATUS            current
        DESCRIPTION
            "(U//FOUO,PR) The window size, in packets, that are used for
             anti-replay integrity, which detects arrival of duplicate IP
             datagrams (within a constrained window). In anti-replay integrity a
             packet's unique sequence number is compared to that of the
             previous packets (whose number to examine is defined by this value)
             on arrival.

             (U//FOUO,PR) This value may be 32, 64, 256, 1024, 4096, 8192,
             16384, or 32768. Note that in this progression 128, 512, and 2048
             are not supported."
        ::= { altasecHv4NetScalars 2 }

altasecHv4IPMulticastIGMPQueryEnable OBJECT-TYPE
        SYNTAX           TruthValue
        MAX-ACCESS       read-write
        STATUS           current
        DESCRIPTION
            "(U//FOUO,PR) IGMP query multicast enable Truth Value."
        ::= { altasecHv4NetScalars 3 }

altasecHv4IPMulticastIGMPVersion OBJECT-TYPE
        SYNTAX           INTEGER { none(0),
                                   version1(1),
                                   version2(2),
                                   version3(3)
                                 }
        MAX-ACCESS       read-write
        STATUS           current
        DESCRIPTION
            "(U//FOUO,PR) IGMP multicast version."
        ::= { altasecHv4NetScalars 4 }

altasecHv4IPAODVEnable OBJECT-TYPE
        SYNTAX           TruthValue
        MAX-ACCESS       read-write
        STATUS           current
        DESCRIPTION
            "(U//FOUO,PR) AODV enable Truth Value."
        ::= { altasecHv4NetScalars 5 }

altasecHv4IPMulticastMLDQueryEnable OBJECT-TYPE
        SYNTAX           TruthValue
        MAX-ACCESS       read-write
        STATUS           current
        DESCRIPTION
            "(U//FOUO,PR) MLD Query multicast enable Truth Value."
        ::= { altasecHv4NetScalars 6 }

altasecHv4IPMulticastMLDVersion OBJECT-TYPE
        SYNTAX           INTEGER { none(0), version1(1), version2(2) }
        MAX-ACCESS       read-write
        STATUS           current
        DESCRIPTION
            "(U//FOUO,PR) MLD multicast version."
        ::= { altasecHv4NetScalars 7 }
       
-- ========================
-- IPv4 Networking Table
-- =========================        
altasecHv4IPv4IfaceTable    OBJECT-TYPE
    SYNTAX                  SEQUENCE OF AltasecHv4IPv4IfaceEntry
    MAX-ACCESS              not-accessible
    STATUS                  current
    DESCRIPTION
        "(U//FOUO) The table containing a list of interface objects for
         the altasesec Haipe 4.0 IPv4 Interface table.
         This table contains information for both PT and CT interfaces.
         It augments the hIPv4IfaceTableEntry in the HAIPE-V4-NETWORKING-MIB."
    ::= { altasecHv4IPv4Augmentation 1 }

altasecHv4IPv4IfaceEntry      OBJECT-TYPE
    SYNTAX                  	AltasecHv4IPv4IfaceEntry
    MAX-ACCESS              	not-accessible
    STATUS                  	current
    DESCRIPTION
        "(U//FOUO) A row mapping IPv4 interface values to an interface."
    AUGMENTS { hIPv4IfaceTableEntry }
    ::= { altasecHv4IPv4IfaceTable 1 }

AltasecHv4IPv4IfaceEntry ::= SEQUENCE
  {
     altasecHv4IPv4IfaceICMPProcessPMTU            TruthValue,
     altasecHv4IPv4IfaceICMPProcessPMTUSetting     TruthValue,
     altasecHv4IPv4IfaceDHCP                       TruthValue,
     altasecHv4IPv4IfaceARPCacheTimeout            Unsigned32,
     altasecHv4IPv4IfaceProxyARP                   TruthValue,
     altasecHv4IPv4IfaceICMPProcessPING            TruthValue
  }
altasecHv4IPv4IfaceICMPProcessPMTU  OBJECT-TYPE
    SYNTAX                          TruthValue
    MAX-ACCESS                      read-only
    STATUS                          current
    DESCRIPTION
        "(U//FOUO,PR) Allows IPv4 Error ICMP messages (such as PMTU
         Discovery, and Source Quench) to be processed by the Linux kernel,
         these are then bypassed out to the PT network after being handled
         internally.

         (U//FOUO,PR) For the CT interface, if IPv4 Fixed Packet Length
         (FPL) is enabled, then this object is internally forced to False.
         
         (U//FOUO,PR) To read and write to its user setting see the
         altasecHv4IPv4IfaceICMPProcessPMTUSetting object. If FPL is 
         currently enabled, the user setting will be utilized once FPL 
         is disabled.
         
         (U//FOUO,PR) The PT interface is not affected by such behavior and  
         its value will mirror that of the altasecIfv4ICMPProcessPMTUSetting 
         object."
    ::= { altasecHv4IPv4IfaceEntry 1 }

altasecHv4IPv4IfaceICMPProcessPMTUSetting	OBJECT-TYPE
	SYNTAX                                  TruthValue
	MAX-ACCESS                              read-write
	STATUS                                  current
	DESCRIPTION
    	"(U//FOUO,PR) Allows IPv4 Error ICMP messages (such as PMTU
         Discovery, and Source Quench) to be processed by the Linux kernel,
         these are then bypassed out to the PT network after being handled
         internally. This is true(1) by default for the PT  interface and
         false(2) by default for the CT interface.

         (U//FOUO,PR) Note: This object is always writeable and contains,
         for the CT interface, the user setting to be applied should IPv4
         Fixed Packet Length (FPL) be disabled. To verify the current
         operational value for this object see the
         altasecIfv4ICMPProcessPMTU object."
	DEFVAL { false }
	::= { altasecHv4IPv4IfaceEntry 2 }

altasecHv4IPv4IfaceDHCP       OBJECT-TYPE
    SYNTAX                    TruthValue
    MAX-ACCESS                read-write
    STATUS                    current
    DESCRIPTION
        "(U//FOUO,PR) Interface DHCP enable Truth Value."
    DEFVAL { false }
    ::= { altasecHv4IPv4IfaceEntry 3 }

altasecHv4IPv4IfaceARPCacheTimeout    OBJECT-TYPE
    SYNTAX                            Unsigned32
    MAX-ACCESS                        read-write
    STATUS                            current
    DESCRIPTION
        "(U//FOUO,PR) ARP cache timeout in seconds."
    DEFVAL { 300 }
    ::= { altasecHv4IPv4IfaceEntry 4 }

altasecHv4IPv4IfaceProxyARP       OBJECT-TYPE
    SYNTAX                        TruthValue
    MAX-ACCESS                    read-write
    STATUS                        current
    DESCRIPTION
        "(U//FOUO,PR) Proxy ARP allows the PT (Red) interface to respond to
         ARP requests for hosts connected by a security association.
         
         (U//FOUO,PR)  Note: This only applies to the PT interface. 
         Values set to the CT interface will return error."
    DEFVAL { false }
    ::= { altasecHv4IPv4IfaceEntry 5 }  

altasecHv4IPv4IfaceICMPProcessPING  OBJECT-TYPE
    SYNTAX                          TruthValue
    MAX-ACCESS                      read-write
    STATUS                          current
    DESCRIPTION
        "(U//FOUO,PR) Allows IPv4 PING messages to be processed by the PT 
         Interface."

    ::= { altasecHv4IPv4IfaceEntry 6 }

-- =========================
-- IPv6 Networking Table
-- =========================

altasecHv4IPv6IfaceTable     OBJECT-TYPE
    SYNTAX              	  SEQUENCE OF AltasecHv4IPv6IfaceEntry
    MAX-ACCESS          	  not-accessible
    STATUS              	  current
    DESCRIPTION
        "(U//FOUO,PR) The table containing a list of ViaSat-specific 
         interface objects for altasec Haipe 4.0 IPv6 interface table.
         It augments the hIPv6IfaceTableEntry in the 
         HAIPE-V4-NETWORKING-MIB."
    ::= { altasecHv4IPv6Augmentation 1 }

altasecHv4IPv6IfaceEntry         OBJECT-TYPE
    SYNTAX                       AltasecHv4IPv6IfaceEntry
    MAX-ACCESS                   not-accessible
    STATUS                       current
    DESCRIPTION
        "(U//FOUO,PR) A row mapping IPv6 interface values to an interface."
    AUGMENTS { hIPv6IfaceTableEntry }
    ::= { altasecHv4IPv6IfaceTable 1 }

AltasecHv4IPv6IfaceEntry ::= SEQUENCE
  {
     altasecHv4IPv6IfaceICMPProcessPMTU          TruthValue,
     altasecHv4IPv6IfaceICMPProcessPMTUSetting   TruthValue,
     altasecHv4IPv6IfaceICMPProcessPING          TruthValue
  }

altasecHv4IPv6IfaceICMPProcessPMTU    OBJECT-TYPE
    SYNTAX                            TruthValue
    MAX-ACCESS                        read-only
    STATUS                            current
    DESCRIPTION
        "(U//FOUO,PR) Allows IPv6 Error ICMP messages (such as PMTU
         Discovery or Destination Unreachable) to be processed by the Linux
         kernel.

         (U//FOUO,PR) For the CT interface, if IPv6 Fixed Packet Length
         (FPL) is enabled, then this object is internally forced to False.
         
         (U//FOUO,PR)  To read and write to its user setting see the
         altasecHv4IPv6IfaceICMPProcessPMTUSetting object. If FPL is 
         currently enabled, the user setting will be utilized once FPL 
         is disabled.
         
         (U//FOUO,PR) The PT interface is not affected by such behavior and 
         its value will mirror that of the 
         altasecHv4IPv6IfaceICMPProcessPMTUSetting object."
    ::= { altasecHv4IPv6IfaceEntry 1 }

altasecHv4IPv6IfaceICMPProcessPMTUSetting    OBJECT-TYPE
    SYNTAX                                   TruthValue
    MAX-ACCESS                               read-write
    STATUS                                   current
    DESCRIPTION
        "(U//FOUO,PR) Allows IPv6 Error ICMP messages (such as PMTU
         Discovery or Destination Unreachable) to be processed by the 
         Linux kernel. 
         
         (U//FOUO,PR)  This is true(1) by default for the PT interface and
         false(2) by default for the CT interface.

         (U//FOUO,PR) Note: This object is always writeable and contains,
         for the CT interface, the user setting to be applied should IPv6
         Fixed Packet Length (FPL) be disabled.
          
         (U//FOUO,PR)  To verify the current operational value for this 
         object see the  altasecHv4IPv6Iface6ICMPProcessPMTU object."
    ::= { altasecHv4IPv6IfaceEntry 2 }
    
altasecHv4IPv6IfaceICMPProcessPING  OBJECT-TYPE
    SYNTAX                          TruthValue
    MAX-ACCESS                      read-write
    STATUS                          current
    DESCRIPTION
        "(U//FOUO,PR) Allows IPv6 PING messages to be processed by the PT 
         Interface."

    ::= { altasecHv4IPv6IfaceEntry 3 }

-- =========================
-- VLAN interface table.
-- =========================

altasecHv4VLANTableCount    OBJECT-TYPE
        SYNTAX              Unsigned32
        MAX-ACCESS          read-only
        STATUS              current
        DESCRIPTION
            "(U//FOUO,PR) The number of rows in the altasecHv4VLANTable."
        ::= { altasecHv4VLAN 1 }

altasecHv4VLANTableLastChanged OBJECT-TYPE
        SYNTAX                 TimeStamp
        MAX-ACCESS             read-only
        STATUS                 current
        DESCRIPTION
            "(U//FOUO,PR) The value of sysUpTime the last time any entry in
             the altasecVLANTable was modified, created, or deleted by
             either SNMP or other management method (e.g., via an HMI).

             (U//FOUO,PR) Managers can use this object to ensure that no
             changes to configuration of this table have happened since the
             last time it examined the table.

             (U//FOUO,PR) A value of 0 indicates that no entry has been
             changed since the agent initialized."
        ::= { altasecHv4VLAN 2 }

altasecHv4VLANTable OBJECT-TYPE
        SYNTAX          SEQUENCE OF AltasecHv4VLANEntry
        MAX-ACCESS      not-accessible
        STATUS          current
        DESCRIPTION
            "(U//FOUO,PR) IP configuration for VLAN Interfaces."
        ::= { altasecHv4VLAN 3 }

altasecHv4VLANEntry OBJECT-TYPE
        SYNTAX          AltasecHv4VLANEntry
        MAX-ACCESS      not-accessible
        STATUS          current
        DESCRIPTION
            "(U//FOUO,PR) A row defining the IP configuration for a VLAN
             Interface."
        INDEX   { altasecHv4VLANID }
        ::= { altasecHv4VLANTable 1 }

AltasecHv4VLANEntry ::= SEQUENCE
    {
        altasecHv4VLANID              Unsigned32,
        altasecHv4VLANAddressType     IPAddressType,
        altasecHv4VLANAddress         IPAddress,
        altasecHv4VLANPfxLen          Unsigned32,
        altasecHv4VLANMTU             Unsigned32,
        altasecHv4VLANMulticastEnable INTEGER,
        altasecHv4VLANRowStatus       RowStatus
    }

altasecHv4VLANID           OBJECT-TYPE
        SYNTAX             Unsigned32
        MAX-ACCESS         read-only
        STATUS             current
        DESCRIPTION
            "(U//FOUO,PR) The VLAN ID associated with this row."
        ::= { altasecHv4VLANEntry 1 }

altasecHv4VLANAddressType  OBJECT-TYPE
        SYNTAX             IPAddressType
        MAX-ACCESS         read-create
        STATUS             current
        DESCRIPTION
            "(U//FOUO,PR) The Internet address type for this interface. Only
             ipv4(1) is supported for V3, ipv6(2) is reserved for future use."
        DEFVAL { ipv4 }
        ::= { altasecHv4VLANEntry 2 }

altasecHv4VLANAddress      OBJECT-TYPE
        SYNTAX             IPAddress (SIZE (4|16))
        MAX-ACCESS         read-create
        STATUS             current
        DESCRIPTION
            "(U//FOUO,PR) The assigned Internet address for this interface."
        ::= { altasecHv4VLANEntry 3 }

altasecHv4VLANPfxLen       OBJECT-TYPE
        SYNTAX             Unsigned32
        MAX-ACCESS         read-create
        STATUS             current
        DESCRIPTION
            "(U//FOUO,PR) The prefix length for this interface."
        ::= { altasecHv4VLANEntry 4 }

altasecHv4VLANMTU          OBJECT-TYPE
        SYNTAX             Unsigned32
        MAX-ACCESS         read-create
        STATUS             current
        DESCRIPTION
            "(U//FOUO,PR) The MTU for this VLAN interface."
        DEFVAL { 1496 }
        ::= { altasecHv4VLANEntry 5 }

altasecHv4VLANMulticastEnable OBJECT-TYPE
        SYNTAX                TruthValue
        MAX-ACCESS            read-create
        STATUS                current
        DESCRIPTION
            "(U//FOUO,PR) Multicast Enable TruthValue for this VLAN Interface."
        DEFVAL { true }
        ::= { altasecHv4VLANEntry 6 }

altasecHv4VLANRowStatus    OBJECT-TYPE
        SYNTAX             RowStatus
        MAX-ACCESS         read-create
        STATUS             current
        DESCRIPTION
            "(U//FOUO,PR) RowStatus for VLAN Interface."
        ::= { altasecHv4VLANEntry 7 }       
        
-- =========================
-- Address Assignment table
-- =========================

altasecHv4AddrAssignTable OBJECT-TYPE
    SYNTAX           SEQUENCE OF AltasecHv4AddrAssignEntry
    MAX-ACCESS       not-accessible
    STATUS           current
    DESCRIPTION
        "(U//FOUO) The table containing a list of ViaSat-specific 
         objects for the altasec Haipe 4.0 Address Assignment table.
         This table augments the hAddressAssignTable in the 
         HAIPE-V4-NETWORKING-MIB."       
    ::= { altasecHv4AddrAssign 1 }

altasecHv4AddrAssignEntry OBJECT-TYPE
    SYNTAX           AltasecHv4AddrAssignEntry
    MAX-ACCESS       not-accessible
    STATUS           current
    DESCRIPTION
        "(U//FOUO) A row which describes an interface to IP address mapping
        This table is indexed by interface id, ip type, and ip address
        corrsponding with the hAddressAssignTable"
    AUGMENTS  { hAddressAssignTableEntry }
    ::= { altasecHv4AddrAssignTable 1 }

AltasecHv4AddrAssignEntry ::= SEQUENCE
{
   altasecHv4AddrAssignAddress            IPAddress,
   altasecHv4AddrAssignPrefixAdverOnly    TruthValue    
}

altasecHv4AddrAssignAddress OBJECT-TYPE
    SYNTAX                 IPAddress
    MAX-ACCESS             read-write
    STATUS                 current
    DESCRIPTION
        "(U//FOUO) The Internet Protocol addressing information for the
         interface indicated by this row. The size and format of this column
         is determined by the hAddressAssignType in the hAddressAssignTable.
         
         This object is used to modify the address of an existing IP address 
         currently configured(assigned) to an interface.  Note that during a 
         write (modify) this value will be different than the value of the 
         Address specfied as the INDEX for this table, i.e hAddressAssignAddr.  
         During a read this value will be the same as hAddressAssignAddr. "
    ::= { altasecHv4AddrAssignEntry 1 }

altasecHv4AddrAssignPrefixAdverOnly OBJECT-TYPE
    SYNTAX                 TruthValue
    MAX-ACCESS             read-only
    STATUS                 current
    DESCRIPTION
        "(U//FOUO) This object indicates whether the entry identified by
         the interface, type, and address instance values is designated 
         only to provide Prefix/Router Advertisement."
    ::= { altasecHv4AddrAssignEntry 2 }
       

-- =========================
-- Interface table
-- =========================

altasecHv4IfTable       OBJECT-TYPE
    SYNTAX              SEQUENCE OF AltasecHv4IfEntry
    MAX-ACCESS          not-accessible
    STATUS              current
    DESCRIPTION
        "(U//FOUO,PR) The table containing a list of ViaSat-specific 
         interface objects."
    ::= { altasecHv4Interface 1 }

altasecHv4IfEntry       OBJECT-TYPE
    SYNTAX              AltasecHv4IfEntry
    MAX-ACCESS          not-accessible
    STATUS              current
    DESCRIPTION
        "(U//FOUO) A row mapping interface variables for the PT and CT 
        interfaces."
    INDEX   { altasecHv4IfIndex }
    ::= { altasecHv4IfTable 1 }

AltasecHv4IfEntry ::= SEQUENCE
    {
        altasecHv4IfIndex                   Unsigned32,
        altasecHv4IfDuplex                  INTEGER,
        altasecHv4IfMode                    INTEGER,
        altasecHv4IfNegotiateSpeedDuplex    BITS,
        altasecHv4IfForceSpeed              Unsigned32,
        altasecHv4IfForceDuplex             INTEGER
    }

altasecHv4IfIndex       OBJECT-TYPE
     SYNTAX             Unsigned32
     MAX-ACCESS         not-accessible
     STATUS             current
     DESCRIPTION
         "(U//FOUO, PR) An unique numeric index that identifies this interface.
         Interface Index column is the primary index column for this table.
         Note, this column is populated internally and can not be read or
         configured."
     ::= { altasecHv4IfEntry 1 }
     
altasecHv4IfDuplex      OBJECT-TYPE
     SYNTAX             INTEGER { unknown(0),
                                  halfDuplex(1),
                                  fullDuplex(2)
                                }
     MAX-ACCESS         read-only
     STATUS             current
     DESCRIPTION
         "(U//FOUO, PR) Operational duplex setting of the current link."
     ::= { altasecHv4IfEntry 2 }

altasecHv4IfMode        OBJECT-TYPE
     SYNTAX             INTEGER { autoNegotiate(1), force(2) }
     MAX-ACCESS         read-write
     STATUS             current
     DESCRIPTION
         "(U//FOUO, PR) The mode by which link speed and duplex should be
          determined."
     DEFVAL { autoNegotiate }
     ::= { altasecHv4IfEntry 3 }

altasecHv4IfNegotiateSpeedDuplex OBJECT-TYPE
     SYNTAX             BITS { speed10MbitHalfDuplex(0),
                               speed10MbitFullDuplex(1),
                               speed100MbitHalfDuplex(2),
                               speed100MbitFullDuplex(3)
                             }
     MAX-ACCESS         read-write
     STATUS             current
     DESCRIPTION
         "(U//FOUO, PR) The speed and duplex modes that should be offered for
          negotiation. These settings are utilized when the altasecHv4IfMode
          object is set to autoNegotiate(1)."
     DEFVAL { { speed10MbitHalfDuplex, speed10MbitFullDuplex,
                speed100MbitHalfDuplex, speed100MbitFullDuplex } }
     ::= { altasecHv4IfEntry 4 }

altasecHv4IfForceSpeed  OBJECT-TYPE
     SYNTAX             Unsigned32
     MAX-ACCESS         read-write
     STATUS             current
     DESCRIPTION
         "(U//FOUO, PR) The speed mode that should be forced. This setting
          is utilized when the altasecHv4IfMode object is set to force(2)."
     DEFVAL { 100000000 }
     ::= { altasecHv4IfEntry 5 }

altasecHv4IfForceDuplex OBJECT-TYPE
     SYNTAX             INTEGER { unknown(0),
                                  halfDuplex(1),
                                  fullDuplex(2)
                                }
     MAX-ACCESS         read-write
     STATUS             current
     DESCRIPTION
         "(U//FOUO, PR) The duplex mode that should be forced. This setting
          is utilized when the altasecHv4IfMode object is set to force(2)."
     DEFVAL { fullDuplex }
     ::= { altasecHv4IfEntry 6 }
        

-- **********************************************************************
--
-- **********************************************************************

-- =========================
-- SFP table
-- =========================

altasecHv4SfpTable      OBJECT-TYPE
    SYNTAX              SEQUENCE OF AltasecHv4SfpEntry
    MAX-ACCESS          not-accessible
    STATUS              current
    DESCRIPTION
        "(U//FOUO,PR) The table containing a list of ViaSat-specific 
         SFP interface objects."
    ::= { altasecHv4SFP 1 }

altasecHv4SfpEntry      OBJECT-TYPE
    SYNTAX              AltasecHv4SfpEntry
    MAX-ACCESS          not-accessible
    STATUS              current
    DESCRIPTION
        "(U//FOUO) A row mapping interface variables for the PT and CT 
        SFP interfaces."
    INDEX   { altasecHv4SfpSide, altasecHv4IfIndex }
    ::= { altasecHv4SfpTable 1 }

AltasecHv4SfpEntry ::= SEQUENCE
    {
        altasecHv4SfpSide        Unsigned32,
        altasecHv4SfpIndex       Unsigned32,
        altasecHv4SfpStatus      INTEGER,
        altasecHv4SfpTrancver    OCTET STRING,
        altasecHv4SfpVendorOui   INTEGER,
        altasecHv4SfpVendorRev   OCTET STRING,
        altasecHv4SfpVendorName  OCTET STRING,
        altasecHv4SfpVendorPn    OCTET STRING
    }

altasecHv4SfpSide       OBJECT-TYPE
     SYNTAX             Unsigned32
     MAX-ACCESS         read-only
     STATUS             current
     DESCRIPTION
         "(U//FOUO, PR) An numeric index that identifies the side of the 
	 interface."
     ::= { altasecHv4SfpEntry 1 }
 
altasecHv4SfpIndex      OBJECT-TYPE
     SYNTAX             Unsigned32
     MAX-ACCESS         read-only
     STATUS             current
     DESCRIPTION
         "(U//FOUO, PR) An unique numeric index that identifies interface."
     ::= { altasecHv4SfpEntry 2 }    

altasecHv4SfpStatus	OBJECT-TYPE
     SYNTAX             INTEGER { sfpActionAllow(1),
                                  sfpActionWarn(2),
                                  sfpActionDisable(4)
                                }
     MAX-ACCESS         read-write
     STATUS             current
     DESCRIPTION
         "(U//FOUO, PR) A numeric value indicate the state of the SFP link."
     ::= { altasecHv4SfpEntry 3 }    

altasecHv4SfpTrancver	OBJECT-TYPE
     SYNTAX             OCTET STRING
     MAX-ACCESS         read-write
     STATUS             current
     DESCRIPTION
         "(U//FOUO, PR) Value that holds detailed information about the SFP."
     ::= { altasecHv4SfpEntry 4 }    

altasecHv4SfpVendorOui	OBJECT-TYPE
     SYNTAX             INTEGER
     MAX-ACCESS         read-write
     STATUS             current
     DESCRIPTION
         "(U//FOUO, PR) The SFP vendor OUI."
     ::= { altasecHv4SfpEntry 5 }    

altasecHv4SfpVendorRev	OBJECT-TYPE
     SYNTAX             OCTET STRING
     MAX-ACCESS         read-write
     STATUS             current
     DESCRIPTION
         "(U//FOUO, PR) The SFP vendor revision number."
     ::= { altasecHv4SfpEntry 6 }    

altasecHv4SfpVendorName	OBJECT-TYPE
     SYNTAX             OCTET STRING
     MAX-ACCESS         read-write
     STATUS             current
     DESCRIPTION
         "(U//FOUO, PR) The SFP vendor name."
     ::= { altasecHv4SfpEntry 7 }    

altasecHv4SfpVendorPn	OBJECT-TYPE
     SYNTAX             OCTET STRING
     MAX-ACCESS         read-write
     STATUS             current
     DESCRIPTION
         "(U//FOUO, PR) The SFP vendor part number."
     ::= { altasecHv4SfpEntry 8 }    
       
-- NOTE: missing column 9: Integer32 (CHIMERA Team)

-- **********************************************************************
--
-- **********************************************************************
    
-- *************************************************
-- Registration Discovery.
--
        
altasecHv4GDCRegistrationTableCount  OBJECT-TYPE
        SYNTAX              Unsigned32
        MAX-ACCESS          read-only
        STATUS              current
        DESCRIPTION
            "(U//FOUO) The number of rows in the altasecHv4GDCRegistrationTable."
        ::= { altasecHv4GDCRegistration 1 }

altasecHv4GDCRegistrationTableLastChanged  OBJECT-TYPE
        SYNTAX                    TimeStamp
        MAX-ACCESS                read-only
        STATUS                    current
        DESCRIPTION
            "(U//FOUO) The value of hSystemUpTime the last time any entry in
             the altasecHv4GDCRegistrationTable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4GDCRegistration 2 }

altasecHv4GDCRegistrationDefaultLifetime OBJECT-TYPE
        SYNTAX      Unsigned32
        UNITS       "seconds"
        MAX-ACCESS  read-write
        STATUS      current
        DESCRIPTION
            "(U//FOUO) This value indicates the default 'prefix
            lifetime parameter' to use when registering an address
            range with a discovery server.  This value should be used
            in registration messages when no other more specific
            information is available."
        DEFVAL { 4294967295 }
        ::= { altasecHv4GDCRegistration 3 }
        
altasecHv4GDCRegistrationTable         OBJECT-TYPE
    SYNTAX                    SEQUENCE OF AltasecHv4GDCRegistrationEntry
    MAX-ACCESS                not-accessible
    STATUS                    current
    DESCRIPTION
        "(U//FOUO) The table containing proprietary information about 
        a set of PT IP addresses (multicast or unicast) that discovery 
        REGISTRATION messages should be sent to.

        (U//FOUO) REGISTRATION messages will be sent to all addresses specified
        in this table.

        (U//FOUO) If the PT address of a given discovery registration
        destination is remote, the REGISTRATION messages to that server will 
        be treated as an outbound PT packet.  Hence, this message will need
        verification against the hPolicyRuleTable to determine the appropriate
        level of protection needed.

        (U//FOUO) Note: The HAIPE IS refers to this as the 'Registration
        Transmission Address Table'."
    ::= { altasecHv4GDCRegistration 4 }

altasecHv4GDCRegistrationEntry         OBJECT-TYPE
    SYNTAX                    AltasecHv4GDCRegistrationEntry
    MAX-ACCESS                not-accessible
    STATUS                    current
    DESCRIPTION
        "(U//FOUO,PR) A row describing the information about a particular 
         PT IP address that discovery REGISTRATION messages should be sent to."
        
        AUGMENTS   { hGDCRegistrationTableEntry }
    ::= { altasecHv4GDCRegistrationTable 1 }

AltasecHv4GDCRegistrationEntry ::= SEQUENCE
    {
        altasecHv4GDCRegistrationPriority        Unsigned32,
        altasecHv4GDCRegistrationStatus          AltasecHv4DiscoveryStatus
    }
    
altasecHv4GDCRegistrationPriority         OBJECT-TYPE
    SYNTAX                    Unsigned32
    MAX-ACCESS                read-write
    STATUS                    current
    DESCRIPTION
        "(U//FOUO) A unique numeric index for each configured 
        Registration Address.

        (U//FOUO) Note: Despite the name, this value does not imply 
        a fixed ordering or prioritization of Registration Addresses."
        
    ::= { altasecHv4GDCRegistrationEntry 4 }

altasecHv4GDCRegistrationStatus         OBJECT-TYPE
    SYNTAX                    AltasecHv4DiscoveryStatus
    MAX-ACCESS                read-only
    STATUS                    current
    DESCRIPTION
        "(U//FOUO) The current status of the Registration entry. The status
        may be active or inactive."
        
    ::= { altasecHv4GDCRegistrationEntry 5 }

-- *************************************************
-- Solicitation Delivery.
--
        
altasecHv4GDCSolicitDelivTableCount  OBJECT-TYPE
        SYNTAX              Unsigned32
        MAX-ACCESS          read-only
        STATUS              current
        DESCRIPTION
            "(U//FOUO) The number of rows in the altasecHv4GDCSolicitDelivTable."
        ::= { altasecHv4GDCSolicitDelivery 1 }

altasecHv4GDCSolicitDelivTableLastChanged  OBJECT-TYPE
        SYNTAX                    TimeStamp
        MAX-ACCESS                read-only
        STATUS                    current
        DESCRIPTION
            "(U//FOUO) The value of hSystemUpTime the last time any entry in
             the altasecHv4GDCSolicitDelivTable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4GDCSolicitDelivery 2 }
        
altasecHv4GDCSolicitDelivTable         OBJECT-TYPE
    SYNTAX                    SEQUENCE OF AltasecHv4GDCSolicitDelivEntry
    MAX-ACCESS                not-accessible
    STATUS                    current
    DESCRIPTION
        "(U//FOUO) This table is an extension of the hGDCSolicitDelivTable
        and provides access to the status and address range of each entry."
    ::= { altasecHv4GDCSolicitDelivery 3 }

altasecHv4GDCSolicitDelivEntry         OBJECT-TYPE
    SYNTAX                    AltasecHv4GDCSolicitDelivEntry
    MAX-ACCESS                not-accessible
    STATUS                    current
    DESCRIPTION
        "(U//FOUO,PR) A row describing the information about a particular 
         PT IP address that discovery REGISTRATION messages should be sent to."
        
        AUGMENTS   { hGDCSolicitDelivTableEntry }
    ::= { altasecHv4GDCSolicitDelivTable 1 }

AltasecHv4GDCSolicitDelivEntry ::= SEQUENCE
    {
        altasecHv4GDCSolicitDelivRangeStart      IPAddress,
        altasecHv4GDCSolicitDelivRangeEnd        IPAddress,
        altasecHv4GDCSolicitDelivStatus          OCTET STRING
    }
    
altasecHv4GDCSolicitDelivRangeStart         OBJECT-TYPE
    SYNTAX                    IPAddress
    MAX-ACCESS                read-write
    STATUS                    current
    DESCRIPTION
        "(U//FOUO) The starting IPv4 or IPv6 address for the range that
        will cause the device to initiate Dynamic Discovery."
        
    ::= { altasecHv4GDCSolicitDelivEntry 2 }
    
altasecHv4GDCSolicitDelivRangeEnd         OBJECT-TYPE
    SYNTAX                    IPAddress
    MAX-ACCESS                read-write
    STATUS                    current
    DESCRIPTION
        "(U//FOUO) The end IPv4 or IPv6 address for the range that
        will cause the device to initiate Dynamic Discovery."
        
    ::= { altasecHv4GDCSolicitDelivEntry 3 }

altasecHv4GDCSolicitDelivStatus         OBJECT-TYPE
    SYNTAX                    OCTET STRING
    MAX-ACCESS                read-only
    STATUS                    current
    DESCRIPTION
        "(U//FOUO) The current status of the solicitation delivery entry."
        
    ::= { altasecHv4GDCSolicitDelivEntry 4 }
    
-- *************************************************
-- Legacy Delivery.
--
        
altasecHv4LegacyDeliveryTableCount  OBJECT-TYPE
        SYNTAX              Unsigned32
        MAX-ACCESS          read-only
        STATUS              current
        DESCRIPTION
            "(U//FOUO) The number of rows in the altasecHv4LegacyDeliveryTable."
        ::= { altasecHv4LegacyDiscoveryDelivery 1 }

altasecHv4LegacyDeliveryTableLastChanged  OBJECT-TYPE
        SYNTAX                    TimeStamp
        MAX-ACCESS                read-only
        STATUS                    current
        DESCRIPTION
            "(U//FOUO) The value of hSystemUpTime the last time any entry in
             the altasecHv4Hv4LegacyDeliveryTable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4LegacyDiscoveryDelivery 2 }

altasecHv4DiscoveryProbeTimeout OBJECT-TYPE
    SYNTAX      Unsigned32
    UNITS       "seconds"
    MAX-ACCESS  read-write
    STATUS      current
    DESCRIPTION
        "(U//FOUO) The timeout value, in seconds, for PROBE messages.

        (U//FOUO) This only applies to sending discovery messages
        where an acknowledgement is expected and sending a request
        again is appropriate.
        "
    ::= { altasecHv4LegacyDiscoveryDelivery 3 }


altasecHv4DiscoveryProbeRetry OBJECT-TYPE
    SYNTAX      Unsigned32
    MAX-ACCESS  read-write
    STATUS      current
    DESCRIPTION
        "(U//FOUO) The number of times PROBE messages will be resent
        if no response is received within the timeout specified by
        the hDiscoveryProbeTimeout object.

        (U//FOUO) This only applies to sending discovery messages
        where an acknowledgement is expected and sending a request
        again is appropriate.
        "
    ::= { altasecHv4LegacyDiscoveryDelivery 4 }
    
altasecHv4LegacyDeliveryTable         OBJECT-TYPE
    SYNTAX                    SEQUENCE OF AltasecHv4LegacyDeliveryEntry
    MAX-ACCESS                not-accessible
    STATUS                    current
    DESCRIPTION
        "(U//FOUO) This table is an extension of the hLegacyDeliveryTable
        and provides access to the priority, status and address range of each entry."
    ::= { altasecHv4LegacyDiscoveryDelivery 5 }

altasecHv4LegacyDeliveryEntry         OBJECT-TYPE
    SYNTAX                    AltasecHv4LegacyDeliveryEntry
    MAX-ACCESS                not-accessible
    STATUS                    current
    DESCRIPTION
        "(U//FOUO,PR) A row describing the information about a particular 
         PT IP address that discovery REGISTRATION messages should be sent to."
        
        AUGMENTS   { hLegacyDeliveryTableEntry }
    ::= { altasecHv4LegacyDeliveryTable 1 }

AltasecHv4LegacyDeliveryEntry ::= SEQUENCE
    {
    	altasecHv4LegacyDeliveryPriority        Unsigned32,
      altasecHv4LegacyDeliveryRangeStart      IPAddress,
      altasecHv4LegacyDeliveryRangeEnd        IPAddress,
      altasecHv4LegacyDeliveryStatus          OCTET STRING
    }
    
altasecHv4LegacyDeliveryPriority         OBJECT-TYPE
    SYNTAX                    Unsigned32
    MAX-ACCESS                read-write
    STATUS                    current
    DESCRIPTION
        "(U//FOUO) A unique numeric index that indicates the priority of the GDC
         server in context. Lower values have a higher priority."
        
    ::= { altasecHv4LegacyDeliveryEntry 2 }
    
altasecHv4LegacyDeliveryRangeStart         OBJECT-TYPE
    SYNTAX                    IPAddress
    MAX-ACCESS                read-write
    STATUS                    current
    DESCRIPTION
        "(U//FOUO) The starting IPv4 or IPv6 address for the range that
        will cause the device to initiate Dynamic Discovery."
        
    ::= { altasecHv4LegacyDeliveryEntry 3 }
    
altasecHv4LegacyDeliveryRangeEnd         OBJECT-TYPE
    SYNTAX                    IPAddress
    MAX-ACCESS                read-write
    STATUS                    current
    DESCRIPTION
        "(U//FOUO) The end IPv4 or IPv6 address for the range that
        will cause the device to initiate Dynamic Discovery."
        
    ::= { altasecHv4LegacyDeliveryEntry 4 }

altasecHv4LegacyDeliveryStatus         OBJECT-TYPE
    SYNTAX                    OCTET STRING
    MAX-ACCESS                read-only
    STATUS                    current
    DESCRIPTION
        "(U//FOUO) The current status of the legacy discovery delivery entry."
        
    ::= { altasecHv4LegacyDeliveryEntry 5 }
    
-- *************************************************
-- RIP Discovery.
--
        
altasecHv4RIPTableCount     OBJECT-TYPE
        SYNTAX              Unsigned32
        MAX-ACCESS          read-only
        STATUS              current
        DESCRIPTION
            "(U//FOUO) The number of rows in the altasecHv4RIPTable."
        ::= { altasecHv4RIPConfig 1 }

altasecHv4RIPTableLastChanged  OBJECT-TYPE
        SYNTAX                    TimeStamp
        MAX-ACCESS                read-only
        STATUS                    current
        DESCRIPTION
            "(U//FOUO) The value of hSystemUpTime the last time any entry in
             the altasecHv4RIPTable was modified, created, or deleted
             by either SNMP or other management method (e.g., via an HMI).

             (U//FOUO) Managers can use this object to ensure that no
             changes to configuration of this table have happened since
             the last time it examined the table.

             (U//FOUO) A value of 0 indicates that no entry has been
             changed since the agent initialized."
        ::= { altasecHv4RIPConfig 2 }
    
altasecHv4RIPTable         	OBJECT-TYPE
    SYNTAX                    SEQUENCE OF AltasecHv4RIPEntry
    MAX-ACCESS                not-accessible
    STATUS                    current
    DESCRIPTION
        "(U//FOUO) This table is an extension of the hRIPTable."
    ::= { altasecHv4RIPConfig 3 }

altasecHv4RIPEntry       OBJECT-TYPE
    SYNTAX                    AltasecHv4RIPEntry
    MAX-ACCESS                not-accessible
    STATUS                    current
    DESCRIPTION
        "(U//FOUO,PR) A row describing the information about a particular 
         RIP entry."
        
        AUGMENTS   { hRIPTableEntry }
    ::= { altasecHv4RIPTable 1 }

AltasecHv4RIPEntry ::= SEQUENCE
    {
    	altasecHv4RIPExpirationTimer        Unsigned32,
        altasecHv4RIPFlushTimer             Unsigned32,
        altasecHv4RIPUpdateTimer            Unsigned32,
        altasecHv4RIPReceive                INTEGER
    }
    
altasecHv4RIPExpirationTimer  OBJECT-TYPE
    SYNTAX                    Unsigned32 (5..999)
    UNITS                     "seconds"
    MAX-ACCESS                read-write
    STATUS                    current
    DESCRIPTION
        "(U//FOUO,PR) The RIP expiration timer, in seconds."
        
    ::= { altasecHv4RIPEntry 3 }
    
altasecHv4RIPFlushTimer       OBJECT-TYPE
    SYNTAX                    Unsigned32 (5..999)
    UNITS                     "seconds"
    MAX-ACCESS                read-write
    STATUS                    current
    DESCRIPTION
        "(U//FOUO,PR) The RIP flush timer, in seconds."
        
    ::= { altasecHv4RIPEntry 4 }
    
altasecHv4RIPUpdateTimer      OBJECT-TYPE
    SYNTAX                    Unsigned32 (5..999)
    UNITS                     "seconds"
    MAX-ACCESS                read-write
    STATUS                    current
    DESCRIPTION
        "(U//FOUO,PR) The RIP update timer, in seconds."
        
    ::= { altasecHv4RIPEntry 5 }
    
altasecHv4RIPReceive OBJECT-TYPE
    SYNTAX   INTEGER {
                    doNotReceive (1),
                    rip1 (2),
                    rip2 (3),
                    rip1OrRip2 (4),
                    ripNG (5)
                 }
    MAX-ACCESS	 read-write
    STATUS		 current
    DESCRIPTION
        "(U//FOUO,PR) The version(s) of RIP updates that are to be accepted.  
        Note that rip2 and rip1OrRip2 implies reception of multicast
        packets.
        
        (U//FOUO,PR) This column extends the haipe version to identify the 
        various types."
    DEFVAL { doNotReceive }
    ::= { altasecHv4RIPEntry 6 }
    
END

--
--            UNCLASSIFIED//FOR OFFICIAL USE ONLY, PROPIN
--
