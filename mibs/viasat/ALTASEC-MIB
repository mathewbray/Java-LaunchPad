--
--            UNCLASSIFIED//FOR OFFICIAL USE ONLY, PROPIN
--
-- This entire document, which defines AltaSec Proprietary MIB objects in the
-- SMIv2 language should be considered U//FOUO,PR.
--
-- The data that will be transmitted on the wire as a result of
-- accessing these MIB objects MUST NOT BE CONSIDERED U//FOUO and is
-- subject to separate classification.  The classification level of this
-- data is not defined or within the scope of this document.
--

ALTASEC-MIB DEFINITIONS ::= BEGIN

IMPORTS
    OBJECT-TYPE, NOTIFICATION-TYPE,
    enterprises, Integer32, Unsigned32,
    Counter64, MODULE-IDENTITY            FROM SNMPv2-SMI
    RowStatus, DateAndTime, TruthValue,
    TimeStamp, DisplayString              FROM SNMPv2-TC
    SnmpAdminString                       FROM SNMP-FRAMEWORK-MIB
    InterfaceIndex, ifEntry               FROM IF-MIB
    InetAddressType, InetAddress,
    InetAddressPrefixLength               FROM INET-ADDRESS-MIB
    hrSystemDate                          FROM HOST-RESOURCES-MIB
    HaipeSecurityLevel,
    HaipeSecurityAuthority,
    HaipeSide                             FROM HAIPE-TC-MIB
    hStationID, hBatteryEntry             FROM HAIPE-MANAGEMENT-MIB
    ipv4InterfaceEntry,
    ipv6InterfaceEntry                    FROM IP-MIB
    PPKShortTitle,
    PPKEdition,
    HaipeSegment,
    hIPhRuleEntry                         FROM HAIPE-TRAFFIC-PROTECTION-MIB
    hTopologyEntry,
    hRIPConfEntry                         FROM HAIPE-NETWORKING-DISCOVERY-MIB
    hPPKChainEntry,
    HaipeIntegrityAlgorithm,
    hIPhFFSAEntry, hTPSAEntry             FROM HAIPE-TRAFFIC-PROTECTION-MIB
    usmUserSecurityName                   FROM SNMP-USER-BASED-SM-MIB;


altasecMIB MODULE-IDENTITY
    LAST-UPDATED "200912100000Z"
    ORGANIZATION "ViaSat"
    CONTACT-INFO
         "(U//FOUO) Not Available"
    DESCRIPTION
        "(U//FOUO) This MIB defines the AltaSec Proprietary MIB objects."
    REVISION     "200912100000Z"
    DESCRIPTION
        "(U//FOUO,PR) AltaSec Proprietary MIB objects for HAIPE 3.1.2.
         For internal 3.1.7 build."
    REVISION     "200910210000Z"
    DESCRIPTION
        "(U//FOUO,PR) First draft AltaSec Proprietary MIB objects for HAIPE
         3.1.2."
    REVISION     "200805140000Z"
    DESCRIPTION
        "(U//FOUO,PR) AltaSec Proprietary MIB objects for HAIPE 3.0.2."
    ::= { viaSat 3 }

viaSat OBJECT IDENTIFIER ::= { enterprises 8698 }

--
-- AltaSec Information Segments
-- Note: These OIDs match the structure of the HAIPE MIBs where extensions are
--       present.
--

altasecMgmt              OBJECT IDENTIFIER ::= { altasecMIB 1 }
altasecNetworking        OBJECT IDENTIFIER ::= { altasecMIB 2 }
altasecNetDiscovery      OBJECT IDENTIFIER ::= { altasecMIB 3 }
altasecTrafficProtection OBJECT IDENTIFIER ::= { altasecMIB 4 }
altasecKeyTransfer       OBJECT IDENTIFIER ::= { altasecMIB 5 }


--
-- Management Group
--

altasecMgmtRemote               OBJECT IDENTIFIER ::= { altasecMgmt 1 }
altasecMgmtRemoteNotifications  OBJECT IDENTIFIER ::= { altasecMgmtRemote 0 }
altasecMgmtTemps                OBJECT IDENTIFIER ::= { altasecMgmt 2 }
altasecMgmtTempsNotifications   OBJECT IDENTIFIER ::= { altasecMgmtTemps 0 }
altasecMgmtSigDL                OBJECT IDENTIFIER ::= { altasecMgmt 3 }
altasecMgmtSigDLNotifications   OBJECT IDENTIFIER ::= { altasecMgmtSigDL 0 }
altasecMgmtReset                OBJECT IDENTIFIER ::= { altasecMgmt 4 }
altasecMgmtResetNotifications   OBJECT IDENTIFIER ::= { altasecMgmtReset 0 }
altasecMgmtAlert                OBJECT IDENTIFIER ::= { altasecMgmt 5 }
altasecMgmtAlertNotifications   OBJECT IDENTIFIER ::= { altasecMgmtAlert 0 }
altasecMgmtTrap                 OBJECT IDENTIFIER ::= { altasecMgmt 6 }
altasecMgmtTrapNotifications    OBJECT IDENTIFIER ::= { altasecMgmtTrap 0 }
altasecMgmtTrapObjects          OBJECT IDENTIFIER ::= { altasecMgmtTrapNotifications 0 }
altasecMgmtAudit                OBJECT IDENTIFIER ::= { altasecMgmt 7 }
altasecMgmtAuditNotifications   OBJECT IDENTIFIER ::= { altasecMgmtAudit 0 }
altasecMgmtBattery              OBJECT IDENTIFIER ::= { altasecMgmt 8 }
altasecMgmtBatteryNotifications OBJECT IDENTIFIER ::= { altasecMgmtBattery 0 }
altasecMgmtSession              OBJECT IDENTIFIER ::= { altasecMgmt 9 }
altasecMgmtSessionNotifications OBJECT IDENTIFIER ::= { altasecMgmtSession 0 }
altasecMgmtCIK                  OBJECT IDENTIFIER ::= { altasecMgmt 10 }
altasecMgmtCIKNotifications     OBJECT IDENTIFIER ::= { altasecMgmtCIK 0 }

--
-- Discovery Group
--

altasecNetDiscoveryPeer  OBJECT IDENTIFIER ::= { altasecNetDiscovery 2 }
altasecNetDiscoveryLocal OBJECT IDENTIFIER ::= { altasecNetDiscovery 3 }
altasecNetDiscoveryOSPF  OBJECT IDENTIFIER ::= { altasecNetDiscovery 4 }

altasecNetDiscoveryPeerConfig      OBJECT IDENTIFIER ::= { altasecNetDiscoveryPeer 1 }
altasecNetTopologyPeerAssignments  OBJECT IDENTIFIER ::= { altasecNetDiscoveryPeer 2 }

altasecRIPConfAugmentation  OBJECT IDENTIFIER ::= { altasecNetDiscoveryLocal 6 }

altasecNetDiscoveryOSPFGeneral     OBJECT IDENTIFIER ::= { altasecNetDiscoveryOSPF 1 }
altasecNetDiscoveryOSPFPT          OBJECT IDENTIFIER ::= { altasecNetDiscoveryOSPF 2 }
altasecNetDiscoveryOSPFAPN         OBJECT IDENTIFIER ::= { altasecNetDiscoveryOSPF 3 }

--
-- Networking Information Segments
--
altasecNetNotifications  OBJECT IDENTIFIER ::= { altasecNetworking 0 }
-- unofficial definition (CHIMERA Team)
altasecNetObjects        OBJECT IDENTIFIER ::= { altasecNetNotifications 0 }
altasecNetIP             OBJECT IDENTIFIER ::= { altasecNetworking 2 }

--
-- AltaSec Traffic Protection Information Segments
--

altasecTPCryptography       OBJECT IDENTIFIER ::= { altasecTrafficProtection 2 }
altasecTPPolicyObjects      OBJECT IDENTIFIER ::= { altasecTrafficProtection 5 }

altasecCryptoControl        OBJECT IDENTIFIER ::= { altasecTPCryptography 1 }
altasecKeyInformation       OBJECT IDENTIFIER ::= { altasecTPCryptography 2 }

altasecPPKInformation       OBJECT IDENTIFIER ::= { altasecKeyInformation 2 }

altasecPPKKeyInformation    OBJECT IDENTIFIER ::= { altasecPPKInformation 1 }
altasecPPKChainInformation  OBJECT IDENTIFIER ::= { altasecPPKInformation 4 }

-- altasecTPPolicyObjects tree
altasecTPPolicyManageObjects     OBJECT IDENTIFIER ::= { altasecTPPolicyObjects 1 }

-- altasecTPPolicyManageObjects tree
altasecTPSecurityPolicyDatabase  OBJECT IDENTIFIER ::= { altasecTPPolicyManageObjects 2 }
altasecTPSecurityAssocDatabase   OBJECT IDENTIFIER ::= { altasecTPPolicyManageObjects 3 }

-- In-Band OID tree
altasecKTIBConfigObjects          OBJECT IDENTIFIER ::= { altasecKeyTransfer 3 }

altasecKTIBClientObjects          OBJECT IDENTIFIER ::= { altasecKTIBConfigObjects 1 }
altasecKTIBControllerObjects      OBJECT IDENTIFIER ::= { altasecKTIBConfigObjects 2 }

altasecKTIBControllerInformation  OBJECT IDENTIFIER ::= { altasecKTIBClientObjects 1 }
altasecKTIBDisabledKeyInformation OBJECT IDENTIFIER ::= { altasecKTIBClientObjects 2 }
altasecKTIBClientsInformation     OBJECT IDENTIFIER ::= { altasecKTIBControllerObjects 1 }


-- *************************************************
-- Remote Management.

-- added old syntax values to description (CHIMERA Team)
altasecMgmtRemoteSetting    OBJECT-TYPE
        SYNTAX          INTEGER
                        {
                           disabled(0),
                           everyone(1),
                           ipTable(2)
                        }
        MAX-ACCESS       read-write
        STATUS           current
        DESCRIPTION
            "(U//FOUO,PR) The setting for how remote management should be
             handled. disabled indicates that remote management is disabled.
             everyone indicates that everyone is able to remotely manage
             this device. ipTable indicates that the 
             altasecMgmtRemoteAddressTable is used to filter who is remotely
             able to manage this device.

             (U//FOUO,PR) Old values: enabled(0), disabled(1), single(2)."
        DEFVAL { disabled }
        ::= { altasecMgmtRemote 1 }

altasecMgmtRemoteAddress4 OBJECT-TYPE
        SYNTAX           InetAddress
        MAX-ACCESS       read-write
        STATUS           current
        DESCRIPTION
            "(U//FOUO,PR) Remote Management IPv4 address."
        ::= { altasecMgmtRemote 2 }

altasecMgmtRemoteAddress6 OBJECT-TYPE
        SYNTAX           InetAddress
        MAX-ACCESS       read-write
        STATUS           current
        DESCRIPTION
            "(U//FOUO,PR) Remote Management IPv6 address."
        ::= { altasecMgmtRemote 3 }

altasecMgmtUDPZeroizeInterval  OBJECT-TYPE
        SYNTAX           Unsigned32
        MAX-ACCESS       read-write
        STATUS           current
        DESCRIPTION
            "(U//FOUO,PR) UDP Management interval before a zeroize executes."
        DEFVAL { 50 }
        ::= { altasecMgmtRemote 4 }

altasecMgmtUDPZeroize    OBJECT-TYPE
        SYNTAX           TruthValue
        MAX-ACCESS       read-write
        STATUS           current
        DESCRIPTION
            "(U//FOUO,PR) UDP Management zeroize flag."
        ::= { altasecMgmtRemote 5 }

altasecMgmtUDPPort OBJECT-TYPE
        SYNTAX           Unsigned32
        MAX-ACCESS       read-write
        STATUS           current
        DESCRIPTION
            "(U//FOUO,PR) UDP Management IP port."
        DEFVAL { 3000 }
        ::= { altasecMgmtRemote 6 }

altasecMgmtUDPRememberHbt OBJECT-TYPE
        SYNTAX           TruthValue
        MAX-ACCESS       read-write
        STATUS           current
        DESCRIPTION
            "(U//FOUO,PR) UDP Management Remember Heartbeat flag. Setting this
            flag causes the INE to remember if a Heartbeat has been previously
            received across reboots."
        ::= { altasecMgmtRemote 7 }

-- *************************************************
-- Remote Management Address Table.

altasecMgmtRemoteAddressTableCount       OBJECT-TYPE
        SYNTAX              Unsigned32
        MAX-ACCESS          read-only
        STATUS              current
        DESCRIPTION
            "(U//FOUO,PR) The number of rows in the altasecMgmtRemoteAddressTable."
        ::= { altasecMgmtRemote 8 }

-- removed conflicting OID assignment (CHIMERA Team)
-- altasecMgmtRemoteAddressTableTableLastChanged OBJECT-TYPE
--         SYNTAX              TimeStamp
--         MAX-ACCESS          read-only
--         STATUS              current
--         DESCRIPTION
--             "(U//FOUO,PR) The value of sysUpTime the last time any entry in
--              the altasecMgmtRemoteAddressTable was modified, created, or deleted by
--              either SNMP or other management method (e.g., via an HMI).
-- 
--              (U//FOUO,PR) Managers can use this object to ensure that no
--              changes to configuration of this table have happened since the
--              last time it examined the table.
-- 
--              (U//FOUO,PR) A value of 0 indicates that no entry has been
--              changed since the agent initialized."
--         ::= { altasecMgmtRemote 9 }

altasecMgmtRemoteAddressTable OBJECT-TYPE
        SYNTAX          SEQUENCE OF ALTASECMgmtRemoteAddressEntry
        MAX-ACCESS      not-accessible
        STATUS          current
        DESCRIPTION
            "(U//FOUO,PR) A table containing a list of networks that are 
             allowed to remotely manage this HAIPE. Note that networks 
             must be distinct (i.e. An Entry within this table cannot be 
             a sub net of another entry)."
        ::= { altasecMgmtRemote 9 }

altasecMgmtRemoteAddressEntry OBJECT-TYPE
        SYNTAX          ALTASECMgmtRemoteAddressEntry
        MAX-ACCESS      not-accessible
        STATUS          current
        DESCRIPTION
            "(U//FOUO,PR) A row defining the IP configuration for a remote management
             network."
        INDEX   { altasecMgmtRemoteAddressType,
                  altasecMgmtRemoteAddressStart }
        ::= { altasecMgmtRemoteAddressTable 1 }

ALTASECMgmtRemoteAddressEntry ::= SEQUENCE
    {
        altasecMgmtRemoteAddressType            InetAddressType,
        altasecMgmtRemoteAddressStart           InetAddress,
        altasecMgmtRemoteAddressPrefixLength    Unsigned32,
        altasecMgmtRemoteAddressLabel           OCTET STRING,
        altasecMgmtRemoteAddressRowStatus       RowStatus
    }

altasecMgmtRemoteAddressType     OBJECT-TYPE
        SYNTAX             InetAddressType
        MAX-ACCESS         read-create
        STATUS             current
        DESCRIPTION
            "(U//FOUO,PR) The Internet address type for this remote management 
             network."
        DEFVAL { ipv4 }
        ::= { altasecMgmtRemoteAddressEntry 1 }

altasecMgmtRemoteAddressStart         OBJECT-TYPE
        SYNTAX             InetAddress (SIZE (4|16))
        MAX-ACCESS         read-create
        STATUS             current
        DESCRIPTION
            "(U//FOUO,PR) The starting IP address for the remote management 
             network."
        ::= { altasecMgmtRemoteAddressEntry 2 }
        
altasecMgmtRemoteAddressPrefixLength         OBJECT-TYPE
        SYNTAX             Unsigned32 (0..128)
        MAX-ACCESS         read-create
        STATUS             current
        DESCRIPTION
            "(U//FOUO,PR) The prefix length for this remote network."
        ::= { altasecMgmtRemoteAddressEntry 3 }

altasecMgmtRemoteAddressLabel              OBJECT-TYPE
        SYNTAX             OCTET STRING (SIZE(1..32))
        MAX-ACCESS         read-create
        STATUS             current
        DESCRIPTION
            "(U//FOUO,PR) An administratively assigned label identifying 
             this entry."
        ::= { altasecMgmtRemoteAddressEntry 4 }
        
altasecMgmtRemoteAddressRowStatus         OBJECT-TYPE
        SYNTAX             RowStatus
        MAX-ACCESS         read-create
        STATUS             current
        DESCRIPTION
            "(U//FOUO,PR) Row status for the Remote Management entry."
        ::= { altasecMgmtRemoteAddressEntry 5 }

altasecMgmtClearAlerts OBJECT-TYPE
        SYNTAX          TruthValue
        MAX-ACCESS      read-write
        STATUS          current
        DESCRIPTION
            "(U//FOUO,PR) This object will always return false(2). Setting this
             object to true(1) will clear the alert Log."
        ::= { altasecMgmtAlert 1 }

altasecMgmtRebootRequired OBJECT-TYPE
        SYNTAX            TruthValue
        MAX-ACCESS        read-only
        STATUS            current
        DESCRIPTION
            "(U//FOUO,PR) Flag indicating if configuration settings have changed
             which require a reboot to take effect."
        ::= { altasecMgmtAlert 2 }

altasecAuditLogCompression OBJECT-TYPE
        SYNTAX          TruthValue
        MAX-ACCESS      read-write
        STATUS          current
        DESCRIPTION
            "(U//FOUO,PR) Audit Log Compression enabled flag."
        ::= { altasecMgmtAudit 1 }

altasecAuditLogAdminStatus OBJECT-TYPE
        SYNTAX          INTEGER
                        {
                           allowAction(0),
                           retrieve(1),
                           delete(2)
                        }
        MAX-ACCESS      read-write
        STATUS          current
        DESCRIPTION
            "(U//FOUO,PR) This scalar controls the audit log handling process.
             When read, it will return allowAction if the last action succeeded,
             or the last requested action, if an action failed or is still in
             progress."
        ::= { altasecMgmtAudit 2 }

altasecAuditLogOperStatus  OBJECT-TYPE
        SYNTAX          INTEGER
                        {
                           noPendingOperation(0),
                           retrievalInProgress(1),
                           retrievalComplete(2),
                           deletionInProgress(3),
                           deletionComplete(4),
                           retrievalFailed(5),
                           deletionFailed(6)
                        }
        MAX-ACCESS      read-only
        STATUS          current
        DESCRIPTION
            "(U//FOUO) This scalar indicates the current state of the audit log.
             retrievalInProgress(1) indicates that an audit log retrieval is
             underway. retrievalComplete(2) indicates that the most recent audit
             log has been successfully retrieved. deletionInProgress(3)
             indicates that an audit log deletion is underway.
             deletionComplete(4) indicates that the audit log has been deleted
             successfully. retrievalFailed(5) indicates that the retrieval of
             the audit log failed. deletionFailed(6) indicates that the deletion
             of the audit log failed."
        ::= { altasecMgmtAudit 3 }

altasecMgmtSendTrap OBJECT-TYPE
        SYNTAX          INTEGER
        MAX-ACCESS      read-write
        STATUS          current
        DESCRIPTION
            "(U//FOUO,PR) Trigger INE to send an SNMP Trap, not accessible by
             users."
        DEFVAL { 0 }
        ::= { altasecMgmtTrap 1 }

altasecMgmtSendPassExpTrap OBJECT-TYPE
        SYNTAX          OCTET STRING (SIZE(1..32))
        MAX-ACCESS      read-write
        STATUS          current
        DESCRIPTION
            "(U//FOUO,PR) Trigger INE to send an SNMP Trap indicating a user's
             password has expired, not accessible by users."
        ::= { altasecMgmtTrap 2 }

altasecMgmtErrorOID     OBJECT-TYPE
        SYNTAX          OBJECT IDENTIFIER
        MAX-ACCESS      accessible-for-notify
        STATUS          current
        DESCRIPTION
            "(U//FOUO,PR) OID of the object linked to the error string caused by
             a set operation. If the column is not known, 0 is returned for the
             column OID. If the object is not known then a ZeroDotZero value
             (0.0) is returned."
        ::= { altasecMgmtTrapObjects 1 }

altasecMgmtErrorString  OBJECT-TYPE
        SYNTAX          DisplayString
        MAX-ACCESS      accessible-for-notify
        STATUS          current
        DESCRIPTION
            "(U//FOUO,PR) Error string caused by a set operation."
        ::= { altasecMgmtTrapObjects 2 }

altasecMgmtPasswordExpired NOTIFICATION-TYPE
        OBJECTS         { hStationID, hrSystemDate, usmUserSecurityName }
        STATUS          current
        DESCRIPTION
            "(U//FOUO,PR) The notification from HAIPE device to HMS indicating
             that a user's password has expired."
        ::= { altasecMgmtTrapNotifications 1 }

altasecMgmtSetError     NOTIFICATION-TYPE
        OBJECTS         { hStationID, hrSystemDate, altasecMgmtErrorString }
        STATUS          current
        DESCRIPTION
            "(U//FOUO,PR) An SNMP set has caused an internal error associated
             with a textual display string."
        ::= { altasecMgmtTrapNotifications 2 }

altasecMgmtMaxSessions OBJECT-TYPE
        SYNTAX          Unsigned32
        MAX-ACCESS      read-write
        STATUS          current
        DESCRIPTION
            "(U//FOUO,PR) The maximum allowed open sessions.  0 is unlimited."
        ::= { altasecMgmtSession 1 }

altasecMgmtOneSessionPerUser OBJECT-TYPE
        SYNTAX          TruthValue
        MAX-ACCESS      read-write
        STATUS          current
        DESCRIPTION
            "(U//FOUO,PR) Only allow one open session per user."
        ::= { altasecMgmtSession 2 }

altasecMgmtInactiveSeconds OBJECT-TYPE
        SYNTAX          Unsigned32
        MAX-ACCESS      read-write
        STATUS          current
        DESCRIPTION
            "(U//FOUO,PR) Inactivity session timeout in seconds."
        ::= { altasecMgmtSession 3 }

altasecMgmtSuiteOfOperation  OBJECT-TYPE
        SYNTAX               INTEGER { unknown(0),
                                       suiteA(1),
                                       suiteB(2)
                                     }
        MAX-ACCESS           read-only
        STATUS               current
        DESCRIPTION
            "(U//FOUO,PR) The current Suite of Operation. If an operational CIK
             is not inserted, the value of this object is unknown(0)."
        ::= { altasecMgmtCIK 1 }
        
altasecMgmtFTRCount          OBJECT-TYPE
        SYNTAX               Unsigned32
        MAX-ACCESS           read-only
        STATUS               current
        DESCRIPTION
            "(U//FOUO,PR) The number of times the INE has been recovered
             in the field. After the maximum count has been reached the unit
             must be returned to the factory for recovery from a tamper state."
        ::= { altasecMgmtCIK 2 }

-- *************************************************
-- Chassis Temperatures.

altasecTemperature1           OBJECT-TYPE
        SYNTAX                Integer32(-1289..1279)
        UNITS                 "tenths of degrees Celsius"
        MAX-ACCESS            read-only
        STATUS                current
        DESCRIPTION
            "(U//FOUO,PR) Chassis Temperature 1, in tenths of degrees
             Celsius:
             
             (U//FOUO,PR) KG-250: Top Front"
        ::= { altasecMgmtTemps 1 }

altasecTemperature2           OBJECT-TYPE
        SYNTAX                Integer32(-1289..1279)
        UNITS                 "tenths of degrees Celsius"
        MAX-ACCESS            read-only
        STATUS                current
        DESCRIPTION
            "(U//FOUO,PR) Chassis Temperature 2, in tenths of degrees
             Celsius:
             
             (U//FOUO,PR) KG-250: Top Back"
        ::= { altasecMgmtTemps 2 }

altasecTemperature3           OBJECT-TYPE
        SYNTAX                Integer32(-1289..1279)
        UNITS                 "tenths of degrees Celsius"
        MAX-ACCESS            read-only
        STATUS                current
        DESCRIPTION
            "(U//FOUO,PR) Chassis Temperature 3, in tenths of degrees
             Celsius:
             
             (U//FOUO,PR) KG-250: Bottom Front"
        ::= { altasecMgmtTemps 3 }

altasecTemperature4           OBJECT-TYPE
        SYNTAX                Integer32(-1289..1279)
        UNITS                 "tenths of degrees Celsius"
        MAX-ACCESS            read-only
        STATUS                current
        DESCRIPTION
            "(U//FOUO,PR) Chassis Temperature 4, in tenths of degrees
             Celsius:
             
             (U//FOUO,PR) KG-250: Bottom Back"
        ::= { altasecMgmtTemps 4 }

-- unofficial definition (CHIMERA Team)
altasecTemperature7           OBJECT-TYPE
        SYNTAX                Integer32(-1289..1279)
        UNITS                 "tenths of degrees Celsius"
        MAX-ACCESS            read-only
        STATUS                current
        DESCRIPTION
            "(U//FOUO,PR) Chassis Temperature 7, in tenths of degrees
             Celsius"
        ::= { altasecMgmtTemps 7 }

-- unofficial definition (CHIMERA Team)
altasecTemperature8           OBJECT-TYPE
        SYNTAX                Integer32(-1289..1279)
        UNITS                 "tenths of degrees Celsius"
        MAX-ACCESS            read-only
        STATUS                current
        DESCRIPTION
            "(U//FOUO,PR) Chassis Temperature 8, in tenths of degrees
             Celsius"
        ::= { altasecMgmtTemps 8 }
        
-- *************************************************
--  Temperature Controls.

altasecMgmtTempsControl           OBJECT IDENTIFIER ::= { altasecMgmtTemps 5 }
        
altasecTemperatureAutomaticShutdown  OBJECT-TYPE
        SYNTAX                       TruthValue
        MAX-ACCESS                   read-write
        STATUS                       current
        DESCRIPTION
            "(U//FOUO,PR) The indication of whether the device should
             automatically shutdown the unit when reaching the maximum
             operating temperature."
        ::= { altasecMgmtTempsControl 1 }

-- *************************************************
-- Proprietary Signature Download.

altasecSoftwareSignatureDownloadAdminStatus OBJECT-TYPE
        SYNTAX          INTEGER
                        {
                           downloadSignature(1),
                           executeSignature(2),
                           deleteSignature(3),
                           allowSignatureDownloadAction(4)
                        }
        MAX-ACCESS      read-write
        STATUS          current
        DESCRIPTION
            "(U//FOUO,PR) Software Signature File Download Admin State. It
             mirrors the purpose of hFirmwareDownloadAdminStatus in the HAIPE
             Management MIB which is used to control Firmware Download."
        ::= { altasecMgmtSigDL 1 }

altasecSoftwareSignatureDownloadOperStatus  OBJECT-TYPE
        SYNTAX          INTEGER
                        {
                           noPendingOperation(0),
                           downloadInProgress(1),
                           downloadComplete(2),
                           downloadFailed(3),
                           executeInProgress(4),
                           executeComplete(5),
                           executeFailed(6),
                           deleteInProgress(7),
                           deleteComplete(8),
                           deleteFailed(9)
                        }
        MAX-ACCESS      read-only
        STATUS          current
        DESCRIPTION
            "(U//FOUO,PR) Software Signature File Download Operational State. It
             mirrors the purpose of hFirmwareDownloadOperStatus in the HAIPE
             Management MIB which is used to check the status of a Firmware
             Download."
        ::= { altasecMgmtSigDL 2 }

altasecSoftwareSignatureDownloadResidentId OBJECT-TYPE
        SYNTAX          OCTET STRING (SIZE(1..256))
        MAX-ACCESS      read-only
        STATUS          current
        DESCRIPTION
            "(U//FOUO,PR) Software Signature currently loaded."
        ::= { altasecMgmtSigDL 3 }

-- *************************************************
-- Proprietary Battery Change Date.

altasecBatteryTable     OBJECT-TYPE
    SYNTAX              SEQUENCE OF ALTASECBatteryEntry
    MAX-ACCESS          not-accessible
    STATUS              current
    DESCRIPTION
        "(U//FOUO,PR) The table containing a writable change date of the
         external battery.  It augments the hBatteryTable in the
         HAIPE-MANAGEMENT-MIB."
    ::= { altasecMgmtBattery 3 }

altasecBatteryEntry OBJECT-TYPE
    SYNTAX      ALTASECBatteryEntry
    MAX-ACCESS  not-accessible
    STATUS      current
    DESCRIPTION
        "(U//FOUO,PR) A row describing a particular battery change date within
         the HAIPE."
    AUGMENTS { hBatteryEntry }
    ::= { altasecBatteryTable 1 }

-- added missing column (CHIMERA Team)
ALTASECBatteryEntry ::= SEQUENCE
    {
        altasecBatteryNumber             Unsigned32,
        altasecBatteryChangeDate         DateAndTime
    }

-- unofficial definition (CHIMERA Team)
altasecBatteryNumber    OBJECT-TYPE
        SYNTAX          Unsigned32
        MAX-ACCESS      read-only
        STATUS          current
        DESCRIPTION
            "(U//FOUO) The unique number enumerating a given battery."
        ::= { altasecBatteryEntry 1 }

altasecBatteryChangeDate     OBJECT-TYPE
        SYNTAX               DateAndTime
        MAX-ACCESS           read-write
        STATUS               current
        DESCRIPTION
            "(U//FOUO,PR) The date and time a changeable battery was last
             replaced. If a battery is not changeable, this column should be
             not-accessible. If a battery is changeable, but has not been
             changed or the last change time was lost then this value should
             be composed with all 0 values.

             (U//FOUO,PR) A user may set to this object, specifying a date
             within the past year or up to 7 days in the future."
        ::= { altasecBatteryEntry 2 }

-- *************************************************
-- Networking Settings.

-- unofficial definition (CHIMERA Team)
altasecNetErrorOID      OBJECT-TYPE
        SYNTAX          OBJECT IDENTIFIER
        MAX-ACCESS      accessible-for-notify
        STATUS          current
        DESCRIPTION
            "(U//FOUO,PR) OID of the object linked to the error string caused by
             a set operation. If the column is not known, 0 is returned for the
             column OID. If the object is not known then a ZeroDotZero value
             (0.0) is returned."
        ::= { altasecNetObjects 1 }

-- unofficial definition (CHIMERA Team)
altasecNetErrorString   OBJECT-TYPE
        SYNTAX          DisplayString
        MAX-ACCESS      accessible-for-notify
        STATUS          current
        DESCRIPTION
            "(U//FOUO,PR) Error string caused by a set operation."
        ::= { altasecNetObjects 2 }

altasecNetRebootRequired        NOTIFICATION-TYPE
        OBJECTS         { hStationID, hrSystemDate }
        STATUS          current
        DESCRIPTION
            "(U//FOUO,PR) The notification from HAIPE device to HMS indicating
             that a reboot is required to apply the latest configuration
             changes."
        ::= { altasecNetNotifications 1 }

-- unofficial definition (CHIMERA Team)
altasecNetSetError      NOTIFICATION-TYPE
        OBJECTS         { hStationID, hrSystemDate, altasecNetErrorOID,
                          altasecNetErrorString }
        STATUS          current
        DESCRIPTION
            "(U//FOUO,PR) An SNMP set has caused an internal error associated
             with a textual display string."
        ::= { altasecNetNotifications 3 }

altasecNetIPSettings OBJECT IDENTIFIER ::= { altasecNetIP 1 }

altasecNetIPv4 OBJECT IDENTIFIER ::= { altasecNetIP 4 }
altasecNetIPv6 OBJECT IDENTIFIER ::= { altasecNetIP 6 }
altasecNetPIM OBJECT IDENTIFIER  ::= { altasecNetIP 7 }

-- *************************************************
-- IPv4/IPv6 Box level settings.

altasecIPv4Settings OBJECT IDENTIFIER ::= { altasecNetIPv4 1 }
altasecIPv6Settings OBJECT IDENTIFIER ::= { altasecNetIPv6 1 }


altasecIPMulticastEnable OBJECT-TYPE
        SYNTAX           TruthValue
        MAX-ACCESS       read-write
        STATUS           current
        DESCRIPTION
            "(U//FOUO,PR) Global multicast enable Truth Value."
        ::= { altasecNetIPSettings 1 }

altasecIPReplayWindowSize OBJECT-TYPE
        SYNTAX            Unsigned32(32..32768)
        MAX-ACCESS        read-write
        STATUS            current
        DESCRIPTION
            "(U//FOUO,PR) The window size, in packets, that are used for
             anti-replay integrity, which detects arrival of duplicate IP
             datagrams (within a constrained window). In anti-replay integrity a
             packet's unique sequence number is compared to that of the
             previous packets (whose number to examine is defined by this value)
             on arrival.

             (U//FOUO,PR) This value may be 32, 64, 256, 1024, 4096, 8192,
             16384, or 32768. Note that in this progression 128, 512, and 2048
             are not supported."
        ::= { altasecNetIPSettings 2 }

altasecIPMulticastIGMPQueryEnable OBJECT-TYPE
        SYNTAX           TruthValue
        MAX-ACCESS       read-write
        STATUS           current
        DESCRIPTION
            "(U//FOUO,PR) IGMP query multicast enable Truth Value."
        ::= { altasecIPv4Settings 1 }

altasecIPMulticastIGMPVersion OBJECT-TYPE
        SYNTAX           INTEGER { none(0),
                                   version1(1),
                                   version2(2),
                                   version3(3)
                                 }
        MAX-ACCESS       read-write
        STATUS           current
        DESCRIPTION
            "(U//FOUO,PR) IGMP multicast version."
        ::= { altasecIPv4Settings 2 }

altasecIPMulticastMLDQueryEnable OBJECT-TYPE
        SYNTAX           TruthValue
        MAX-ACCESS       read-write
        STATUS           current
        DESCRIPTION
            "(U//FOUO,PR) MLD Query multicast enable Truth Value."
        ::= { altasecIPv6Settings 1 }

altasecIPMulticastMLDVersion OBJECT-TYPE
        SYNTAX           INTEGER { none(0), version1(1), version2(2) }
        MAX-ACCESS       read-write
        STATUS           current
        DESCRIPTION
            "(U//FOUO,PR) MLD multicast version."
        ::= { altasecIPv6Settings 2 }

altasecIPPIMEnable OBJECT-TYPE
        SYNTAX           TruthValue
        MAX-ACCESS       read-write
        STATUS           current
        DESCRIPTION
            "(U//FOUO,PR) PIM enable Truth Value."
        ::= { altasecNetPIM 1 }
        
altasecIPPIMM2MXorVal OBJECT-TYPE
        SYNTAX           Unsigned32(0..255)
        MAX-ACCESS       read-write
        STATUS           current
        DESCRIPTION
            "(U//FOUO,PR) Value to use to obscure CT Multicast address."
        ::= { altasecNetPIM 2 }
        
altasecIPPIMRendesvousPointTimer OBJECT-TYPE
        SYNTAX           Unsigned32(10..65535)
        MAX-ACCESS       read-write
        STATUS           current
        DESCRIPTION
            "(U//FOUO,PR) The interval to send the BSR messages."
        ::= { altasecNetPIM 3 }
        
altasecIPPIMRendesvousPointPri OBJECT-TYPE
        SYNTAX           Unsigned32(0..255)
        MAX-ACCESS       read-write
        STATUS           current
        DESCRIPTION
            "(U//FOUO,PR) The Rendesvous Point Priority."
        ::= { altasecNetPIM 4 }
        
altasecIPPIMBootstrapPri OBJECT-TYPE
        SYNTAX           Unsigned32(0..255)
        MAX-ACCESS       read-write
        STATUS           current
        DESCRIPTION
            "(U//FOUO,PR) The Bootstrap Router Priority."
        ::= { altasecNetPIM 5 }

-- *************************************************
-- Proprietary IPv4 interface augmentation table.

altasecIfv4TableAugmentation OBJECT IDENTIFIER ::= { altasecNetIPv4 2 }

altasecIfv4HaipeTable   OBJECT-TYPE
    SYNTAX              SEQUENCE OF ALTASECIfv4HaipeEntry
    MAX-ACCESS          not-accessible
    STATUS              current
    DESCRIPTION
        "(U//FOUO,PR) The table containing a list of AltaSec-specific interface
         objects for IPv4.  It augments the hIfv4HaipeEntry in the
         HAIPE-NETWORKING-MIB."
    ::= { altasecIfv4TableAugmentation 3 }

altasecIfv4HaipeEntry OBJECT-TYPE
    SYNTAX      ALTASECIfv4HaipeEntry
    MAX-ACCESS  not-accessible
    STATUS      current
    DESCRIPTION
        "(U//FOUO,PR) A row mapping IPv4 interface variables to an interface."
    AUGMENTS { ipv4InterfaceEntry }
    ::= { altasecIfv4HaipeTable 1 }

ALTASECIfv4HaipeEntry ::= SEQUENCE
    {
        altasecIfv4ICMPAllowPing                            TruthValue,
        altasecIfv4ICMPProcessPMTU                          TruthValue,
        altasecIfv4ICMPProcessPMTUSetting                   TruthValue,
        altasecIfv4DHCP                                     TruthValue,
        altasecIfv4ARPCacheTimeout                          Unsigned32,
        altasecIfv4ProxyARP                                 TruthValue
    }

altasecIfv4ICMPAllowPing     OBJECT-TYPE
        SYNTAX               TruthValue
        MAX-ACCESS           read-write
        STATUS               current
        DESCRIPTION
            "(U//FOUO,PR) Allows IPv4 Informational ICMP messages to be
             processed by the Linux kernel, this includes echo responses to
             incoming echo requests. This is true(1) by default for the PT
             interface and false(2) by default for the CT interface."
        ::= { altasecIfv4HaipeEntry 1 }

altasecIfv4ICMPProcessPMTU   OBJECT-TYPE
        SYNTAX               TruthValue
        MAX-ACCESS           read-only
        STATUS               current
        DESCRIPTION
            "(U//FOUO,PR) Allows IPv4 Error ICMP messages (such as PMTU
             Discovery, and Source Quench) to be processed by the Linux kernel,
             these are then bypassed out to the PT network after being handled
             internally.

             (U//FOUO,PR) For the CT interface, if IPv4 Fixed Packet Length
             (FPL) is enabled, then this object is internally forced to False.
             To read and write to its user setting see the
             altasecIfv4ICMPProcessPMTUSetting object. If FPL is currently
             enabled, the user setting will be utilized once FPL is disabled.
             The PT interface is not affected by such behavior and its value
             will mirror that of the altasecIfv4ICMPProcessPMTUSetting object."
        ::= { altasecIfv4HaipeEntry 2 }

altasecIfv4ICMPProcessPMTUSetting    OBJECT-TYPE
        SYNTAX                       TruthValue
        MAX-ACCESS                   read-write
        STATUS                       current
        DESCRIPTION
            "(U//FOUO,PR) Allows IPv4 Error ICMP messages (such as PMTU
             Discovery, and Source Quench) to be processed by the Linux kernel,
             these are then bypassed out to the PT network after being handled
             internally. This is true(1) by default for the PT  interface and
             false(2) by default for the CT interface.

             (U//FOUO,PR) Note: This object is always writeable and contains,
             for the CT interface, the user setting to be applied should IPv4
             Fixed Packet Length (FPL) be disabled. To verify the current
             operational value for this object see the
             altasecIfv4ICMPProcessPMTU object."
        DEFVAL { false }
        ::= { altasecIfv4HaipeEntry 3 }

altasecIfv4DHCP              OBJECT-TYPE
        SYNTAX               TruthValue
        MAX-ACCESS           read-write
        STATUS               current
        DESCRIPTION
            "(U//FOUO,PR) Interface DHCP enable Truth Value."
        DEFVAL { false }
        ::= { altasecIfv4HaipeEntry 4 }

altasecIfv4ARPCacheTimeout   OBJECT-TYPE
        SYNTAX               Unsigned32
        MAX-ACCESS           read-write
        STATUS               current
        DESCRIPTION
            "(U//FOUO,PR) ARP cache timeout in seconds."
        DEFVAL { 300 }
        ::= { altasecIfv4HaipeEntry 5 }

altasecIfv4ProxyARP          OBJECT-TYPE
        SYNTAX               TruthValue
        MAX-ACCESS           read-write
        STATUS               current
        DESCRIPTION
            "(U//FOUO,PR) Proxy ARP allows the PT (Red) interface to respond to
             ARP requests for hosts connected by a security association.
             Note: This only applies to the PT interface. Values set to the CT
             interface will return a wrongValue error."
        DEFVAL { false }
        ::= { altasecIfv4HaipeEntry 6 }


-- *************************************************
-- Proprietary IPv6 interface augmentation table.

altasecIfv6TableAugmentation OBJECT IDENTIFIER ::= { altasecNetIPv6 2 }

altasecIfv6HaipeTable   OBJECT-TYPE
    SYNTAX              SEQUENCE OF ALTASECIfv6HaipeEntry
    MAX-ACCESS          not-accessible
    STATUS              current
    DESCRIPTION
        "(U//FOUO,PR) The table containing a list of AltaSec-specific interface
         objects for IPv6.  It augments the hIfv6HaipeEntry in the
         HAIPE-NETWORKING-MIB."
    ::= { altasecIfv6TableAugmentation 3 }

altasecIfv6HaipeEntry OBJECT-TYPE
    SYNTAX      ALTASECIfv6HaipeEntry
    MAX-ACCESS  not-accessible
    STATUS      current
    DESCRIPTION
        "(U//FOUO,PR) A row mapping IPv6 interface variables to an interface."
    AUGMENTS { ipv6InterfaceEntry }
    ::= { altasecIfv6HaipeTable 1 }

ALTASECIfv6HaipeEntry ::= SEQUENCE
    {
        altasecIfv6ICMPAllowPing            TruthValue,
        altasecIfv6ICMPProcessPMTU          TruthValue,
        altasecIfv6ICMPProcessPMTUSetting   TruthValue
    }

altasecIfv6ICMPAllowPing     OBJECT-TYPE
        SYNTAX               TruthValue
        MAX-ACCESS           read-write
        STATUS               current
        DESCRIPTION
            "(U//FOUO,PR) Allows IPv6 Informational ICMP messages to be
             processed by the Linux kernel, this includes echo responses to
             incoming echo requests. This is true(1) by default for the PT
             interface and false(2) by default for the CT interface."
        ::= { altasecIfv6HaipeEntry 1 }

altasecIfv6ICMPProcessPMTU   OBJECT-TYPE
        SYNTAX               TruthValue
        MAX-ACCESS           read-only
        STATUS               current
        DESCRIPTION
            "(U//FOUO,PR) Allows IPv6 Error ICMP messages (such as PMTU
             Discovery or Destination Unreachable) to be processed by the Linux
             kernel.

             (U//FOUO,PR) For the CT interface, if IPv6 Fixed Packet Length
             (FPL) is enabled, then this object is internally forced to False.
             To read and write to its user setting see the
             altasecIfv6ICMPProcessPMTUSetting object. If FPL is currently
             enabled, the user setting will be utilized once FPL is disabled.
             The PT interface is not affected by such behavior and its value
             will mirror that of the altasecIfv6ICMPProcessPMTUSetting object."
        ::= { altasecIfv6HaipeEntry 2 }

altasecIfv6ICMPProcessPMTUSetting    OBJECT-TYPE
        SYNTAX                       TruthValue
        MAX-ACCESS                   read-write
        STATUS                       current
        DESCRIPTION
            "(U//FOUO,PR) Allows IPv6 Error ICMP messages (such as PMTU
             Discovery or Destination Unreachable) to be processed by the Linux
             kernel. This is true(1) by default for the PT  interface and
             false(2) by default for the CT interface.

             (U//FOUO,PR) Note: This object is always writeable and contains,
             for the CT interface, the user setting to be applied should IPv6
             Fixed Packet Length (FPL) be disabled. To verify the current
             operational value for this object see the
             altasecIfv6ICMPProcessPMTU object."
        ::= { altasecIfv6HaipeEntry 3 }

-- *************************************************
-- AltaSec Topology augmentation table.


altasecTopologyTable      OBJECT-TYPE
        SYNTAX            SEQUENCE OF ALTASECTopologyEntry
        MAX-ACCESS        not-accessible
        STATUS            current
        DESCRIPTION
            "(U//FOUO,PR) Proprietary RIP configuration items."
        ::= { altasecNetTopologyPeerAssignments 3 }

altasecTopologyEntry  OBJECT-TYPE
        SYNTAX            ALTASECTopologyEntry
        MAX-ACCESS        not-accessible
        STATUS            current
        DESCRIPTION
            "(U//FOUO,PR) A row defining the AltaSec proprietary extensions to
             the Topology Table providing explicit mapping between remote
             enclave entries and tunnel SAs."
        AUGMENTS   { hTopologyEntry }
        ::= { altasecTopologyTable 1 }

-- added missing columns (CHIMERA Team)
ALTASECTopologyEntry ::= SEQUENCE
    {
        altasecTopologyDestHostAddrType       InetAddressType,
        altasecTopologyDestHost               InetAddress,
        altasecTopologyDestHostPTPfxLen       InetAddressPrefixLength,
        altasecTopologyDestHaipeCTAddrType    InetAddressType,
        altasecTopologyDestHaipeCTAddr        InetAddress,
        altasecTopologyTunnelAssociationName  SnmpAdminString,
        altasecTopologyDestinationName        SnmpAdminString
    }

-- unofficial definition (CHIMERA Team)
altasecTopologyDestHostAddrType  OBJECT-TYPE
        SYNTAX                   InetAddressType
        MAX-ACCESS               read-only
        STATUS                   current
        DESCRIPTION
            "(U//FOUO) The PT Host Internet address type.

            (U//FOUO) Only ipv4(1), ipv6(2) and ipv6z(4) address types
            are supported."
        ::= { altasecTopologyEntry 1 }

-- unofficial definition (CHIMERA Team)
altasecTopologyDestHost  OBJECT-TYPE
        SYNTAX           InetAddress (SIZE (4|16|20))
        MAX-ACCESS       read-only
        STATUS           current
        DESCRIPTION
            "(U//FOUO) The PT Host (or network) IP
            address(es)."
        ::= { altasecTopologyEntry 2 }

-- unofficial definition (CHIMERA Team)
altasecTopologyDestHostPTPfxLen  OBJECT-TYPE
        SYNTAX                   InetAddressPrefixLength
        MAX-ACCESS               read-only
        STATUS                   current
        DESCRIPTION
            "(U//FOUO) The prefix length of the address
            stored in hTopologyDestHost (IE, the network mask)."
        ::= { altasecTopologyEntry 3 }

-- unofficial definition (CHIMERA Team)
altasecTopologyDestHaipeCTAddrType  OBJECT-TYPE
        SYNTAX                      InetAddressType
        MAX-ACCESS                  read-only
        STATUS                      current
        DESCRIPTION
            "(U//FOUO) The Destination HAIPE CT Internet
            address type.

            (U//FOUO) Only ipv4(1), ipv6(2) and ipv6z(4) address types
            are supported."
        ::= { altasecTopologyEntry 4 }

-- unofficial definition (CHIMERA Team)
altasecTopologyDestHaipeCTAddr  OBJECT-TYPE
        SYNTAX                  InetAddress (SIZE (4|16|20))
        MAX-ACCESS              read-only
        STATUS                  current
        DESCRIPTION
            "(U//FOUO) The Destination HAIPE CT IP address."
        ::= { altasecTopologyEntry 5 }

altasecTopologyTunnelAssociationName  OBJECT-TYPE
        SYNTAX                        SnmpAdminString
        MAX-ACCESS                    read-write
        STATUS                        current
        DESCRIPTION
            "(U//FOUO,PR) For remote enclave (PEPT) entries, the device name of
             the Tunnel that is currently associated with this entry. If the
             PEPT entry does not have a Tunnel association, a zero length
             string is returned. Local enclave (LEPT) entries do not have this
             object."
        DEFVAL { "" }
        ::= { altasecTopologyEntry 6 }

altasecTopologyDestinationName  OBJECT-TYPE
        SYNTAX                  SnmpAdminString
        MAX-ACCESS              read-write
        STATUS                  current
        DESCRIPTION
            "(U//FOUO,PR) For remote enclave (PEPT) entries, the destination 
             name of destination network. If the PEPT entry does not have a 
             destination name, a zero length string is returned. Local enclave 
             (LEPT) entries do not have this object."
        DEFVAL { "" }
        ::= { altasecTopologyEntry 7 }

-- *************************************************
-- AltaSec RIP Configuration augmentation table.


altasecRIPConfTable       OBJECT-TYPE
        SYNTAX            SEQUENCE OF ALTASECRIPConfEntry
        MAX-ACCESS        not-accessible
        STATUS            current
        DESCRIPTION
            "(U//FOUO,PR) Proprietary RIP configuration items."
        ::= { altasecRIPConfAugmentation 3 }

altasecRIPConfEntry  OBJECT-TYPE
        SYNTAX            ALTASECRIPConfEntry
        MAX-ACCESS        not-accessible
        STATUS            current
        DESCRIPTION
            "(U//FOUO,PR) A row defining the AltaSec proprietary extensions to
             the RIP configuration on the per-interface level."
        AUGMENTS   { hRIPConfEntry }
        ::= { altasecRIPConfTable 1 }

ALTASECRIPConfEntry ::= SEQUENCE
    {
        altasecrcExpirationTimer        Unsigned32,
        altasecrcFlushTimer             Unsigned32,
        altasecrcUpdateTimer            Unsigned32,
        altasecrcAdminCost              Unsigned32,
        altasecrcLifetime               Unsigned32
    }

altasecrcExpirationTimer         OBJECT-TYPE
        SYNTAX                   Unsigned32(5..999)
        MAX-ACCESS               read-write
        STATUS                   current
        DESCRIPTION
            "(U//FOUO,PR) The RIP expiration timer, in seconds."
        DEFVAL { 180 }
        ::= { altasecRIPConfEntry 3 }

altasecrcFlushTimer              OBJECT-TYPE
        SYNTAX                   Unsigned32(5..999)
        MAX-ACCESS               read-write
        STATUS                   current
        DESCRIPTION
            "(U//FOUO,PR) The RIP flush timer, in seconds."
        DEFVAL { 120 }
        ::= { altasecRIPConfEntry 4 }

altasecrcUpdateTimer             OBJECT-TYPE
        SYNTAX                   Unsigned32(5..999)
        MAX-ACCESS               read-write
        STATUS                   current
        DESCRIPTION
            "(U//FOUO,PR) The RIP update timer, in seconds."
        DEFVAL { 30 }
        ::= { altasecRIPConfEntry 5 }

altasecrcAdminCost               OBJECT-TYPE
        SYNTAX                   Unsigned32(1..255)
        MAX-ACCESS               read-write
        STATUS                   current
        DESCRIPTION
            "(U//FOUO,PR) The administrative cost for learned RIP routes."
        DEFVAL { 120 }
        ::= { altasecRIPConfEntry 6 }

altasecrcLifetime                OBJECT-TYPE
        SYNTAX                   Unsigned32(0..65535)
        MAX-ACCESS               read-write
        STATUS                   current
        DESCRIPTION
            "(U//FOUO,PR) Lifetime of RIP route after import."
        DEFVAL { 65535 }
        ::= { altasecRIPConfEntry 7 }

-- ***********************************************************
-- Proprietary OSPF Configuration Objects
--

altasecOSPFRedistributeRoutes       OBJECT-TYPE
        SYNTAX                      TruthValue
        MAX-ACCESS                  read-write
        STATUS                      current
        DESCRIPTION
            "(U//FOUO,PR) This determines if the OSPF Routes should be
            redistributed."
        ::= { altasecNetDiscoveryOSPFGeneral 1 }

altasecOSPFRedistributeMetricType   OBJECT-TYPE
        SYNTAX                      INTEGER { e1(1),
                                              e2(2)
                                            }
        MAX-ACCESS                  read-write
        STATUS                      current
        DESCRIPTION
            "(U//FOUO,PR) This defines the OSPF Metric type to redistribute.

             (U//FOUO,PR) Controls whether an OSPF router on the PT-side of
             an AltaSec will add (E1) or not add (E2) the cost of the path
             to the fronting AltaSec (ASBR) to the cost of a kernel route
             that the AltaSec originates as an AS-External/Type 5.  This
             gives the user at a multiple-AltaSec enclave the opportunity to
             control path selection from either the PT router or the AltaSec."
        ::= { altasecNetDiscoveryOSPFGeneral 2 }

altasecOSPFNeighborLog   OBJECT-TYPE
        SYNTAX                      TruthValue
        MAX-ACCESS                  read-only
        STATUS                      current
        DESCRIPTION
            "(U//FOUO,PR) When enabled, the neighbor log displays messages 
             indicating when neighbors are discovered, removed, or change state."
        ::= { altasecNetDiscoveryOSPFGeneral 3 }

altasecOSPFPTOperationEnable        OBJECT-TYPE
        SYNTAX                      TruthValue
        MAX-ACCESS                  read-write
        STATUS                      current
        DESCRIPTION
            "(U//FOUO,PR) This defines the operation of the OSPF mode for the
             PT (Red) Interface."
        ::= { altasecNetDiscoveryOSPFPT 1 }

altasecOSPFPTMode                   OBJECT-TYPE
        SYNTAX                      INTEGER { passive(1),
                                              active(2)
                                            }
        MAX-ACCESS                  read-write
        STATUS                      current
        DESCRIPTION
            "(U//FOUO,PR) Do not speak OSPF interface on the given interface,
             but do advertise the interface as a stub link in the
             router-LSA (Link State Advertisement) for this router. This
             allows one to advertise addresses on such connected interfaces
             without having to originate AS-External/Type 5 LSAs (which have
             global flooding scope) - as would occur if connected addresses
             were redistributed into OSPF. This is the only way to advertise
             non-OSPF links into stub areas."
        ::= { altasecNetDiscoveryOSPFPT 2 }

altasecOSPFPTAdvertiseDefaultRoute  OBJECT-TYPE
        SYNTAX                      TruthValue
        MAX-ACCESS                  read-write
        STATUS                      current
        DESCRIPTION
            "(U//FOUO,PR) Advertise a default route to remote PT destinations.
             This object only applies when Legacy and/or Generic Discovery
             is configured."
        ::= { altasecNetDiscoveryOSPFPT 3 }

altasecOSPFPTDefaultRouteMetric     OBJECT-TYPE
        SYNTAX                      Unsigned32(1..15)
        MAX-ACCESS                  read-write
        STATUS                      current
        DESCRIPTION
            "(U//FOUO,PR) Defines the metric advertised for the default route."
        ::= { altasecNetDiscoveryOSPFPT 4 }

altasecOSPFPTAuthenticationKeyID     OBJECT-TYPE
        SYNTAX                      Unsigned32(0..255)
        MAX-ACCESS                  read-write
        STATUS                      current
        DESCRIPTION
            "(U//FOUO,PR) The authentication key ID to be used for MD5 
             authentication. A value of 0 indicates that MD5 authentication is
             disabled. Both the key ID and key must match on all neighbors.
             
             (U//FOUO,PR) If this is value is set to a nonzero value when it
             was previously set to 0 the altasecOSPFPTAuthenticationKey will
             default to a value of pt_auth_key_set1"
        ::= { altasecNetDiscoveryOSPFPT 5 }
        
altasecOSPFPTAuthenticationKey      OBJECT-TYPE
        SYNTAX                      OCTET STRING (SIZE(16))
        MAX-ACCESS                  read-write
        STATUS                      current
        DESCRIPTION
            "(U//FOUO,PR) The authentication key to be used for MD5 
             authentication. Note that this object should not exist if MD5
             authentication is disabled. Both the key ID and key must match 
             on all neighbors."
        ::= { altasecNetDiscoveryOSPFPT 6 }
        
altasecOSPFAPNOperationEnable       OBJECT-TYPE
        SYNTAX                      TruthValue
        MAX-ACCESS                  read-write
        STATUS                      current
        DESCRIPTION
            "(U//FOUO,PR) This defines the operation of the OSPF mode for the
             AltaSec Peer Network (APN) Interface."
        ::= { altasecNetDiscoveryOSPFAPN 1 }

altasecOSPFAPNCTMulticastAddress    OBJECT-TYPE
        SYNTAX                      InetAddress
        MAX-ACCESS                  read-write
        STATUS                      current
        DESCRIPTION
            "(U//FOUO,PR) The AltaSec's APN CT Multicast address destination.

             (U//FOUO,PR) This address must be an IPv4 multicast address."
        ::= { altasecNetDiscoveryOSPFAPN 2 }

altasecOSPFAPNAddress               OBJECT-TYPE
        SYNTAX                      InetAddress
        MAX-ACCESS                  read-write
        STATUS                      current
        DESCRIPTION
            "(U//FOUO,PR) The AltaSec's IP address on the AltaSec Peer Network.
             By default this address is auto-generated.

             (U//FOUO,PR) This address must be an IPv4 unicast address."
        ::= { altasecNetDiscoveryOSPFAPN 3 }

altasecOSPFAPNPPKChain              OBJECT-TYPE
        SYNTAX                      SnmpAdminString (SIZE(0..15))
        MAX-ACCESS                  read-write
        STATUS                      current
        DESCRIPTION
            "(U//FOUO,PR) The PPK Chain used to protect the APN Security
             Association (SA).

             (U//FOUO,PR) A zero-length string indicates that no PPK Chain is
             configured."
        ::= { altasecNetDiscoveryOSPFAPN 4 }

altasecOSPFAPNspiCurrent            OBJECT-TYPE
        SYNTAX                      Unsigned32(256..4294967295)
        MAX-ACCESS                  read-write
        STATUS                      current
        DESCRIPTION
            "(U//FOUO,PR) The Current Security Parameters Index (SPI) value for
              the APN Security Association (SA).

             (U//FOUO,PR) Note that certain SPI values maybe restricted from
             use."
        ::= { altasecNetDiscoveryOSPFAPN 5 }

altasecOSPFAPNspiNext               OBJECT-TYPE
        SYNTAX                      Unsigned32(256..4294967295)
        MAX-ACCESS                  read-write
        STATUS                      current
        DESCRIPTION
            "(U//FOUO,PR) The Next Security Parameters Index (SPI) value for
              the APN Security Association (SA).

             (U//FOUO,PR) Note that certain SPI values maybe restricted from
             use."
        ::= { altasecNetDiscoveryOSPFAPN 6 }

altasecOSPFAPNblockSize             OBJECT-TYPE
        SYNTAX                      Unsigned32(8..48)
        MAX-ACCESS                  read-write
        STATUS                      current
        DESCRIPTION
            "(U//FOUO,PR) The crypto block size for ESPv1 MEDLEY-BIP32"
        ::= { altasecNetDiscoveryOSPFAPN 7 }
        
        
altasecOSPFAPNAuthenticationKeyID   OBJECT-TYPE
        SYNTAX                      Unsigned32(0..255)
        MAX-ACCESS                  read-write
        STATUS                      current
        DESCRIPTION
            "(U//FOUO,PR) The authentication key ID to be used for MD5 
             authentication. A value of 0 indicates that MD5 authentication is
             disabled. Both the key ID and key must match on all neighbors.
                        
             (U//FOUO,PR) If this is value is set to a nonzero value when it
             was previously set to 0 the altasecOSPFAPNAuthenticationKey will
             default to a value of apn_auth_key_set"
        ::= { altasecNetDiscoveryOSPFAPN 8 }
        
altasecOSPFAPNAuthenticationKey     OBJECT-TYPE
        SYNTAX                      OCTET STRING (SIZE(16))
        MAX-ACCESS                  read-write
        STATUS                      current
        DESCRIPTION
            "(U//FOUO,PR) The authentication key to be used for MD5 
             authentication. Note that this object should not exist if MD5
             authentication is disabled. Both the key ID and key must match 
             on all neighbors."
        ::= { altasecNetDiscoveryOSPFAPN 9 }

-- ***********************************************************
-- Interface Networking Objects (IP version neutral)
--

altasecIf           OBJECT IDENTIFIER ::= { altasecNetIP 2 }

-- *************************************************
-- Proprietary If augmentation table.

altasecIfTableAugmentation OBJECT IDENTIFIER ::= { altasecIf 2 }

altasecIfTable   OBJECT-TYPE
    SYNTAX       SEQUENCE OF ALTASECIfEntry
    MAX-ACCESS   not-accessible
    STATUS       current
    DESCRIPTION
        "(U//FOUO,PR) The table containing a list of AltaSec-specific interface
         objects.  It augments the ifEntry in the IF-MIB."
    ::= { altasecIfTableAugmentation 3 }

altasecIfEntry OBJECT-TYPE
    SYNTAX      ALTASECIfEntry
    MAX-ACCESS  not-accessible
    STATUS      current
    DESCRIPTION
        "(U//FOUO) A row mapping IPv6 interface variables to an interface."
    AUGMENTS { ifEntry }
    ::= { altasecIfTable 1 }

ALTASECIfEntry ::= SEQUENCE
    {
        altasecIfIndex                   InterfaceIndex,
        altasecIfDuplex                  INTEGER,
        altasecIfMode                    INTEGER,
        altasecIfNegotiateSpeedDuplex    BITS,
        altasecIfForceSpeed              Unsigned32,
        altasecIfForceDuplex             INTEGER
    }

-- changed to unique name (CHIMERA Team)
altasecIfIndex                   OBJECT-TYPE
        SYNTAX                   InterfaceIndex
        MAX-ACCESS               read-only
        STATUS                   current
        DESCRIPTION
            "A unique value, greater than zero, for each interface.  It
            is recommended that values are assigned contiguously
            starting from 1.  The value for each interface sub-layer
            must remain constant at least from one re-initialization of
            the entity's network management system to the next re-
            initialization."
    ::= { altasecIfEntry 1 }

altasecIfDuplex                  OBJECT-TYPE
        SYNTAX                   INTEGER { unknown(0),
                                           halfDuplex(1),
                                           fullDuplex(2)
                                         }
        MAX-ACCESS               read-only
        STATUS                   current
        DESCRIPTION
            "(U//FOUO, PR) Operational duplex setting of the current link."
        ::= { altasecIfEntry 2 }

altasecIfMode   OBJECT-TYPE
        SYNTAX                   INTEGER { autoNegotiate(1), force(2) }
        MAX-ACCESS               read-write
        STATUS                   current
        DESCRIPTION
            "(U//FOUO, PR) The mode by which link speed and duplex should be
             determined."
        DEFVAL { autoNegotiate }
        ::= { altasecIfEntry 3 }

-- added unofficial values 4-5 (CHIMERA Team)
altasecIfNegotiateSpeedDuplex    OBJECT-TYPE
        SYNTAX                   BITS { speed10MbitHalfDuplex(0),
                                        speed10MbitFullDuplex(1),
                                        speed100MbitHalfDuplex(2),
                                        speed100MbitFullDuplex(3),
                                        speed1000MbitHalfDuplex(4),
                                        speed1000MbitFullDuplex(5)
                                      }
        MAX-ACCESS               read-write
        STATUS                   current
        DESCRIPTION
            "(U//FOUO, PR) The speed and duplex modes that should be offered for
             negotiation. These settings are utilized when the altasecIfMode
             object is set to autoNegotiate(1)."
        DEFVAL { { speed10MbitHalfDuplex, speed10MbitFullDuplex,
                   speed100MbitHalfDuplex, speed100MbitFullDuplex } }
        ::= { altasecIfEntry 4 }

altasecIfForceSpeed              OBJECT-TYPE
        SYNTAX                   Unsigned32
        MAX-ACCESS               read-write
        STATUS                   current
        DESCRIPTION
            "(U//FOUO, PR) The speed mode that should be forced. This setting
             is utilized when the altasecIfMode object is set to force(2)."
        DEFVAL { 100000000 }
        ::= { altasecIfEntry 5 }

altasecIfForceDuplex             OBJECT-TYPE
        SYNTAX                   INTEGER { unknown(0),
                                           halfDuplex(1),
                                           fullDuplex(2)
                                         }
        MAX-ACCESS               read-write
        STATUS                   current
        DESCRIPTION
            "(U//FOUO, PR) The duplex mode that should be forced. This setting
             is utilized when the altasecIfMode object is set to force(2)."
        DEFVAL { fullDuplex }
        ::= { altasecIfEntry 6 }

altasecVLAN         OBJECT IDENTIFIER ::= { altasecIf 3 }

-- *************************************************
-- VLAN interface table.

altasecVLANTableCount       OBJECT-TYPE
        SYNTAX              Unsigned32
        MAX-ACCESS          read-only
        STATUS              current
        DESCRIPTION
            "(U//FOUO,PR) The number of rows in the altasecVLANTable."
        ::= { altasecVLAN 1 }

altasecVLANTableLastChanged OBJECT-TYPE
        SYNTAX              TimeStamp
        MAX-ACCESS          read-only
        STATUS              current
        DESCRIPTION
            "(U//FOUO,PR) The value of sysUpTime the last time any entry in
             the altasecVLANTable was modified, created, or deleted by
             either SNMP or other management method (e.g., via an HMI).

             (U//FOUO,PR) Managers can use this object to ensure that no
             changes to configuration of this table have happened since the
             last time it examined the table.

             (U//FOUO,PR) A value of 0 indicates that no entry has been
             changed since the agent initialized."
        ::= { altasecVLAN 2 }

altasecVLANTable OBJECT-TYPE
        SYNTAX          SEQUENCE OF ALTASECVLANEntry
        MAX-ACCESS      not-accessible
        STATUS          current
        DESCRIPTION
            "(U//FOUO,PR) IP configuration for VLAN Interfaces."
        ::= { altasecVLAN 3 }

altasecVLANEntry OBJECT-TYPE
        SYNTAX          ALTASECVLANEntry
        MAX-ACCESS      not-accessible
        STATUS          current
        DESCRIPTION
            "(U//FOUO,PR) A row defining the IP configuration for a VLAN
             Interface."
        INDEX   { altasecVLANID }
        ::= { altasecVLANTable 1 }

ALTASECVLANEntry ::= SEQUENCE
    {
        altasecVLANID              Unsigned32,
        altasecVLANAddressType     InetAddressType,
        altasecVLANAddress         InetAddress,
        altasecVLANPfxLen          Unsigned32,
        altasecVLANMTU             Unsigned32,
        altasecVLANMulticastEnable INTEGER,
        altasecVLANRowStatus       RowStatus
    }

altasecVLANID              OBJECT-TYPE
        SYNTAX             Unsigned32
        MAX-ACCESS         read-only
        STATUS             current
        DESCRIPTION
            "(U//FOUO,PR) The VLAN ID associated with this row."
        ::= { altasecVLANEntry 1 }

altasecVLANAddressType     OBJECT-TYPE
        SYNTAX             InetAddressType
        MAX-ACCESS         read-create
        STATUS             current
        DESCRIPTION
            "(U//FOUO,PR) The Internet address type for this interface. Only
             ipv4(1) is supported for V3, ipv6(2) is reserved for future use."
        DEFVAL { ipv4 }
        ::= { altasecVLANEntry 2 }

altasecVLANAddress         OBJECT-TYPE
        SYNTAX             InetAddress (SIZE (4|16))
        MAX-ACCESS         read-create
        STATUS             current
        DESCRIPTION
            "(U//FOUO,PR) The assigned Internet address for this interface."
        ::= { altasecVLANEntry 3 }

altasecVLANPfxLen          OBJECT-TYPE
        SYNTAX             Unsigned32
        MAX-ACCESS         read-create
        STATUS             current
        DESCRIPTION
            "(U//FOUO,PR) The prefix length for this interface."
        ::= { altasecVLANEntry 4 }

altasecVLANMTU             OBJECT-TYPE
        SYNTAX             Unsigned32
        MAX-ACCESS         read-create
        STATUS             current
        DESCRIPTION
            "(U//FOUO,PR) The MTU for this VLAN interface."
        DEFVAL { 1496 }
        ::= { altasecVLANEntry 5 }

altasecVLANMulticastEnable OBJECT-TYPE
        SYNTAX             TruthValue
        MAX-ACCESS         read-create
        STATUS             current
        DESCRIPTION
            "(U//FOUO,PR) Multicast Enable TruthValue for this VLAN Interface."
        DEFVAL { true }
        ::= { altasecVLANEntry 6 }

altasecVLANRowStatus       OBJECT-TYPE
        SYNTAX             RowStatus
        MAX-ACCESS         read-create
        STATUS             current
        DESCRIPTION
            "(U//FOUO,PR) RowStatus for VLAN Interface."
        ::= { altasecVLANEntry 7 }

-- **********************************************************************
-- Cryptographic Control objects
-- **********************************************************************

altasecPanicZeroize OBJECT-TYPE
        SYNTAX      TruthValue
        MAX-ACCESS  read-write
        STATUS      current
        DESCRIPTION
            "(U//FOUO) Setting this object to 'true' will panic zeroize the
            HAIPE device, zeroizing all the keys contained within the device as
            well as the CIK.  It must not modify any other information in the
            device such as the persistent storage or the audit log.  Also see
            the HAIPE-TRAFFIC-PROTECTION-MIB::haipeZeroizeAllKeys and
            HAIPE-MANAGEMENT-MIB::haipeSanitizeDevice objects.  When read this
            object should return false.  When set to false this object must not
            perform any operation but should accept this as a valid SET
            operation."
        ::= { altasecCryptoControl 1 }

-- *************************************************
-- PPK Information.
--

-- *************************************************
-- PPK Key Information.
--

altasecPreplacedKeyTableCount OBJECT-TYPE
        SYNTAX          Unsigned32
        MAX-ACCESS      read-only
        STATUS          current
        DESCRIPTION
            "(U//FOUO,PR) The number of rows in the altasecPreplacedKeyTable."
        ::= { altasecPPKKeyInformation 1 }

altasecPreplacedKeyTableCapacity OBJECT-TYPE
        SYNTAX          Unsigned32
        MAX-ACCESS      read-only
        STATUS          current
        DESCRIPTION
            "(U//FOUO,PR) The total number of pre-placed keys (PPK's)
            this HAIPE can hold."
        ::= { altasecPPKKeyInformation 2 }

altasecPreplacedKeyTableLastChanged OBJECT-TYPE
        SYNTAX      TimeStamp
        MAX-ACCESS  read-only
        STATUS      current
        DESCRIPTION
            "(U//FOUO,PR) The value of sysUpTime the last time any entry
            in the altasecPreplacedKeyTable was modified, created, or
            deleted by either SNMP or other management method
            (e.g. via an HMI).

            (U//FOUO,PR) Managers can use this object to ensure that no
            changes to configuration of this table have happened
            since the last time it examined the table.

            (U//FOUO,PR) A value of 0 indicates that no entry has been
            changed since the agent initialized."
        ::= { altasecPPKKeyInformation 3 }

altasecPreplacedKeyTable  OBJECT-TYPE
    SYNTAX            SEQUENCE OF ALTASECPreplacedKeyEntry
    MAX-ACCESS        not-accessible
    STATUS            current
    DESCRIPTION
        "(U//FOUO,PR) The table containing information about the loaded
         pre-placed keys (PPK's). This proprietary table is necessary in that
         users may optionally load multiple copies of the same key. This table
         differs from the hPreplacedKeyTable in that the PPK unique IDs are used as
         an additional index into the table. In addition to the values provided
         in the hPreplacedKeyTable, the PPK Chain to which it is assigned (if
         any) is provided for added granularity."
    ::= { altasecPPKKeyInformation 4 }

altasecPreplacedKeyEntry  OBJECT-TYPE
    SYNTAX                ALTASECPreplacedKeyEntry
    MAX-ACCESS            not-accessible
    STATUS                current
    DESCRIPTION
        "(U//FOUO,PR) A row indicating a pre-placed key (PPK) within a
        chain of PPK's and the order that the PPK indicated will be
        used by the HAIPE device as part of that chain."
    INDEX  { altasecPPKShortTitleName, altasecPPKEdition,
             altasecPPKSegment, altasecPPKID }
    ::= { altasecPreplacedKeyTable 1 }

ALTASECPreplacedKeyEntry ::= SEQUENCE
    {
        altasecPPKShortTitleName         PPKShortTitle,
        altasecPPKEdition                PPKEdition,
        altasecPPKSegment                HaipeSegment,
        altasecPPKID                     Unsigned32,
        altasecPPKUsageType              INTEGER,
        altasecPPKEffectiveDate          DateAndTime,
        altasecPPKSecurityLevel          HaipeSecurityLevel,
        altasecPPKZeroizeKey             TruthValue,
        altasecPPKRegister               OCTET STRING,
        altasecPPKAuthority              HaipeSecurityAuthority,
        altasecPPKLastChanged            TimeStamp,
        altasecPPKChainID                SnmpAdminString,
        altasecPPKQKeyLabel              SnmpAdminString
    }

-- changed to unique name (CHIMERA Team)
altasecPPKShortTitleName  OBJECT-TYPE
        SYNTAX            PPKShortTitle
        MAX-ACCESS        read-only
        STATUS            current
        DESCRIPTION
            "(U//FOUO) The short title of the pre-placed key (PPK)."
        ::= { altasecPreplacedKeyEntry 1 }

-- changed to unique name (CHIMERA Team)
altasecPPKEdition       OBJECT-TYPE
        SYNTAX          PPKEdition
        MAX-ACCESS      read-only
        STATUS          current
        DESCRIPTION
            "(U//FOUO) The edition of this pre-placed key (PPK)."
        ::= { altasecPreplacedKeyEntry 2 }

-- changed to unique name (CHIMERA Team)
altasecPPKSegment       OBJECT-TYPE
        SYNTAX          HaipeSegment
        MAX-ACCESS      read-only
        STATUS          current
        DESCRIPTION
            "(U//FOUO) The segment number of this pre-placed key (PPK)."
        ::= { altasecPreplacedKeyEntry 3 }

altasecPPKID            OBJECT-TYPE
        SYNTAX          Unsigned32
        MAX-ACCESS      read-only
        STATUS          current
        DESCRIPTION
            "(U//FOUO,PR) The unique ID assigned to the pre-placed key (PPK)."
        ::= { altasecPreplacedKeyEntry 4 }

-- changed to unique name (CHIMERA Team)
altasecPPKUsageType     OBJECT-TYPE
        SYNTAX          INTEGER { unassigned(1),
                                  trafficKey(2),
                                  exclusionKey(3) }
        MAX-ACCESS      read-only
        STATUS          current
        DESCRIPTION
            "(U//FOUO) Indicates how this key can be used.  Unlike the
            hPreplacedKeyTable, this value is read-only."
        ::= { altasecPreplacedKeyEntry 5 }

-- changed to unique name (CHIMERA Team)
altasecPPKEffectiveDate  OBJECT-TYPE
        SYNTAX           DateAndTime
        MAX-ACCESS       read-only
        STATUS           current
        DESCRIPTION
            "(U//FOUO) The effective start date and time of this
            pre-placed key (PPK).  This object will be automatically
            set from the chain information once the spot in the chain
            is reached where this key becomes actively used."
        ::= { altasecPreplacedKeyEntry 6 }

-- changed to unique name (CHIMERA Team)
altasecPPKSecurityLevel  OBJECT-TYPE
        SYNTAX           HaipeSecurityLevel
        MAX-ACCESS       read-only
        STATUS           current
        DESCRIPTION
            "(U//FOUO) The security level usable with this
            pre-placed key (PPK)."
        ::= { altasecPreplacedKeyEntry 7 }

-- changed to unique name (CHIMERA Team)
altasecPPKZeroizeKey    OBJECT-TYPE
        SYNTAX          TruthValue
        MAX-ACCESS      read-write
        STATUS          current
        DESCRIPTION
            "(U//FOUO,PR) Setting this object to 'true' will zeroize
            this key. Any active SAs using this key should be torn
            down.  It must not modify any other information in the
            device including the audit log.  When read this object
            should return true if the key has been zeroized, or
            false otherwise.  If this object is set to the same
            value as the current value, the device must not perform
            any operation but should accept this as a valid SET
            operation. Once the value is set to true, attempts to
            set it back to false will return an inconsistentValue
            error.

            (U//FOUO) It is beyond the scope of the MIB model to
            indicate whether zeroized keys are reported in this table
            or not.  This text allows for either the keys to continue
            to be reported or the row may be removed when a key is
            zeroized.  Which mode a device supports is implementation
            dependent."
        ::= { altasecPreplacedKeyEntry 8 }

-- changed to unique name (CHIMERA Team)
altasecPPKRegister      OBJECT-TYPE
        SYNTAX          OCTET STRING (SIZE(5))
        MAX-ACCESS      read-only
        STATUS          current
        DESCRIPTION
            "(U//FOUO) The register number of this PPK.  The right
            most 36 bits are used to signify the register number.  The
            left most 4 bits must be set to zero in responses from the
            SNMP agent."
        ::= { altasecPreplacedKeyEntry 9 }

-- changed to unique name (CHIMERA Team)
altasecPPKAuthority  OBJECT-TYPE
        SYNTAX       HaipeSecurityAuthority
        MAX-ACCESS   read-only
        STATUS       deprecated
        DESCRIPTION
            "(U//FOUO) This object is deprecated and should not be
            implemented."
        ::= { altasecPreplacedKeyEntry 10 }

-- changed to unique name (CHIMERA Team)
altasecPPKLastChanged   OBJECT-TYPE
        SYNTAX          TimeStamp
        MAX-ACCESS      read-only
        STATUS          current
        DESCRIPTION
            "(U//FOUO) The value of sysUpTime the last time any value
            in this row was modified, created, or deleted by either
            SNMP or other management method (e.g. via an HMI).

            (U//FOUO) Managers can use this object to ensure that no
            changes to configuration of this row have happened since
            the last time it examined the row.

            (U//FOUO) A value of 0 indicates that no value has been
            changed since the agent initialized."
        ::= { altasecPreplacedKeyEntry 11 }

altasecPPKChainID   OBJECT-TYPE
        SYNTAX      SnmpAdminString
        MAX-ACCESS  read-only
        STATUS      current
        DESCRIPTION
            "(U//FOUO,PR) An administratively assigned name to link a group
            of PPKs together.  This object may be referenced by the
            hIPhRuleActionIndex object in the hIPhRuleTable if it is not a
            zero-length string."
        ::= { altasecPreplacedKeyEntry 12 }

altasecPPKQKeyLabel   OBJECT-TYPE
        SYNTAX        SnmpAdminString
        MAX-ACCESS    read-only
        STATUS        current
        DESCRIPTION
            "(U//FOUO,PR) An administratively assigned name to identify
            the Q-key (trust anchor) used to authenticate an APPK.
            This object only applies when the INE is operating in Suite B,
            otherwise N/A is returned."
        ::= { altasecPreplacedKeyEntry 13 }

-- *************************************************
-- PPK Chain Information.
--

altasecPPKChainTable  OBJECT-TYPE
    SYNTAX            SEQUENCE OF ALTASECPPKChainEntry
    MAX-ACCESS        not-accessible
    STATUS            current
    DESCRIPTION
        "(U//FOUO,PR) The table containing proprietary information about
        pre-placed key (PPK) chains.  This table includes a column to
        set the integrity algorithm at creation time for the PPK Chain."
    ::= { altasecPPKChainInformation 7 }

altasecPPKChainEntry  OBJECT-TYPE
    SYNTAX            ALTASECPPKChainEntry
    MAX-ACCESS        not-accessible
    STATUS            current
    DESCRIPTION
        "(U//FOUO,PR) A row indicating a pre-placed key (PPK) within a
        chain of PPK's and the order that the PPK indicated will be
        used by the HAIPE device as part of that chain."
        AUGMENTS   { hPPKChainEntry }
    ::= { altasecPPKChainTable 1 }

ALTASECPPKChainEntry ::= SEQUENCE
    {
        altasecPPKChainID-2                 SnmpAdminString,
        altasecPPKChainOrder                Unsigned32,
        altasecPPKChainIntegrityAlgorithm   HaipeIntegrityAlgorithm
    }

-- changed to unique name (CHIMERA Team)
altasecPPKChainID-2   OBJECT-TYPE
    SYNTAX            SnmpAdminString (SIZE(1..255))
    MAX-ACCESS        read-write
    STATUS            current
    DESCRIPTION
        "(U//FOUO) An administratively assigned name to link a group
        of PPKs together.  This object may be referenced by the
        hIPhRuleActionIndex object in the hIPhRuleTable if it is not a
        zero-length string."
    ::= { altasecPPKChainEntry 1 }

-- changed to unique name (CHIMERA Team)
altasecPPKChainOrder  OBJECT-TYPE
    SYNTAX            Unsigned32 (1..65535)
    MAX-ACCESS        read-only
    STATUS            current
    DESCRIPTION
        "(U//FOUO) The order of which this key is applied.
         Lower values occur first (e.g. a hPPKChainOrder of 1 is
         used before a hPPKChainOrder of 2)."
    ::= { altasecPPKChainEntry 2 }

altasecPPKChainIntegrityAlgorithm  OBJECT-TYPE
    SYNTAX                         HaipeIntegrityAlgorithm
    MAX-ACCESS                     read-write
    STATUS                         current
    DESCRIPTION
        "(U//FOUO,PR) The integrity algorithm to be used by this key.
         This integrity algorithm should be manually configured for
         the first key assigned to the chain but later keys added to
         the same chain will have this integrity algorithm field set
         to the same integrity algorithm from the previous key in the
         chain."
    ::= { altasecPPKChainEntry 3 }


-- ********************************************************************
-- Security Policy Database
-- Information on SPD Action  policy.
-- ********************************************************************

altasecTPiphRule  OBJECT IDENTIFIER ::= { altasecTPSecurityPolicyDatabase 1 }
altasecTPiphActions OBJECT IDENTIFIER ::= { altasecTPSecurityPolicyDatabase 3 }

-- ********************************************************************
-- HAIPE SPD Rule Table
--

altasecIPhRuleTable   OBJECT-TYPE
    SYNTAX            SEQUENCE OF ALTASECIPhRuleEntry
    MAX-ACCESS        not-accessible
    STATUS            current
    DESCRIPTION
        "(U//FOUO,PR) The table for configuring AltaSec proprietary extensions
         to the HAIPE-TRAFFIC-PROTECTION-MIB's hIPhRuleTable."
    ::= { altasecTPiphRule 3 }

altasecIPhRuleEntry   OBJECT-TYPE
    SYNTAX            ALTASECIPhRuleEntry
    MAX-ACCESS        not-accessible
    STATUS            current
    DESCRIPTION
        "(U//FOUO) A row which describes the handling of IP
         messages arriving on a particular interface."
    AUGMENTS   { hIPhRuleEntry }
    ::= { altasecIPhRuleTable 1 }

ALTASECIPhRuleEntry ::= SEQUENCE
    {
        altasecIPhRuleActionProtectType              INTEGER,
        altasecIPhRuleActionProtectTransportSAIndex  Unsigned32,
        altasecIPhRuleActionProtectTransportName     SnmpAdminString
    }

altasecIPhRuleActionProtectType    OBJECT-TYPE
    SYNTAX                         INTEGER { tunnel(1), transport(2) }
    MAX-ACCESS                     read-write
    STATUS                         current
    DESCRIPTION
        "(U//FOUO,PR) The type of SA to protect should the parent hIPhRuleAction
         object be set to protectWithPPK or protectWithFF, else no object will
         be returned."
    DEFVAL { tunnel }
    ::= { altasecIPhRuleEntry 4 }

altasecIPhRuleActionProtectTransportSAIndex    OBJECT-TYPE
    SYNTAX                                     Unsigned32
    MAX-ACCESS                                 read-write
    STATUS                                     current
    DESCRIPTION
        "(U//FOUO,PR) The hTPSAIndex value to explicitly link a protect
         transport rule to a transport SA. If this value is zero, then a protect
         transport rule link is attempted on peer HAIPE and both host addresses.
         This may be needed if multiple Transports are configured between the
         same two Source and Destination Addresses. If the rule is not intended
         to protect transport SAs no object will be returned."
    DEFVAL { 0 }
    ::= { altasecIPhRuleEntry 5 }

altasecIPhRuleActionProtectTransportName       OBJECT-TYPE
    SYNTAX                                     SnmpAdminString
    MAX-ACCESS                                 read-only
    STATUS                                     current
    DESCRIPTION
        "(U//FOUO,PR) The device name given to the internal SA device, if
         configured to protect an active Transport SA. If the Transport SA is
         not currently active, it will not have a device name and return a zero
         length string. Other Rule types will not return this object."
    ::= { altasecIPhRuleEntry 6 }

-- ********************************************************************
-- SPD Security Association Transform Actions

altasecTPiphSATransforms OBJECT IDENTIFIER ::= { altasecTPiphActions 2 }

-- ********************************************************************
-- FF Security Association Configuration
-- altasecTPiphFFSA
--

altasecTPiphFFSA         OBJECT IDENTIFIER ::= { altasecTPiphSATransforms 2 }
altasecTPiphFFSAKey      OBJECT IDENTIFIER ::= { altasecTPiphFFSA 1 }

-- ********************************************************************
-- altasecIPhFFSATable
-- Table of FFSA Management
--

altasecIPhFFSATable        OBJECT-TYPE
        SYNTAX             SEQUENCE OF ALTASECIPhFFSAEntry
        MAX-ACCESS         not-accessible
        STATUS             current
        DESCRIPTION
            "(U//FOUO,PR) The table for configuring AltaSec proprietary
             extensions to the HAIPE-TRAFFIC-PROTECTION-MIB's hIPhFFSATable."
        ::= { altasecTPiphFFSAKey 3 }

altasecIPhFFSAEntry     OBJECT-TYPE
        SYNTAX          ALTASECIPhFFSAEntry
        MAX-ACCESS      not-accessible
        STATUS          current
        DESCRIPTION
            "(U//FOUO,PR) A row which describes the proprietary information to
             further configure settings to setup a Security Association with a
             remote HAIPE."
        AUGMENTS   { hIPhFFSAEntry }
        ::= { altasecIPhFFSATable 1 }

ALTASECIPhFFSAEntry ::= SEQUENCE
    {
        altasecIPhFFSADSCPCopyValue                            OCTET STRING,
        altasecIPhFFSAECNValue                                 OCTET STRING,
        altasecIPhFFSAECNCopyValue                             OCTET STRING,
        altasecIPhFFSADFBitSetting                             INTEGER,
        altasecIPhFFSATunnelPreferredFragmentationSide         HaipeSide,
        altasecIPhFFSATunnelPreferredFragmentationSideSetting  HaipeSide,
        altasecIPhFFSAMulticastBypassMode                      TruthValue,
        altasecIPhFFSAMulticastResetSource                     TruthValue
    }

altasecIPhFFSADSCPCopyValue  OBJECT-TYPE
    SYNTAX                   OCTET STRING (SIZE (1))
    MAX-ACCESS               read-write
    STATUS                   current
    DESCRIPTION
        "(U//FOUO,PR) The Differentiated Service Code Points (DSCP)
         value for this SA.

         (U//FOUO,PR) The use of this value is dependent on the value
         of the hIPhFFSADSCP column in its parent hIPhFFSATable row being
         set to set(1). Any other values (acceptlist(3)) will result in
         sets to the object returning an inconsistentValue error.

         (U//FOUO,PR) When the hIPhFFSADSCP column is set to set(1), it
         implicitly sets this object to 0x00.

         (U//FOUO,PR) If the hIPhFFSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hIPhFFSADSCPValue column."
    DEFVAL { '00'h }
    ::= { altasecIPhFFSAEntry 3 }

altasecIPhFFSAECNValue  OBJECT-TYPE
    SYNTAX              OCTET STRING (SIZE (1))
    MAX-ACCESS          read-write
    STATUS              current
    DESCRIPTION
        "(U//FOUO,PR) The indication of how the Explicit Congestion
         Notification (ECN) bits should be treated within this SA.

         (U//FOUO,PR) The use of this value overrides the setting of the
         hIPhFFSAECN column in its parent hTPSATable, which will then return
         a no such instance error.

         (U//FOUO,PR) This value should be one octet in length: 0x00, 0x01,
         0x02, 0x03. Any attempt to set this column to value outside of this
         range should fail with a wrong value error.  The ECN value garnered
         from these lower/right-most 2 of the octet are placed within the
         outgoing packet's Explicit Congestion Notification (ECN) header value."
    DEFVAL { '00'h }
    ::= { altasecIPhFFSAEntry 4 }

altasecIPhFFSAECNCopyValue  OBJECT-TYPE
    SYNTAX                  OCTET STRING (SIZE (1))
    MAX-ACCESS              read-write
    STATUS                  current
    DESCRIPTION
        "(U//FOUO,PR) The indication of how the Explicit Congestion
         Notification (ECN) bits should be treated within this SA.

         (U//FOUO,PR) The use of this value overrides the setting of the
         hIPhFFSAECN column in its parent hTPSATable, which will then return
         a no such instance error.

         (U//FOUO,PR) This value should be one octet in length: 0x00, 0x01,
         0x02, 0x03. Any attempt to set this column to value outside of this
         range should fail with a wrong value error.  Any bits set in these
         lower/right-most 2 of the octet will indicate that those bits be
         copied from the incoming packet's Explicit Congestion Notification
         (ECN) header value to the outgoing packet. Any bits set for this
         value effectively overrides, to copy, those set in the above
         altasecIPhFFSAECNValue column."
    DEFVAL { '00'h }
    ::= { altasecIPhFFSAEntry 5 }

altasecIPhFFSADFBitSetting  OBJECT-TYPE
    SYNTAX                  INTEGER { set(1), clear(2), copy(3) }
    MAX-ACCESS              read-write
    STATUS                  current
    DESCRIPTION
        "(U//FOUO,PR) The user setting of how to handle the DF bit created in
         the CT packet: set it; clear it, or copy the DF bit from the PT packet.

         (U//FOUO,PR) Note: This column is only pertinent to IPv4 traffic that
         is being encrypted (i.e. PT->CT traffic).

         (U//FOUO,PR) Note: This object is always writeable and contains the
         user setting to be applied should IPv4 Fixed Packet Length (FPL) be
         disabled and PT be the Preferred Fragmentation Side as represented by
         the altasecIfv4TunnelPreferredFragmentationSide object. If IPv4 FPL is
         enabled, only 'Clear' is a valid operational value. If IPv4 FPL is
         disabled and CT is the Preferred Fragmentation Side, only 'Copy' and
         'Clear' may become operational. A user setting of 'Set' will translate
         into an operational setting of 'Clear'. Otherwise (IPv4 FPL off & PT
         Frag Side), all three settings are operationally valid. To verify the
         current operational value for this object, see hIPhFFSADFBit."
    DEFVAL { clear }
    ::= { altasecIPhFFSAEntry 6 }

altasecIPhFFSATunnelPreferredFragmentationSide  OBJECT-TYPE
        SYNTAX                               HaipeSide
        MAX-ACCESS                           read-only
        STATUS                               current
        DESCRIPTION
            "(U//FOUO,PR) The Operational Fragmentation Side (pt(1) or ct(2))
             for SAs. If the preferred fragmentation side is CT, then CT
             DFBit(s) will be ignored.

             (U//FOUO,PR) Note: This extension is only applicable to Tunnel SAs
             and will be ignored otherwise. If IPv4 Fixed Packet Length (FPL)
             is enabled, then this object is internally forced to PT. To read
             and write to its user setting (to be utilized once IPv4 FPL is
             disabled) see the
             altasecIPhFFSATunnelPreferredFragmentationSideSetting object."
        DEFVAL { pt }
        ::= { altasecIPhFFSAEntry 7 }

altasecIPhFFSATunnelPreferredFragmentationSideSetting  OBJECT-TYPE
        SYNTAX                                      HaipeSide
        MAX-ACCESS                                  read-write
        STATUS                                      current
        DESCRIPTION
            "(U//FOUO,PR) The desired Fragmentation Side Setting (pt(1) or
             ct(2)) for SAs.

             (U//FOUO,PR) Note: This object is always writeable and contains the
             user setting to be applied should FPL be disabled. To verify
             the current operational value for this object, see
             altasecIPhFFSATunnelPreferredFragmentationSide."
        DEFVAL { pt }
        ::= { altasecIPhFFSAEntry 8 }

altasecIPhFFSAMulticastBypassMode    OBJECT-TYPE
        SYNTAX                       TruthValue
        MAX-ACCESS                   read-write
        STATUS                       current
        DESCRIPTION
            "(U//FOUO,PR) The Multicast Bypass/Host support method for SAs."
        DEFVAL { false }
        ::= { altasecIPhFFSAEntry 9 }

altasecIPhFFSAMulticastResetSource   OBJECT-TYPE
        SYNTAX                       TruthValue
        MAX-ACCESS                   read-write
        STATUS                       current
        DESCRIPTION
            "(U//FOUO,PR) Causes decrypted multicast traffic to have the HAIPE's
             PT IP address as its source address, instead of the multicast
             sender's original IP address."
        DEFVAL { false }
        ::= { altasecIPhFFSAEntry 10 }

-- **********************************************************************
-- Security Association Database Objects   SAD
--

altasecTPSAManagement   OBJECT IDENTIFIER ::= { altasecTPSecurityAssocDatabase 1 }

altasecTPSAManagementSettings OBJECT IDENTIFIER ::= { altasecTPSAManagement 7 }

--
-- Table of SA Management
--

altasecTPSATable           OBJECT-TYPE
        SYNTAX             SEQUENCE OF ALTASECTPSAEntry
        MAX-ACCESS         not-accessible
        STATUS             current
        DESCRIPTION
            "(U//FOUO,PR) This table supplements the information provided in the
             corresponding hTPSATable in the HAIPE-TRAFFIC-PROTECTION-MIB
             with additional proprietary values. The hTPSAIndex column is
             the only index for this table and references its parent
             entry in the aforementioned hTPSATable.

             (U//FOUO,PR) As part of the proprietary extension, configuration
             items that affect the behavior of the SAs may be modified, even
             if the SA is currently active."
        ::= { altasecTPSAManagement 3 }

altasecTPSAEntry        OBJECT-TYPE
        SYNTAX          ALTASECTPSAEntry
        MAX-ACCESS      not-accessible
        STATUS          current
        DESCRIPTION
            "(U//FOUO,PR) A row describing the additional proprietary
             information about current Security Associations (SA's) that
             are not included in the HAIPE hTPSATable."
        AUGMENTS   { hTPSAEntry }
        ::= { altasecTPSATable 1 }

ALTASECTPSAEntry ::= SEQUENCE
    {
        altasecTPSADSCPCopyValue                      OCTET STRING,
        altasecTPSAECNValue                           OCTET STRING,
        altasecTPSAECNCopyValue                       OCTET STRING,
        altasecTPSATTLHopLimit                        INTEGER,
        altasecTPSADFBitSetting                       INTEGER,
        altasecTPSAName                               SnmpAdminString,
        altasecTPSAIsMulticast                        TruthValue,
        altasecTPSAMulticastBypassMode                TruthValue,
        altasecTPSAMulticastResetSource               TruthValue,
        altasecTPSAConnectionStatus                   INTEGER,
        altasecTPSATransformID                        INTEGER,
        altasecTPSATransportPacketsDropped            Counter64,
        altasecTPSATransportFragmentedPacketsDropped  Counter64
    }

altasecTPSADSCPCopyValue  OBJECT-TYPE
    SYNTAX                OCTET STRING (SIZE (1))
    MAX-ACCESS            read-write
    STATUS                current
    DESCRIPTION
        "(U//FOUO,PR) The Differentiated Service Code Points (DSCP)
         value for this SA.

         (U//FOUO,PR) The use of this value is dependent on the value
         of the hTPSADSCP column in its parent hTPSATable row being
         set to set(1). Any other values (acceptlist(3)) will result in
         this value being ignored.

         (U//FOUO,PR) If the hTPSADSCP column is set to set(1), this
         value should be one octet in length in the range 0x00 -
         0x3f. Any attempt to set this column to value outside of
         this range should, in this case, fail with an invalid value
         error. Any bits set in these lower/right-most 6 of the
         octet will indicate that those bits be copied from the
         incoming packet's Differentiated Service Code Points (DSCP)
         header value to the outgoing packet. Any bits set for this
         value effectively overrides, to copy, those set in the
         parent hTPSADSCPValue column."
    DEFVAL { '00'h }
    ::= { altasecTPSAEntry 2 }

altasecTPSAECNValue  OBJECT-TYPE
    SYNTAX           OCTET STRING (SIZE (1))
    MAX-ACCESS       read-write
    STATUS           current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  The
         ECN value garnered from these lower/right-most 2 of the octet
         are placed within the outgoing packet's Explicit Congestion
         Notification (ECN) header value."
    DEFVAL { '00'h }
    ::= { altasecTPSAEntry 3 }

altasecTPSAECNCopyValue  OBJECT-TYPE
    SYNTAX               OCTET STRING (SIZE (1))
    MAX-ACCESS           read-write
    STATUS               current
    DESCRIPTION
        "(U//FOUO,PR) The indication of how the Explicit Congestion
         Notification (ECN) bits should be treated within this SA.

         (U//FOUO,PR) The use of this value is dependent on the value
         of the hTPSAECN column in its parent hTPSATable row being
         set to disabled(1). Any other values (congestionNotification(2),
         admissionControl(3)) will result in this value being ignored.

         (U//FOUO,PR) If the hTPSAECN column is set to disabled(1), this
         value should be one octet in length: 0x00, 0x01, 0x02, 0x03.
         Any attempt to set this column to value outside of this range
         should, in this case, fail with an wrong value error.  Any
         bits set in these lower/right-most 2 of the octet will indicate
         that those bits be copied from the incoming packet's Explicit
         Congestion Notification (ECN) header value to the outgoing
         packet. Any bits set for this value effectively overrides, to
         copy, those set in the above altaTPSAECNValue column."
    DEFVAL { '00'h }
    ::= { altasecTPSAEntry 4 }

altasecTPSATTLHopLimit  OBJECT-TYPE
    SYNTAX              INTEGER (0..255)
    MAX-ACCESS          read-write
    STATUS              current
    DESCRIPTION
        "(U//FOUO,PR) The TTL or Hop Limit value for a packet associated with
         this SA. If this value has not been set when an internal SA goes
         active, it will be overridden with the current box-level default for
         the appropriate address type, from either the hIfv4TTL or hIfv6HopLimit
         objects in the HAIPE-NETWORKING-MIB.
         
         If this value is set to 0, the TTL or Hop Limit will be copied
         from the PT packet header into the CT packet header and
         decremented by one."
    ::= { altasecTPSAEntry 5 }

altasecTPSADFBitSetting  OBJECT-TYPE
    SYNTAX               INTEGER { set(1), clear(2), copy(3) }
    MAX-ACCESS           read-write
    STATUS               current
    DESCRIPTION
        "(U//FOUO,PR) The user setting of how to handle the DF bit created in
         the CT packet: set it; clear it, or copy the DF bit from the PT packet.

         (U//FOUO,PR) Note: This column is only pertinent to IPv4 traffic that
         is being encrypted (i.e. PT->CT traffic).

         (U//FOUO,PR) Note: This object is always writeable and contains the
         user setting to be applied should IPv4 Fixed Packet Length (FPL) be
         disabled and PT be the Preferred Fragmentation Side as represented by
         the altasecIfv4TunnelPreferredFragmentationSide object. If IPv4 FPL is
         enabled, only 'Clear' is a valid operational value. If IPv4 FPL is
         disabled and CT is the Preferred Fragmentation Side, only 'Copy' and
         'Clear' may become operational. A user setting of 'Set' will translate
         into an operational setting of 'Clear'. Otherwise (IPv4 FPL off & PT
         Frag Side), all three settings are operationally valid. To verify the
         current operational value for this object, see hTPSADFBit."
    DEFVAL { clear }
    ::= { altasecTPSAEntry 6 }

altasecTPSAName      OBJECT-TYPE
    SYNTAX           SnmpAdminString
    MAX-ACCESS       read-only
    STATUS           current
    DESCRIPTION
        "(U//FOUO,PR) The device name given to the internal SA device, logically
         grouping two or four entries in the table. If the SA is not currently
         active, it will not have a device name and return a zero length
         string. Device names themselves are unique to the logically linked
         SPI values they identify."
    ::= { altasecTPSAEntry 7 }

altasecTPSAIsMulticast  OBJECT-TYPE
    SYNTAX              TruthValue
    MAX-ACCESS          read-only
    STATUS              current
    DESCRIPTION
        "(U//FOUO,PR) This isMulticast flag is read-only and is provided as a
         convenience to the operator, as this option can be gathered from the IP
         address associated with this SA. If an address has not yet been
         specified, a false TruthValue will be returned."
    ::= { altasecTPSAEntry 8 }

altasecTPSAMulticastBypassMode  OBJECT-TYPE
    SYNTAX                      TruthValue
    MAX-ACCESS                  read-write
    STATUS                      current
    DESCRIPTION
        "(U//FOUO,PR) The Multicast Bypass/Host support method for this specific
          SA. This value is only available should the SA be multicast."
    DEFVAL { false }
    ::= { altasecTPSAEntry 9 }

altasecTPSAMulticastResetSource  OBJECT-TYPE
    SYNTAX                       TruthValue
    MAX-ACCESS                   read-write
    STATUS                       current
    DESCRIPTION
        "(U//FOUO,PR) Causes decrypted multicast traffic to have the HAIPE's PT
         IP address as its source address, instead of the multicast sender's
         original IP address."
    DEFVAL { false }
    ::= { altasecTPSAEntry 10 }

altasecTPSAConnectionStatus  OBJECT-TYPE
    SYNTAX                   INTEGER { unknown(0), up(1), down(2),
                                       noKey(3), noRoute(4), noPolicy(5),
                                       notReachable(6), needSuiteA(7),
                                       needSuiteB(8), invalidKey(9),
                                       noSPI(10), noGCM0(11) }
    MAX-ACCESS               read-write
    STATUS                   current
    DESCRIPTION
        "(U//FOUO,PR) The status of this SA with regards to its ability to
         pass traffic.

         (U//FOUO,PR) This object may be used to manually initiate HIKE, for
         HIKE SAs, by setting this object to 'up'. Similarly a connected HIKE SA
         can be disconnected by setting this object to 'down'. Any other setting
         will result in a wrongValue error. An attempt to modify this setting
         for an Inactive or non-HIKE SA will result in an inconsistentValue
         error.

         (U//FOUO,PR) If FPL is enabled, all Transport SAs for that respective
         interface (IPv4 and/or IPv6) will have a value of 'down', unless the
         Transport's Transform is not supported in the current suite."
    ::= { altasecTPSAEntry 11 }

altasecTPSATransformID       OBJECT-TYPE
    SYNTAX                   INTEGER { unknown(0),
                                       useGlobalTransforms(1),
                                       suiteAmedgcm96eff(2),
                                       suiteAmedgcm128eff(3),
                                       legacymedbip32eff(4),
                                       altasecmedbip32eff(5),
                                       altasecmedbip32bff(6),
                                       legacybatonbip32eff(7),
                                       legacymedbip32bff(8),
                                       legacybatonbip32bff(9),
                                       suiteBaesgcm96mqv(10),
                                       suiteBaesgcm128mqv(11),
                                       suiteAmedgcm96efftran(12),
                                       suiteAmedgcm0efftran(13),
                                       suiteAmedgcm128efftran(14),
                                       suiteBmedgcm96efftran(15),
                                       suiteBmedgcm0efftran(16),
                                       suiteBmedgcm128efftran(17)
                                     }
    MAX-ACCESS               read-write
    STATUS                   current
    DESCRIPTION
        "(U//FOUO,PR) When read, the transform used to protect the traffic as
         determined by the protecting PPK chain for PPK SAs or by the
         negotiated transform for HIKE SAs.
         
         (U//FOUO,PR) When written, only applicable for inactive manually
         configured HIKE SAs, the transform(s) that will be offered for
         negotiation. If 'useGlobalTransforms' is selected then the configured
         list in the hIPhFFSATransformsTable will be offered."
    DEFVAL { useGlobalTransforms }
    ::= { altasecTPSAEntry 12 }

altasecTPSATransportPacketsDropped             OBJECT-TYPE
    SYNTAX                                     Counter64
    MAX-ACCESS                                 read-only
    STATUS                                     current
    DESCRIPTION
        "(U//FOUO,PR) For Transport SAs, if the PT packet length is greater than
         the CT MTU then the packet will be dropped since fragmentation cannot
         occur. This object serves as a counter to indicate the number of
         packets that have been dropped on this SA (the grouped set of SA
         entries by altasecTPSAName) due to packet length since the last reboot.
         Tunnel SAs and non-active Transport SAs do not have this object."
    ::= { altasecTPSAEntry 13 }

altasecTPSATransportFragmentedPacketsDropped   OBJECT-TYPE
    SYNTAX                                     Counter64
    MAX-ACCESS                                 read-only
    STATUS                                     current
    DESCRIPTION
        "(U//FOUO,PR) For Transport SAs, packets that have already been
         fragmented on the PT network cannot be sent to the CT network. This
         object serves as a counter to indicate the number of packets that have
         been dropped on this SA (the grouped set of SA entries by
         altasecTPSAName) due to PT-side fragmentation since the last reboot.
         Tunnel SAs and non-active Transport SAs do not have this object."
    ::= { altasecTPSAEntry 14 }

--
-- Proprietary Global SA Settings
--

altasecESPv1PSEQNMultiplier   OBJECT-TYPE
    SYNTAX                    OCTET STRING (SIZE(8))
    MAX-ACCESS                read-write
    STATUS                    current
    DESCRIPTION
        "(U//FOUO,PR) Global SA setting that allows the ESPv1 PSEQN multiplier
         to change to a user-desired value.  This value is a 64-bit unsigned
         integer represented here as an 8-octet string.  This serves as a
         straightforward way to meet requirements while still keeping
         operability with older AltaSec INEs."
        ::= { altasecTPSAManagementSettings 1 }

altasecESPv3PSEQNMultiplier   OBJECT-TYPE
    SYNTAX                    OCTET STRING (SIZE(8))
    MAX-ACCESS                read-write
    STATUS                    current
    DESCRIPTION
        "(U//FOUO,PR) Global SA setting that allows the ESPv3 PSEQN multiplier
         to change to a user-desired value.  This value is a 64-bit unsigned
         integer represented here as an 8-octet string.  This serves as a
         straightforward way to meet requirements while still keeping
         operability with older AltaSec INEs."
        ::= { altasecTPSAManagementSettings 2 }

-- ********************************************************************
-- altasecKTIBDisabledKeyTable
-- holds the list of keys disabled for in-band key transfersn

altasecKTIBDisabledKeyTableCount OBJECT-TYPE
    SYNTAX      Unsigned32
    MAX-ACCESS  read-only
    STATUS      current
    DESCRIPTION
        "(U//FOUO) The number of rows in the
        ALTASECKIBDisabledKeyTable."
     ::= { altasecKTIBDisabledKeyInformation 1 }

altasecKTIBDisabledKeyTableLastChanged OBJECT-TYPE
    SYNTAX      TimeStamp
    MAX-ACCESS  read-only
    STATUS      current
    DESCRIPTION
        "(U//FOUO) The value of sysUpTime the last time any entry
         in the altasecKTIBDisabledKeyTable was modified, created, or
         deleted by either SNMP or other management method (.eg.,
         via an HMI).

         (U//FOUO) Managers can use this object to ensure that no
         changes to configuration of this table have happened since
         the last time it examined the table.

         (U//FOUO) A value of 0 indicates that no entry has been
         changed since the agent initialized."
     ::= { altasecKTIBDisabledKeyInformation 2 }

altasecKTIBDisabledKeyTable OBJECT-TYPE
    SYNTAX      SEQUENCE OF ALTASECKTIBDisabledKeyEntry
    MAX-ACCESS  not-accessible
    STATUS      current
    DESCRIPTION
        "(U//FOUO) The table for configuring a list of the client's
        keys for which in-band key transfer supersession is disabled.
        This table resides on the client. This proprietary table is necessary in
        that users may optionally load multiple copies of the same key. This
        table differs from the hKTIBDisabledKeyTable in that the PPK unique IDs are
        used as an additional index into the table."
    ::= { altasecKTIBDisabledKeyInformation 3 }

altasecKTIBDisabledKeyEntry OBJECT-TYPE
    SYNTAX      ALTASECKTIBDisabledKeyEntry
    MAX-ACCESS  not-accessible
    STATUS      current
    DESCRIPTION
        "(U//FOUO) A row which identifies a key that is disabled for
        in-band key transfers."
    INDEX { altasecKTIBDKShortTitle, altasecKTIBDKPPKEdition,
            altasecKTIBDKPPKSegment, altasecKTIBDKPPKID }
    ::= { altasecKTIBDisabledKeyTable 1 }

ALTASECKTIBDisabledKeyEntry ::= SEQUENCE
    {
    altasecKTIBDKShortTitle          PPKShortTitle,
    altasecKTIBDKPPKEdition          PPKEdition,
    altasecKTIBDKPPKSegment          HaipeSegment,
    altasecKTIBDKPPKID               Unsigned32,
    altasecKTIBDKRowStatus           RowStatus
    }

-- changed to unique name (CHIMERA Team)
altasecKTIBDKShortTitle  OBJECT-TYPE
    SYNTAX               PPKShortTitle
    MAX-ACCESS           read-create
    STATUS               current
    DESCRIPTION
        "(U//FOUO) The short title of the disabled key."
    ::= { altasecKTIBDisabledKeyEntry 1 }

-- changed to unique name (CHIMERA Team)
altasecKTIBDKPPKEdition  OBJECT-TYPE
    SYNTAX               PPKEdition
    MAX-ACCESS           read-create
    STATUS               current
    DESCRIPTION
        "(U//FOUO) The edition of the disabled key."
    ::= { altasecKTIBDisabledKeyEntry 2 }

-- changed to unique name (CHIMERA Team)
altasecKTIBDKPPKSegment  OBJECT-TYPE
    SYNTAX               HaipeSegment
    MAX-ACCESS           read-create
    STATUS               current
    DESCRIPTION
        "(U//FOUO) The segment number of the disabled key."
    ::= { altasecKTIBDisabledKeyEntry 3 }

altasecKTIBDKPPKID  OBJECT-TYPE
    SYNTAX          Unsigned32
    MAX-ACCESS      read-create
    STATUS          current
    DESCRIPTION
            "(U//FOUO,PR) The unique ID assigned to the disabled key."
        ::= { altasecKTIBDisabledKeyEntry 4 }

-- changed to unique name (CHIMERA Team)
altasecKTIBDKRowStatus  OBJECT-TYPE
    SYNTAX              RowStatus
    MAX-ACCESS          read-create
    STATUS              current
    DESCRIPTION
        "(U//FOUO) The status of the row, by which new entries may
        be created, or old entries deleted from this table.

        (U//FOUO) The value of this object has no effect on whether
        other objects in this row can be modified.

        (U//FOUO) If any column is set to an invalid or unsupported
        value (during row creation or any other time), a wrongValue
        error will be returned for that object.

        (U//FOUO) An active row cannot be changed to an inconsistent
        state (an inconsistentValue error will be returned for the
        object)."
    ::= { altasecKTIBDisabledKeyEntry 5 }

END

--
--            UNCLASSIFIED//FOR OFFICIAL USE ONLY, PROPIN
--
