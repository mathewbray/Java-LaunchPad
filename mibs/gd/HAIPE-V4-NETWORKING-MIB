--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-NETWORKING-MIB  DEFINITIONS  ::= BEGIN

IMPORTS
    hv4Networking                       FROM HAIPE-V4-FEATURE-HIERARCHY-MIB
    OBJECT-TYPE,
    MODULE-IDENTITY, Unsigned32         FROM SNMPv2-SMI
    RowStatus, TruthValue,
    TimeStamp, TestAndIncr              FROM SNMPv2-TC
    IPAddressType, IPAddress,
    HaipeDeviceSide                     FROM HAIPE-V4-TEXTUAL-CONVENTIONS-MIB;

haipev4NetworkingMIB MODULE-IDENTITY
    LAST-UPDATED "201602190530Z"
    ORGANIZATION "HAIPE PO"
    CONTACT-INFO
         "(U//FOUO) Not Available."
    DESCRIPTION
        "(U//FOUO) This MIB defines the HAIPE networking MIB objects."
    REVISION     "201602190530Z"
    DESCRIPTION  "(U//FOUO) MIB 4.2.3 Final"		
    ::= { hv4Networking 1 }

hNetworkingGlobalScalars      OBJECT IDENTIFIER ::= { haipev4NetworkingMIB 1 }

hIPv4Networking               OBJECT IDENTIFIER ::= { haipev4NetworkingMIB 2 }
hIPv4Interfaces               OBJECT IDENTIFIER ::= { hIPv4Networking 1 }
hIPv6Networking               OBJECT IDENTIFIER ::= { haipev4NetworkingMIB 3 }
hIPv6Interfaces               OBJECT IDENTIFIER ::= { hIPv6Networking 1 }

hAddressAssignments           OBJECT IDENTIFIER ::= { haipev4NetworkingMIB 4 }
hInterfacePrefixes            OBJECT IDENTIFIER ::= { haipev4NetworkingMIB 5 }
hDefaultRouters               OBJECT IDENTIFIER ::= { haipev4NetworkingMIB 6 }
hRouterAdvertisements         OBJECT IDENTIFIER ::= { haipev4NetworkingMIB 7 }
hCIDRRoutes                   OBJECT IDENTIFIER ::= { haipev4NetworkingMIB 8 }

hNetworkingNotifications      OBJECT IDENTIFIER ::= { haipev4NetworkingMIB 9 }

-- **********************************************************************
-- Networking Global Scalars
-- **********************************************************************

hIGMPSupportMode OBJECT-TYPE
    SYNTAX     INTEGER {hostIGMP(1), bypassIGMP(2)}
    MAX-ACCESS read-write
    STATUS     current
    DESCRIPTION
        "(U//FOUO) The HAIPE's IGMP support method."
    DEFVAL {hostIGMP}
    ::= { hNetworkingGlobalScalars 1 }

hMLDSupportMode OBJECT-TYPE
    SYNTAX     INTEGER {hostMLD(1), bypassMLD(2)}
    MAX-ACCESS read-write
    STATUS     current
    DESCRIPTION
        "(U//FOUO) The HAIPE's MLD support method."
    DEFVAL {hostMLD}
    ::= { hNetworkingGlobalScalars 2 }

-- **********************************************************************
-- IPv4 Networking
-- **********************************************************************

-- =========
-- IPv4 Interface Table
-- =========

hIPv4IfaceTableCount OBJECT-TYPE
    SYNTAX     Unsigned32
    MAX-ACCESS read-only
    STATUS     current
    DESCRIPTION
        "(U//FOUO) The number of rows in the hIPv4IfaceTable."
    ::= { hIPv4Interfaces 1 }

hIPv4IfaceTableLastChanged OBJECT-TYPE
    SYNTAX     TimeStamp
    MAX-ACCESS read-only
    STATUS     current
    DESCRIPTION
        "(U//FOUO) The value of hSystemUpTime the last time any entry in the
         hIPv4IfaceTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hIPv4Interfaces 2 }

hIPv4IfaceTable OBJECT-TYPE
    SYNTAX     SEQUENCE OF HIPv4IfaceTableEntry
    MAX-ACCESS not-accessible
    STATUS     current
    DESCRIPTION
        "(U//FOUO) The table containing a list of interface objects for IPv4.
         This table contains information for both PT and CT interfaces."
    ::= { hIPv4Interfaces 3 }

hIPv4IfaceTableEntry OBJECT-TYPE
    SYNTAX     HIPv4IfaceTableEntry
    MAX-ACCESS not-accessible
    STATUS     current
    DESCRIPTION
        "(U//FOUO) A row mapping IPv4 interface variables to an interface."
    INDEX  { hIPv4IfaceIndex }
    ::= { hIPv4IfaceTable 1 }

HIPv4IfaceTableEntry ::= SEQUENCE
  {
       hIPv4IfaceIndex                 Unsigned32,
       hIPv4IfaceSide                  HaipeDeviceSide,
       hIPv4IfaceStatus                INTEGER,
       hIPv4IfaceMTU                   Unsigned32,
       hIPv4IfaceTTL                   Unsigned32,
       hIPv4IfaceNATTEnable            TruthValue,
       hIPv4IfaceICMPEnable            TruthValue
  }

hIPv4IfaceIndex OBJECT-TYPE
    SYNTAX     Unsigned32
    MAX-ACCESS not-accessible
    STATUS     current
    DESCRIPTION
        "(U//FOUO) An unique numeric index that identifies this interface.
         Interface Index column is the primary index column for this table.
         Note, this column is populated internally and can not be read or
         configured.

         (U//FOUO) Note that implementations may wish to maintain
         uniqueness between hIPv4IfaceIndex and hIPv6IfaceIndex to ease
         deconfliction issues, especially with tables that are used for both
         IPv4 and IPv6 interfaces (e.g., hAddressAssignTable)." 
    ::= { hIPv4IfaceTableEntry 1 }

hIPv4IfaceSide OBJECT-TYPE
    SYNTAX     HaipeDeviceSide
    MAX-ACCESS read-only
    STATUS     current
    DESCRIPTION
        "(U//FOUO) A given side of the HAIPE device.

         (1) PT: The plain-text side, where unencrypted  traffic is generally
         sent and received.

         (2) CT: The cipher-text side, where encrypted traffic is generally
         sent and received.

         (3) other: An interface that isn't responsible for processing traffic
         between networks, e.g., a management interface or some other
         secondary interface."
    ::= { hIPv4IfaceTableEntry 2 }

hIPv4IfaceStatus OBJECT-TYPE
    SYNTAX     INTEGER {up(1), down(2)}
    MAX-ACCESS read-write
    STATUS     current
    DESCRIPTION
        "(U//FOUO) The current operational state of the interface. (1) Up (2)
         Down.

         (U//FOUO) It is important to note that this value does not affect
         the state of the interface, just the connection to the IPv4 stack."
    ::= { hIPv4IfaceTableEntry 3 }

hIPv4IfaceMTU OBJECT-TYPE
    SYNTAX     Unsigned32
    MAX-ACCESS read-write
    STATUS     current
    DESCRIPTION
        "(U//FOUO) The largest packet, in bytes, that the interface is capable of 
        encapsulating in a single ethernet frame."
    ::= { hIPv4IfaceTableEntry 4 }

hIPv4IfaceTTL OBJECT-TYPE
    SYNTAX     Unsigned32 (1..255)
    MAX-ACCESS read-write
    STATUS     current
    DESCRIPTION
        "(U//FOUO) The TTL Value indicates the time-to-live value for outgoing
         packets sent by this interface.  For PT interface, this applies only
         to HAIPE generated Packets. For CT packets, this applies to all
         packets.

         (U//FOUO) Note this value is not used for packets with TTL values
         prescribed by the protocol (e.g., ICMP PMTU)."
    ::= { hIPv4IfaceTableEntry 5 }

hIPv4IfaceNATTEnable OBJECT-TYPE
    SYNTAX     TruthValue
    MAX-ACCESS read-write
    STATUS     current
    DESCRIPTION
         "(U//FOUO) This object indicates whether or not IKEv1 NAT-T is enabled 
          for IPv4 on this interface.

          (U//FOUO) Note, that this column is only relevant to CT side
          interfaces. When hIPv4IfaceSide is 'pt', this column must not
          exist for that row."
    DEFVAL { true }
    ::= { hIPv4IfaceTableEntry 6 }

    hIPv4IfaceICMPEnable OBJECT-TYPE
    SYNTAX     TruthValue
    MAX-ACCESS read-write
    STATUS     current
    DESCRIPTION
         "(U//FOUO) This object indicates whether or not this interface will
          respond to ICMP messages.

          (U//FOUO) Note, not all ICMP messages will be supported by an
          interface. Security guidance may override the interface's capability
          to respond to an ICMP message. For example, ICMP Redirect and Source
          Quench messages are often ignored by HAIPE implementations."
    DEFVAL { false }
    ::= { hIPv4IfaceTableEntry 7 }

-- **********************************************************************
-- IPv6 Networking
-- **********************************************************************

-- =========
-- IPv6 Interface Table
-- =========

hIPv6IfaceTableCount OBJECT-TYPE
    SYNTAX     Unsigned32
    MAX-ACCESS read-only
    STATUS     current
    DESCRIPTION
        "(U//FOUO) The number of rows in the hIPv6IfaceTable."
    ::= { hIPv6Interfaces 1 }

hIPv6IfaceTableLastChanged OBJECT-TYPE
    SYNTAX     TimeStamp
    MAX-ACCESS read-only
    STATUS     current
    DESCRIPTION
        "(U//FOUO) The value of hSystemUpTime the last time any entry in the
         hIPv6IfaceTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hIPv6Interfaces 2 }

hIPv6IfaceTable OBJECT-TYPE
    SYNTAX     SEQUENCE OF HIPv6IfaceTableEntry
    MAX-ACCESS not-accessible
    STATUS     current
    DESCRIPTION
        "(U//FOUO) The table containing a list of interface objects for IPv6.
         This table contains information for both PT and CT interfaces."
    ::= { hIPv6Interfaces 3 }

hIPv6IfaceTableEntry OBJECT-TYPE
    SYNTAX     HIPv6IfaceTableEntry
    MAX-ACCESS not-accessible
    STATUS     current
    DESCRIPTION
        "(U//FOUO) A row mapping IPv6 interface variables to an interface."
    INDEX  { hIPv6IfaceIndex }
    ::= { hIPv6IfaceTable 1 }

HIPv6IfaceTableEntry ::= SEQUENCE
  {
       hIPv6IfaceIndex                  Unsigned32,
       hIPv6IfaceIdentifier             OCTET STRING,
       hIPv6IfaceSide                   HaipeDeviceSide,
       hIPv6IfaceStatus                 INTEGER,
       hIPv6IfaceMTU                    Unsigned32,
       hIPv6IfaceHopLimit               Unsigned32,
       hIPv6IfaceAutoAddrConfig         TruthValue,
       hIPv6IfaceDAD                    TruthValue,
       hIPv6IfaceRouterSolicitSetting   TruthValue,
       hIPv6IfaceNATTEnable             TruthValue,
       hIPv6IfaceICMPv6Enable           TruthValue
  }

hIPv6IfaceIndex OBJECT-TYPE
    SYNTAX     Unsigned32
    MAX-ACCESS not-accessible
    STATUS     current
    DESCRIPTION
        "(U//FOUO) An unique numeric index that identifies this interface. IPv6
         Interface Index column is the primary index column for this table.
         Note, this column is populated internally and can not be read or
         configured.

         (U//FOUO) Note that implementations may wish to maintain uniqueness
         between hIPv4IfaceIndex and hIPv6IfaceIndex to ease deconfliction
         issues, especially with tables that are used for both IPv4 and IPv6
         interfaces (e.g., hAddressAssignTable)."
    ::= { hIPv6IfaceTableEntry 1 }

hIPv6IfaceIdentifier OBJECT-TYPE
    SYNTAX     OCTET STRING(SIZE(0..8))
    MAX-ACCESS read-write
    STATUS     current
    DESCRIPTION
        "(U//FOUO) The Interface Identifier for this interface. The Interface
         Identifier is combined with an address prefix to form an interface
         address.

         (U//FOUO) By default, the Interface Identifier is auto-configured
         according to the rules of the link type to which this interface
         is attached.

         (U//FOUO) A zero length identifier may be used where appropriate. One
         possible example is a loopback interface."
    ::= { hIPv6IfaceTableEntry 2 }

hIPv6IfaceSide OBJECT-TYPE
    SYNTAX     HaipeDeviceSide
    MAX-ACCESS read-only
    STATUS     current
    DESCRIPTION
        "(U//FOUO) A given side of the HAIPE device. 

         (1) PT: The plain-text side, where unencrypted traffic is generally sent
         and received.
         
         (2) CT: The cipher-text side, where encrypted traffic is generally sent
         and received.        
         
         (3) other: A interface that isn't responsible for processing
         traffic between networks, e.g., a management interface or some other
         secondary interface."
    ::= { hIPv6IfaceTableEntry 3 }

hIPv6IfaceStatus OBJECT-TYPE
    SYNTAX     INTEGER {up(1), down(2)}
    MAX-ACCESS read-write
    STATUS     current
    DESCRIPTION
        "(U//FOUO) The current operational state of the interface.  (1) Up (2)
         Down

         (U//FOUO) It is important to note that this value does not affect
         the state of the interface, just the connection to the IPv6 stack."
    ::= { hIPv6IfaceTableEntry 4 }

hIPv6IfaceMTU OBJECT-TYPE
    SYNTAX     Unsigned32
    MAX-ACCESS read-write
    STATUS     current
    DESCRIPTION
        "(U//FOUO) The largest packet, in bytes, that the interface is capable of 
        encapsulating in a single ethernet frame."
    ::= { hIPv6IfaceTableEntry 5 }

hIPv6IfaceHopLimit OBJECT-TYPE
    SYNTAX     Unsigned32 (1..255)
    MAX-ACCESS read-write
    STATUS     current
    DESCRIPTION
        "(U//FOUO) The Hop Limit value indicates the time-to-live value for
         outgoing packets sent by this interface. For PT interface, this
         applies only to HAIPE generated Packets. For CT interface, this
         applies to all packets.

         (U//FOUO) Note this value is not used for packets with Hop Limit
         values prescribed by the protocol (e.g., ICMP PMTU)."
    ::= { hIPv6IfaceTableEntry 6 }

hIPv6IfaceAutoAddrConfig OBJECT-TYPE
    SYNTAX     TruthValue
    MAX-ACCESS read-write
    STATUS     current
    DESCRIPTION
        "(U//FOUO) The indication of whether stateless or stateful address
         configuration should take place on this interface.  A value of 'true'
         indicates that stateless address configuration should take place. The
         default value is 'false', which indicates that no stateless address
         configuration should take place.

         (U//FOUO) This object must be in sync with the hIPv6IfaceDAD object. 
         If stateless address configuration is enabled, duplicate address detection
         must also be enabled. If one is disabled, the other must also be disabled. 

         (U//FOUO) Note, that this column is only relevant to CT side
         interfaces. When hIPv6IfaceSide is 'pt', this column must not exist
         for that row."
    DEFVAL { false }
    ::= { hIPv6IfaceTableEntry 7 }

hIPv6IfaceDAD OBJECT-TYPE
    SYNTAX     TruthValue
    MAX-ACCESS read-write
    STATUS     current
    DESCRIPTION
        "(U//FOUO) The indication of whether the interface should use
         duplicate address detection.  A value of 'true' indicates that
         duplicate address detection should be attempted. The default value is
         'false', which indicates that no duplicate address detection should
         take place.
         
         (U//FOUO) This object must be in sync with the hIPv6IfaceAutoAddrConfig
         object. If stateless address configuration is enabled, duplicate address
         detection must also be enabled. If one is disabled, the other must also
         be disabled."
    DEFVAL { false }
    ::= { hIPv6IfaceTableEntry 8 }

hIPv6IfaceRouterSolicitSetting OBJECT-TYPE
    SYNTAX     TruthValue
    MAX-ACCESS read-write
    STATUS     current
    DESCRIPTION
        "(U//FOUO) The indication of whether an interface should send Router Solicitations.
         A value of 'true' indicates that sending Router Solicitations is allowed.  The
         default is to not send Router Solicitations, 'false'.

         (U//FOUO) Note, that this column is only relevant to CT side interfaces. When
         hIPv6IfaceSide is 'pt', this column must not exist for that row."
    DEFVAL { false } 
    ::= { hIPv6IfaceTableEntry 9 }

hIPv6IfaceNATTEnable OBJECT-TYPE
    SYNTAX     TruthValue
    MAX-ACCESS read-write
    STATUS     current
    DESCRIPTION
        "(U//FOUO) This object indicates whether or not IKEv1 NAT-T is enabled 
         for IPv6 on this interface.

         (U//FOUO) Note, that this column is only relevant to CT side interfaces. When
         hIPv6IfaceSide is 'pt', this column must not exist for that row."
    DEFVAL { true }
    ::= { hIPv6IfaceTableEntry 10 }


hIPv6IfaceICMPv6Enable OBJECT-TYPE
    SYNTAX     TruthValue
    MAX-ACCESS read-write
    STATUS     current
    DESCRIPTION
        "(U//FOUO) This object indicates whether or not this interface will
         respond to ICMPv6 messages from the IPv6 network to which it is connected.

         (U//FOUO) Note, not all ICMPv6 messages will be supported by an interface.
         Security guidance or HAIPE IS requirements may override the interface's
         capability to respond to an ICMP message. For example, ICMPv6 Destination
         Unreachable can be ignored by HAIPE implementations.

         (U//FOUO) HAIPS shall reject an attempt to set this object when it is
         in conflict with other settings (for example hIPv6IfaceDAD) and return 
         an inconsistent value setting."
    DEFVAL { false }
    ::= { hIPv6IfaceTableEntry 11 }

-- **********************************************************************
-- Address Assignment
-- **********************************************************************

-- =========
-- Address Assignment Table
-- =========

hAddressAssignTableCount OBJECT-TYPE
    SYNTAX     Unsigned32
    MAX-ACCESS read-only
    STATUS     current
    DESCRIPTION
        "(U//FOUO) The number of rows in the hAddressAssignTable."
    ::= { hAddressAssignments 1 }

hAddressAssignTableLastChanged OBJECT-TYPE
    SYNTAX     TimeStamp
    MAX-ACCESS read-only
    STATUS     current
    DESCRIPTION
        "(U//FOUO) The value of hSystemUpTime the last time any entry in the
         hAddressAssignTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hAddressAssignments 2 }

hAddressAssignTable OBJECT-TYPE
    SYNTAX     SEQUENCE OF HAddressAssignTableEntry
    MAX-ACCESS not-accessible
    STATUS     current
    DESCRIPTION
        "(U//FOUO) The table containing a list of all IP addresses assigned to
         each interface.  It supports both IPv4 and IPv6 addresses."
    ::= { hAddressAssignments 3 }

hAddressAssignTableEntry OBJECT-TYPE
    SYNTAX     HAddressAssignTableEntry
    MAX-ACCESS not-accessible
    STATUS     current
    DESCRIPTION
        "(U//FOUO) A row which describes an interface to IP address mapping."
    INDEX  { hAddressAssignIndex, hAddressAssignType, hAddressAssignAddr }
    ::= { hAddressAssignTable 1 }

HAddressAssignTableEntry ::= SEQUENCE
{
   hAddressAssignIndex             Unsigned32,
        hAddressAssignType              IPAddressType,
   hAddressAssignAddr              IPAddress,
   hAddressAssignPrefixLength      Unsigned32,
   hAddressAssignRowStatus         RowStatus
}

hAddressAssignIndex OBJECT-TYPE
    SYNTAX     Unsigned32
    MAX-ACCESS not-accessible
    STATUS     current
    DESCRIPTION
        "(U//FOUO) The interface to which this address is assigned. This should
         be a reference to the hIPv4IfaceTable or the hIPv6IfaceTable."
    ::= { hAddressAssignTableEntry 1 }

hAddressAssignType OBJECT-TYPE
    SYNTAX     IPAddressType
    MAX-ACCESS not-accessible
    STATUS     current
    DESCRIPTION
         "(U//FOUO) The Internet Protocol version, IPv4 or IPv6, of the IP
          address assigned to this interface. Specifically, the value of this
          property determines the size and format of the hAddressAssignAddr."
    ::= { hAddressAssignTableEntry 2 }

hAddressAssignAddr OBJECT-TYPE
    SYNTAX     IPAddress
    MAX-ACCESS not-accessible
    STATUS     current
    DESCRIPTION
        "(U//FOUO) The Internet Protocol addressing information for the
         interface indicated by this row. The size and format of this column
         is determined by the hAddressAssignType."
    ::= { hAddressAssignTableEntry 3 }

hAddressAssignPrefixLength OBJECT-TYPE
    SYNTAX     Unsigned32 (0..128)
    MAX-ACCESS read-create
    STATUS     current
    DESCRIPTION
        "(U//FOUO) The prefix length for this address."
    ::= { hAddressAssignTableEntry 4 }

hAddressAssignRowStatus OBJECT-TYPE
    SYNTAX     RowStatus
    MAX-ACCESS read-create
    STATUS     current
    DESCRIPTION
       "(U//FOUO) The status of the row, by which new entries may be created,
       or old entries deleted from this table.

       (U//FOUO) Entries created within this table may not become active unless
       all read-create columns in this table have valid values, as detailed
       by each individual column's description.

       (U//FOUO) At a minimum, implementations must support createAndGo and
       destroy management functions. Support for createAndWait, active,
       notInService, and notReady management functions is optional."
    ::= { hAddressAssignTableEntry 5 }

-- **********************************************************************
-- Interface Prefixes
-- **********************************************************************

-- =========
-- Interface Prefix Table
-- =========

hPrefixTableCount OBJECT-TYPE
    SYNTAX     Unsigned32
    MAX-ACCESS read-only
    STATUS     current
    DESCRIPTION
        "(U//FOUO) The number of rows in the hPrefixTable."
    ::= { hInterfacePrefixes 1 }

hPrefixTableLastChanged OBJECT-TYPE
    SYNTAX     TimeStamp
    MAX-ACCESS read-only
    STATUS     current
    DESCRIPTION
        "(U//FOUO) The value of hSystemUpTime the last time any entry in the
         hPrefixTable was modified, created, or deleted by either SNMP or other
         management method (e.g. via an HMI).

         (U//FOUO) Managers can use this object to ensure that no changes to
         configuration of this table have happened since the last time the
         manager examined the table.

         (U//FOUO) A value of 0 indicates that no entry has been changed since
         the agent initialized."
    ::= { hInterfacePrefixes 2 }

hPrefixTable OBJECT-TYPE
    SYNTAX     SEQUENCE OF HPrefixTableEntry
    MAX-ACCESS not-accessible
    STATUS     current
    DESCRIPTION
        "(U//FOUO) This table allows the user to determine the source of an IPv6
         address or set of IPv6 addresses, and allows other tables to share the
         information via a pointer rather than by copying.

         (U//FOUO) For example, when the node configures both a unicast and anycast
         address for a prefix, the hPrefix objects for those addresses will
         point to a single row in this table.

         (U//FOUO) The table only provides support for IPv6 prefixes.

         (U//FOUO) All prefixes used by this entity should be included in this
         table independent of how the entity learned the prefix. This table
         isn't limited to prefixes learned from router advertisements."
    ::= { hInterfacePrefixes 3 }

hPrefixTableEntry OBJECT-TYPE
    SYNTAX     HPrefixTableEntry
    MAX-ACCESS not-accessible
    STATUS     current
    DESCRIPTION
        "(U//FOUO) A row in the hPrefixTable"
    INDEX  { hPrefixIndex, hPrefixPrefix, hPrefixPrefixLength }
    ::= { hPrefixTable 1 }

HPrefixTableEntry ::= SEQUENCE
{
   hPrefixIndex                    Unsigned32,
   hPrefixPrefix                   OCTET STRING,
   hPrefixPrefixLength             Unsigned32,
   hPrefixOrigin                   INTEGER,
   hPrefixOnLinkFlag               TruthValue,
   hPrefixAutoAddrConfigFlag       TruthValue,
   hPrefixValidLifetime            Unsigned32,
   hPrefixPreferredLifetime        Unsigned32
}

hPrefixIndex OBJECT-TYPE
    SYNTAX     Unsigned32
    MAX-ACCESS not-accessible
    STATUS     current
    DESCRIPTION
        "(U//FOUO) A unique numeric index that identifies this interface. This
         column is the primary index for this table."
    ::= { hPrefixTableEntry 1 }

hPrefixPrefix OBJECT-TYPE
    SYNTAX     OCTET STRING (SIZE(1..32))
    MAX-ACCESS not-accessible
    STATUS     current
    DESCRIPTION
        "(U//FOUO) The IPv6 address prefix.

         (U//FOUO) Implementers need to be aware that, if the size of
         IpAddressPrefixPrefix exceeds 114 octets, then OIDS of instances of
         columns in this row will have more than 128 sub-identifiers and cannot
         be accessed using SNMPv1, SNMPv2c, or SNMPv3."
    ::= { hPrefixTableEntry 2 }

hPrefixPrefixLength OBJECT-TYPE
    SYNTAX     Unsigned32 (0..128)
    MAX-ACCESS not-accessible
    STATUS     current
    DESCRIPTION
        "(U//FOUO) The prefix length associated with this prefix. Specifically,
         the value of this property determines the size of hPrefixPrefix. The
         value 0 has no special meaning for this object.  It simply refers to
         address '::/0'."
    ::= { hPrefixTableEntry 3 }

hPrefixOrigin OBJECT-TYPE
    SYNTAX     INTEGER { other(1), dhcp(2), linklayer(3), random(4) }
    MAX-ACCESS read-only
    STATUS     current
    DESCRIPTION
        "(U//FOUO) The origin of this prefix.

         dhcp(2) indicates an address  that was assigned to this system by a
         DHCP server.

         linklayer(3) indicates an address created by IPv6 stateless auto-
         configuration.

         random(4) indicates an address chosen by the system at random, e.g.,
         an RFC 3041 privacy address."
    ::= { hPrefixTableEntry 4 }

hPrefixOnLinkFlag OBJECT-TYPE
    SYNTAX     TruthValue
    MAX-ACCESS read-only
    STATUS     current
    DESCRIPTION
        "(U//FOUO) Note: this object is based on the  TruthValue TEXTUAL-
         CONVENTION. This object has the value 'true(1)', if this prefix can be
         used for on-link determination; otherwise, the value is 'false(2)'.

         (U//FOUO) Also see Reference:

         (U//FOUO) RFC 2461, especially sections 2 and 4.6.2 and RFC 2462."
    ::= { hPrefixTableEntry 5 }

hPrefixAutoAddrConfigFlag OBJECT-TYPE
    SYNTAX     TruthValue
    MAX-ACCESS read-only
    STATUS     current
    DESCRIPTION
        "(U//FOUO) Autonomous address configuration flag.  When
         true(1), indicates that this prefix can be used for autonomous address
         configuration (i.e., can be used to form a local interface address).
         If false(2), it is not used to auto-configure a local interface
         address.

         (U//FOUO) Also see Reference:

         (U//FOUO) RFC 2461, especially sections 2 and 4.6.2 and RFC 2462."
    ::= { hPrefixTableEntry 6 }

hPrefixValidLifetime OBJECT-TYPE
    SYNTAX     Unsigned32
    MAX-ACCESS read-only
    STATUS     current
    DESCRIPTION
        "(U//FOUO) The remaining length of time, in seconds, that this prefix
         will continue to be preferred, i.e., time until deprecation.

         (U//FOUO) A value of 4,294,967,295 represents infinity.

         (U//FOUO) The address generated from a deprecated prefix should no
         longer be used as a source address in new communications, but packets
         received on such an interface are processed as expected.

         (U//FOUO) Also see Reference:

         (U//FOUO) RFC 2461, especially sections 2 and 4.6.2 and RFC 2462."
    ::= { hPrefixTableEntry 7 }

hPrefixPreferredLifetime OBJECT-TYPE
    SYNTAX     Unsigned32
    MAX-ACCESS read-only
    STATUS     current
    DESCRIPTION
        "(U//FOUO) The remaining length of time, in seconds, that this prefix
         will continue to be valid, i.e., time until invalidation. A value of
         4,294,967,295 represents infinity. The address generated from an
         invalidated prefix should not appear as the destination or source
         address of a packet.

         (U//FOUO) Also see Reference:

         (U//FOUO) RFC 2461, especially sections 2 and 4.6.2 and RFC 2462."
    ::= { hPrefixTableEntry 8 }


-- **********************************************************************
-- Default Routers
-- **********************************************************************

-- =========
-- Default Router Table
-- =========

hDefaultRouterTableCount OBJECT-TYPE
    SYNTAX     Unsigned32
    MAX-ACCESS read-only
    STATUS     current
    DESCRIPTION
        "(U//FOUO) The number of rows in the hDefaultRouterTable."
    ::= { hDefaultRouters 1 }

hDefaultRouterTableLastChanged OBJECT-TYPE
    SYNTAX     TimeStamp
    MAX-ACCESS read-only
    STATUS     current
    DESCRIPTION
        "(U//FOUO) The value of hSystemUpTime the last time any entry in the
         hDefaultRouterTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hDefaultRouters 2 }

hDefaultRouterTable OBJECT-TYPE
    SYNTAX     SEQUENCE OF HDefaultRouterTableEntry
    MAX-ACCESS not-accessible
    STATUS     current
    DESCRIPTION
        "(U//FOUO) The table used to describe the default routers known to this
         entity."
    ::= { hDefaultRouters 3 }

hDefaultRouterTableEntry OBJECT-TYPE
    SYNTAX     HDefaultRouterTableEntry
    MAX-ACCESS not-accessible
    STATUS     current
    DESCRIPTION
        "(U//FOUO) A row in the hDefaultRouterTable."
    INDEX  { hDefaultRouterIndex, hDefaultRouterAddrType,
             hDefaultRouterAddr }
    ::= { hDefaultRouterTable 1 }

HDefaultRouterTableEntry ::= SEQUENCE
  {
       hDefaultRouterIndex             Unsigned32,
       hDefaultRouterAddrType          IPAddressType,
       hDefaultRouterAddr              IPAddress,
       hDefaultRouterLifetime          Unsigned32,
       hDefaultRouterPreference        INTEGER
  }

hDefaultRouterIndex OBJECT-TYPE
    SYNTAX     Unsigned32
    MAX-ACCESS not-accessible
    STATUS     current
    DESCRIPTION
         "(U//FOUO) The index value that uniquely identifies the interface
          by which the router can be reached. "
    ::= { hDefaultRouterTableEntry 1 }

hDefaultRouterAddrType OBJECT-TYPE
    SYNTAX     IPAddressType
    MAX-ACCESS not-accessible
    STATUS     current
    DESCRIPTION
         "(U//FOUO) The Internet Protocol version, IPv4 or IPv6, of the IP address
         for the default router. Specifically, the value of this property
         determines the size and format of the hDefaultRouterAddr."
    ::= { hDefaultRouterTableEntry 2 }

hDefaultRouterAddr OBJECT-TYPE
    SYNTAX     IPAddress
    MAX-ACCESS not-accessible
    STATUS     current
    DESCRIPTION
         "(U//FOUO) The Internet Protocol addressing information for the the
         default router. The size and format of this column is determined by
         the hDefaultRouterAddrType."
    ::= { hDefaultRouterTableEntry 3 }

hDefaultRouterLifetime OBJECT-TYPE
    SYNTAX     Unsigned32
    MAX-ACCESS read-only
    STATUS     current
    DESCRIPTION
        "(U//FOUO) The remaining length of time, in seconds, that this router
         will continue to be useful as a default router. A value of zero
         indicates that it is no longer useful as a default router. It is left
         to the implementer of the MIB as to whether a router with a lifetime of
         zero is removed from the list.

         (U//FOUO) For IPv6, this value should be extracted from the router
         advertisement messages.

         (U//FOUO) Also see Reference:

         (U//FOUO) For IPv6 RFC 2462 sections 4.2 and 6.3.4."
    ::= { hDefaultRouterTableEntry 4 }

hDefaultRouterPreference OBJECT-TYPE
    SYNTAX     INTEGER
    MAX-ACCESS read-only
    STATUS     current
    DESCRIPTION
        "(U//FOUO) An indication of preference given to this router as a default
         router as described in the Default Router Preferences document.
         Treating the value as a 2 bit signed integer allows for simple
         arithmetic comparisons.

         (U//FOUO) For IPv4 routers or IPv6 routers that are not using the
         updated router advertisement format, this object is set to medium (0).

         (U//FOUO) Also see Reference:

         (U//FOUO) RFC 4191, section 2.1 -2 reserved -1 low 0 medium 1 high."
    DEFVAL { 0 }
    ::= { hDefaultRouterTableEntry 5 }


-- **********************************************************************
-- Router Advertisements
-- **********************************************************************

-- =========
-- Router Advertisement Table
-- =========

hIPv6RouterAdverTableCount OBJECT-TYPE
    SYNTAX     Unsigned32
    MAX-ACCESS read-only
    STATUS     current
    DESCRIPTION
        "(U//FOUO) The number of rows in the hIPv6RouterAdverTable."
    ::= { hRouterAdvertisements 1 }

hIPv6RouterAdverTableLastChanged OBJECT-TYPE
    SYNTAX     TimeStamp
    MAX-ACCESS read-only
    STATUS     current
    DESCRIPTION
        "(U//FOUO) The value of hSystemUpTime the last time any entry in the
         hIPv6RouterAdverTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hRouterAdvertisements 2 }

hIPv6RouterAdverTable OBJECT-TYPE
    SYNTAX     SEQUENCE OF HIPv6RouterAdverTableEntry
    MAX-ACCESS not-accessible
    STATUS     current
    DESCRIPTION
        "(U//FOUO) The containing information used to construct router
         advertisements."
    ::= { hRouterAdvertisements 3 }

hIPv6RouterAdverTableEntry OBJECT-TYPE
    SYNTAX     HIPv6RouterAdverTableEntry
    MAX-ACCESS not-accessible
    STATUS     current
    DESCRIPTION
        "(U//FOUO) An entry containing information used to construct router
         advertisements.

         (U//FOUO) Information in this table is persistent, and when this
         object is written, the entity should save the change to non-volatile
         storage."
    INDEX  { hIPv6RouterAdverIfIndex }
    ::= { hIPv6RouterAdverTable 1 }

HIPv6RouterAdverTableEntry ::= SEQUENCE
{
        hIPv6RouterAdverIfIndex              Unsigned32,
        hIPv6RouterAdverEnable               TruthValue,
        hIPv6RouterAdverMaxInterval          Unsigned32,
        hIPv6RouterAdverMinInterval          Unsigned32,
        hIPv6RouterAdverManagedFlag          TruthValue,
        hIPv6RouterAdverConfigFlag           TruthValue,
        hIPv6RouterAdverMTU                  Unsigned32,
        hIPv6RouterAdverReachableTime        Unsigned32,
        hIPv6RouterAdverRetransTime          Unsigned32,
        hIPv6RouterAdverHopLimit             Unsigned32,
        hIPv6RouterAdverDefLifetime          Unsigned32,
        hIPv6RouterAdverRowStatus            RowStatus
}

hIPv6RouterAdverIfIndex OBJECT-TYPE
    SYNTAX     Unsigned32
    MAX-ACCESS not-accessible
    STATUS     current
    DESCRIPTION
        "(U//FOUO) A unique numeric index that identifies the interface
         on which router advertisements, constructed with the information
         contained in this row, will be transmitted. This value is the
         primary index for this row."
    ::= { hIPv6RouterAdverTableEntry 1 }

hIPv6RouterAdverEnable OBJECT-TYPE
    SYNTAX     TruthValue
    MAX-ACCESS read-create
    STATUS     current
    DESCRIPTION
        "(U//FOUO) This column is a flag indicating whether the router
         will send periodic router advertisements and respond to router
         solicitations on this interface.

         (U//FOUO) [true] this interface will send router advertisements
         and respond to router solicitations.

         (U//FOUO) [false] this interface will not send router
         advertisements or respond to router solicitations."
    ::= { hIPv6RouterAdverTableEntry 2 }

hIPv6RouterAdverMaxInterval OBJECT-TYPE
    SYNTAX     Unsigned32
    MAX-ACCESS read-create
    STATUS     current
    DESCRIPTION
        "(U//FOUO) The maximum time allowed between sending unsolicted
         router advertisements from this interface."
    ::= { hIPv6RouterAdverTableEntry 3 }

hIPv6RouterAdverMinInterval OBJECT-TYPE
    SYNTAX     Unsigned32
    MAX-ACCESS read-create
    STATUS     current
    DESCRIPTION
        "(U//FOUO) The minimum time allowed between sending unsolicited
         router advertisements from this interface.

         (U//FOUO) The default is 0.33 * hIPv6RouterAdverMaxInterval,
         however in the case of a low value for hIPv6RouterAdverMaxInterval,
         the minimum value for this object is restricted to 3."
    ::= { hIPv6RouterAdverTableEntry 4 }

hIPv6RouterAdverManagedFlag OBJECT-TYPE
    SYNTAX     TruthValue
    MAX-ACCESS read-create
    STATUS     current
    DESCRIPTION
        "(U//FOUO) This column is a flag that is placed into the 'managed
         address configuration' flag field in router advertisements sent
         from this interface."
    DEFVAL { false }
    ::= { hIPv6RouterAdverTableEntry 5 }

hIPv6RouterAdverConfigFlag OBJECT-TYPE
    SYNTAX     TruthValue
    MAX-ACCESS read-create
    STATUS     current
    DESCRIPTION
        "(U//FOUO) This column is a flag that is placed into the 'other
         stateful configuration' flag field in router advertisements sent
         from this interface."
    DEFVAL { false }
    ::= { hIPv6RouterAdverTableEntry 6 }

hIPv6RouterAdverMTU OBJECT-TYPE
    SYNTAX     Unsigned32
    MAX-ACCESS read-create
    STATUS     current
    DESCRIPTION
        "(U//FOUO) This column indicates the value to be placed in the MTU
         options field in router advertisements sent by the router on this
         interface.

         (U//FOUO) A value of zero indicates that no MTU options are sent."
    DEFVAL { 0 }
    ::= { hIPv6RouterAdverTableEntry 7 }

hIPv6RouterAdverReachableTime OBJECT-TYPE
    SYNTAX     Unsigned32
    MAX-ACCESS read-create
    STATUS     current
    DESCRIPTION
        "(U//FOUO) This column indicates the value to be placed in the
         reachable time field in router advertisement messages sent from
         this interface.

         (U//FOUO) A value of zero in the router advertisement indicates that the
         advertisement isn't specifying a value for reachable time."
    DEFVAL { 0 }
    ::= { hIPv6RouterAdverTableEntry 8 }

hIPv6RouterAdverRetransTime OBJECT-TYPE
    SYNTAX     Unsigned32
    MAX-ACCESS read-create
    STATUS     current
    DESCRIPTION
        "(U//FOUO) This column indicates the value to be placed in the
         retransmit time field in router advertisements sent from this
         interface.

         (U//FOUO) A value of zero in the router advertisement indicates
         that the advertisement isn't specifying a value for retrans time."
    DEFVAL { 0 }
    ::= { hIPv6RouterAdverTableEntry 9 }

hIPv6RouterAdverHopLimit OBJECT-TYPE
    SYNTAX     Unsigned32
    MAX-ACCESS read-create
    STATUS     current
    DESCRIPTION
        "(U//FOUO) This column indicates the default value to be placed in
         the current hop limit field in router advertisements sent from
         this interface.

         (U//FOUO) A value of zero in the router advertisement indicates that
         the advertisement isn't specifying a value for the current hop limit.

         (U//FOUO) The default value should be set to the value specified in
         the IANA web pages (www.iana.org) at the time of the implementation."
    ::= { hIPv6RouterAdverTableEntry 10 }

hIPv6RouterAdverDefLifetime OBJECT-TYPE
    SYNTAX     Unsigned32
    MAX-ACCESS read-create
    STATUS     current
    DESCRIPTION
        "(U//FOUO) This column indicates the value to be placed in the router
         lifetime field of router advertisements sent from this interface. This
         value must be either 0 or between hIPv6RouterAdverMaxInterval and
         9000 seconds.

         (U//FOUO) A value of zero indicates that the router is not to be used
         as a default router.

         (U//FOUO) The default value is 3 * hIPv6RouterAdverMaxInterval."
    ::= { hIPv6RouterAdverTableEntry 11 }

hIPv6RouterAdverRowStatus OBJECT-TYPE
    SYNTAX     RowStatus
    MAX-ACCESS read-create
    STATUS     current
    DESCRIPTION
        "(U//FOUO) The status of the row by which new entries may be created,
         existing entries enabled/disabled or existing entries deleted from
         this table.

         (U//FOUO) Entries created within this table may not become active
         unless all read-create columns of this table have valid values, as
         detailed by each individual column's description.

         (U//FOUO) If an implementation has a row preconfigured it MUST at a 
         minimum allow modification of the row.  If a device does not have this 
         row preconfigured, at a minimum, implementations must support createAndGo 
         and destroy management functions. Support for createAndWait, active, 
         notInService, and notReady management functions is optional."
    ::= { hIPv6RouterAdverTableEntry 12 }

-- **********************************************************************
-- CIDR Routes
-- **********************************************************************

-- =========
-- CIDR Route Table
-- =========

hCIDRRouteTableCount OBJECT-TYPE
    SYNTAX     Unsigned32
    MAX-ACCESS read-only
    STATUS     current
    DESCRIPTION
        "(U//FOUO) The number of rows in the hCIDRRouteTable."
    ::= { hCIDRRoutes 1 }

hCIDRRouteTableLastChanged OBJECT-TYPE
    SYNTAX     TimeStamp
    MAX-ACCESS read-only
    STATUS     current
    DESCRIPTION
        "(U//FOUO) The value of hSystemUpTime the last time any entry in the
         hCIDRRouteTable was modified, created, or deleted by either SNMP or
         other management method (e.g. via an HMI).

         (U//FOUO) Managers can use this object to ensure that no changes to
         configuration of this table have happened since the last time the
         manager examined the table.

         (U//FOUO) A value of 0 indicates that no entry has been changed since
         the agent initialized."
    ::= { hCIDRRoutes 2 }

hCIDRRouteTable OBJECT-TYPE
    SYNTAX     SEQUENCE OF HCIDRRouteTableEntry
    MAX-ACCESS not-accessible
    STATUS     current
    DESCRIPTION
        "(U//FOUO) This entity's IP Routing table.

         (U//FOUO) Also see Reference:

         (U//FOUO) RFC 1213 Section 6.6, The IP Group."
    ::= { hCIDRRoutes 3 }

hCIDRRouteTableEntry OBJECT-TYPE
    SYNTAX     HCIDRRouteTableEntry
    MAX-ACCESS not-accessible
    STATUS     current
    DESCRIPTION
        "(U//FOUO) A row in the hCIDRRouteTable"
    INDEX  { hCIDRRouteAddrType, hCIDRRouteAddr,
             hCIDRRouteSide, hCIDRRoutePrefixLength,
             hCIDRRoutePolicy, hCIDRRouteNextHopType, 
             hCIDRRouteNextHop }
    ::= { hCIDRRouteTable 1 }

HCIDRRouteTableEntry ::= SEQUENCE
  {
      hCIDRRouteAddrType              IPAddressType,
      hCIDRRouteAddr                  IPAddress,
      hCIDRRouteSide                  HaipeDeviceSide,
      hCIDRRoutePrefixLength          Unsigned32,
      hCIDRRoutePolicy                Unsigned32,
      hCIDRRouteNextHopType           IPAddressType,
      hCIDRRouteNextHop               IPAddress,
      hCIDRRouteIfIndex               Unsigned32,
      hCIDRRouteType                  INTEGER,
      hCIDRRouteProtocol              INTEGER,
      hCIDRRouteMetric                INTEGER,
      hCIDRRouteRowStatus             RowStatus
  }

hCIDRRouteAddrType OBJECT-TYPE
    SYNTAX     IPAddressType
    MAX-ACCESS not-accessible
    STATUS     current
    DESCRIPTION
         "(U//FOUO) The type of the hCIDRRouteAddr as defined in the IPAddress 
          MIB.

         (U//FOUO) Only those address types that may appear in an actual
         routing table are allowed as values of this object.

         (U//FOUO) Also see referenece: RFC 4001."
    ::= { hCIDRRouteTableEntry 1 }

hCIDRRouteAddr OBJECT-TYPE
    SYNTAX     IPAddress
    MAX-ACCESS not-accessible
    STATUS     current
    DESCRIPTION
         "(U//FOUO) The destination IP address of this route.

         (U//FOUO) The type of this address is determined by the value of the
         CIDR Route Table Destination Address Type object.

         (U//FOUO) The values for the index hCIDRRouteAddr and 
         hCIDRRoutePrefixLength must be consistent. When the value of 
         hCIDRRouteAddr is x, then the bitwise logical-AND of x with the value 
         of the mask formed from the corresponding index object 
         hCIDRRoutePrefixLength MUST be equal to x. If not, then the index pair 
         is not consistent and an inconsistentNameerror must be returned on SET 
         or CREATE requests."
    ::= { hCIDRRouteTableEntry 2 }

hCIDRRouteSide OBJECT-TYPE
    SYNTAX     HaipeDeviceSide
    MAX-ACCESS not-accessible
    STATUS     current
    DESCRIPTION
        "(U//FOUO) A given side of the HAIPE device. (1) PT: The 
        plain-text side, where unencrypted traffic is generally sent 
        and received. (2) CT: the cipher-text side, where encrypted 
        traffic is generally sent and received. (3) other: An 
        interface that isn't responsible for processing traffic 
        between networks, e.g., a management interface or some other 
        secondary interface."
    ::= { hCIDRRouteTableEntry 3 }

hCIDRRoutePrefixLength OBJECT-TYPE
    SYNTAX     Unsigned32
    MAX-ACCESS not-accessible
    STATUS     current
    DESCRIPTION
         "(U//FOUO) Indicates the number of leading one bits that form the mask
          to be logical-ANDed with the destination address before being 
          compared to the value in the hCIDRRouteAddr field.

          (U//FOUO) The values for the index objects hCIDRRouteAddr and
          hCIDRRoutePrefixLength must be consistent.  When the value of 
          hCIDRRouteAddr is x, then the bitwise logical-AND of x with the value 
          of the mask formed from the corresponding index object 
          hCIDRRoutePrefixLength MUST be equal to x.  If not, then the index 
          pair is not consistent and an inconsistentName error must be 
          returned on SET or CREATE requests."
    ::= { hCIDRRouteTableEntry 4 }

hCIDRRoutePolicy OBJECT-TYPE
    SYNTAX     Unsigned32   
    MAX-ACCESS not-accessible
    STATUS     current
    DESCRIPTION
         "(U//FOUO) This object is an opaque object without any defined
          semantics.  Its purpose is to serve as an additional index that may 
          delineate between multiple entries to the same destination.  
          The value 0 shall be used as the default value for this 
          object."
    DEFVAL {0}
    ::= { hCIDRRouteTableEntry 5 }

hCIDRRouteNextHopType OBJECT-TYPE
    SYNTAX     IPAddressType
    MAX-ACCESS not-accessible
    STATUS     current
    DESCRIPTION
        "(U//FOUO) The type of hCIDRRouteNextHop address.

         (U//FOUO) Only those address types that may appear in an
         actual routing table are allowed as values of this object.

         (U//FOUO) Also see Reference: RFC 4001."
    ::= { hCIDRRouteTableEntry 6 }

hCIDRRouteNextHop OBJECT-TYPE
    SYNTAX     IPAddress
    MAX-ACCESS not-accessible
    STATUS     current
    DESCRIPTION
         "(U//FOUO) On remote routes, the address of the next system
         en route. For non-remote routes, a zero length string. The type of
         this address is determined by the value of the hCIDRRouteNextHopType
         object."
    ::= { hCIDRRouteTableEntry 7 }

hCIDRRouteIfIndex OBJECT-TYPE
    SYNTAX      Unsigned32
    MAX-ACCESS read-create
    STATUS     current
    DESCRIPTION
        "(U//FOUO) Note: this object is based on the InterfaceIndexOrZero
         TEXTUAL-CONVENTION.

         (U//FOUO) The ifIndex value that identifies the
         local interface through which the next hop of this route should be
         reached. A value of 0 is valid and represents the scenario where no
         interface is specified."
    ::= { hCIDRRouteTableEntry 8 }

hCIDRRouteType OBJECT-TYPE
    SYNTAX     INTEGER {other(1), reject(2), local(3), remote(4), blackhole(5)}
    MAX-ACCESS read-create
    STATUS     current
    DESCRIPTION
        "(U//FOUO) The type of route.  Note that local(3) refers to a route for
         which the next hop is the final destination; remote(4) refers to a
         route for which the next hop is not the final destination.

         (U//FOUO) Routes that do not result in traffic forwarding or rejection
         should not be displayed, even if the implementation keeps them stored
         internally.

         (U//FOUO) reject(2) refers to a route that, if matched, discards the
         message as unreachable and returns a notification (e.g., ICMP error) to
         the message sender.  This is used in some protocols as a means of
         correctly aggregating routes.

         (U//FOUO) blackhole(5) refers to a route that, if matched, discards the
         message silently."
    ::= { hCIDRRouteTableEntry 9 }

hCIDRRouteProtocol OBJECT-TYPE
    SYNTAX     INTEGER {other(1), local(2), netmgmt(3), icmp(4), egp(5), ggp(6),
                        hello(7), rip(8), isIs(9), esIs(10), ciscoIgrp(11),
         bbnSpfIgp(12), ospf(13), bgp(14), idpr(15),
         ciscoEigrp(16), dvmrp(17)}
    MAX-ACCESS read-only
    STATUS     current
    DESCRIPTION
        "(U//FOUO) Note: this object is based on the IANAipRouteProtocol
        TEXTUAL-CONVENTION. 

        (U//FOUO) The routing mechanism via which this route was learned. 
        Inclusion of values for gateway routing protocols is not intended to
        imply that hosts should support those protocols."
    ::= { hCIDRRouteTableEntry 10 } 

hCIDRRouteMetric OBJECT-TYPE
    SYNTAX     INTEGER
    MAX-ACCESS read-create
    STATUS     current
    DESCRIPTION
        "(U//FOUO) The primary routing metric for this route.  The semantics of
         this metric are determined by the routing protocol specified in the
         route's CIDR Route Table Route Protocol value.  If this metric is not
         used, its value should be set to -1."
    DEFVAL     {-1}
    ::= { hCIDRRouteTableEntry 11 }

hCIDRRouteRowStatus OBJECT-TYPE
    SYNTAX     RowStatus
    MAX-ACCESS read-create
    STATUS     current
    DESCRIPTION
        "(U//FOUO) The status of the row by which new entries may be created,
         existing entries enabled/disabled or existing entries deleted from
         this table.

         (U//FOUO) Entries created within this table may not become active
         unless all read-create columns of this table have valid values, as
         detailed by each individual column's description.

         (U//FOUO) At a minimum, implementations must support createAndGo and
         destroy management functions. Support for createAndWait, active,
         notInService, and notReady management functions is optional."
    ::= { hCIDRRouteTableEntry 12 }

END
