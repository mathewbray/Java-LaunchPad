--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-RCIK-MIB  DEFINITIONS  ::= BEGIN

IMPORTS
    hv4RCIK                             FROM HAIPE-V4-FEATURE-HIERARCHY-MIB
    OBJECT-TYPE, Unsigned32,
    MODULE-IDENTITY                     FROM SNMPv2-SMI                         
    RowStatus, TimeStamp, DateAndTime   FROM SNMPv2-TC
    IPAddress, IPAddressType            FROM HAIPE-V4-TEXTUAL-CONVENTIONS-MIB;

haipev4RCIKMIB MODULE-IDENTITY
    LAST-UPDATED "201602190530Z"
    ORGANIZATION "HAIPE PO"
    CONTACT-INFO
        "(U//FOUO) Not Available"
    DESCRIPTION
        "(U//FOUO) This MIB defines the HAIPE RCIK Net Controller and Client MIB 
         objects.  Note that ALL objects within this module must not exist if an
         implementation does not support the Remote Cryptographic Ignition 
         Key Client Extension and/or the Remote Cryptographic Ignitioin Key Net
         Controller Extension."
    REVISION     "201602190530Z"
    DESCRIPTION  "(U//FOUO) MIB 4.2.3 Final"		 
    ::= { hv4RCIK 1 }

-- **********************************************************************
-- RCIK Information Segments
-- **********************************************************************
hRCIKControlObjects              OBJECT IDENTIFIER ::= { haipev4RCIKMIB 1 }
hRCIKScalars                     OBJECT IDENTIFIER ::= { haipev4RCIKMIB 2 }
hRCIKNotifications               OBJECT IDENTIFIER ::= { haipev4RCIKMIB 3 }
hRCIKNetController               OBJECT IDENTIFIER ::= { haipev4RCIKMIB 4 }
hRCIKClient                      OBJECT IDENTIFIER ::= { haipev4RCIKMIB 5 }

hRCIKNetControllerControlObjects OBJECT IDENTIFIER ::= { hRCIKNetController 1 }
hRCIKNetControllerScalars        OBJECT IDENTIFIER ::= { hRCIKNetController 2 }
hRCIKNetControllerNotifications  OBJECT IDENTIFIER ::= { hRCIKNetController 3 }
hRCIKClients                     OBJECT IDENTIFIER ::= { hRCIKNetController 4 }

hRCIKClientControlObjects        OBJECT IDENTIFIER ::= { hRCIKClient 1 }
hRCIKClientScalars               OBJECT IDENTIFIER ::= { hRCIKClient 2 }
hRCIKClientNotifications         OBJECT IDENTIFIER ::= { hRCIKClient 3 }
hRCIKNetControllers              OBJECT IDENTIFIER ::= { hRCIKClient 4 }


-- **********************************************************************
-- RCIK Net Controller Control Objects
-- **********************************************************************

-- **********************************************************************
-- RCIK Net Controller Scalars 
-- **********************************************************************
                                     
-- **********************************************************************
-- RCIK Net Controller Notifications 
-- **********************************************************************

-- =========
-- RCIK Client Table
-- =========
hRCIKClientTableCount OBJECT-TYPE
    SYNTAX     Unsigned32
    MAX-ACCESS read-only
    STATUS     current
    DESCRIPTION
        "(U//FOUO) The number of rows in the hRCIKClientTable."
    ::= { hRCIKClients 1}

hRCIKClientTableLastChanged OBJECT-TYPE
    SYNTAX     TimeStamp
    MAX-ACCESS read-only
    STATUS     current
    DESCRIPTION
        "(U//FOUO) The value of hSystemUpTime the last time any entry in the
         hRCIKClientTable was modified, created, or deleted by either SNMP or 
         other management method (e.g. via an HMI).

         (U//FOUO) Managers can use this object to ensure that no changes to
         configuration of this table have happened since the last time it
         examined the table.

         (U//FOUO) A value of 0 indicates that no entry has been changed since
         the agent initialized."
    ::= { hRCIKClients 2}

hRCIKClientTable OBJECT-TYPE
    SYNTAX     SEQUENCE OF HRCIKClientTableEntry
    MAX-ACCESS not-accessible
    STATUS     current
    DESCRIPTION
        "(U//FOUO) This table stores Remote Cryptograpic Ignition Key Client 
         IP Address information.  This table is supported by RCIK Net 
         Controllers.

         (U//FOUO) This table is used to control the transmission of RCIK 
         messages to RCIK Clients and to provide additional RCIK information 
         (e.g., current known RCIK Client state)."
    ::= { hRCIKClients 3 }

hRCIKClientTableEntry OBJECT-TYPE
    SYNTAX     HRCIKClientTableEntry
    MAX-ACCESS not-accessible
    STATUS     current
    DESCRIPTION
        "(U//FOUO) A row in the hRCIKClientTable specifying an authorized RCIK 
        Client IP address information."
    INDEX  { hRCIKClientIPAddressType, hRCIKClientIPAddress }
    ::= { hRCIKClientTable 1 }

HRCIKClientTableEntry ::= SEQUENCE
{
   hRCIKClientIPAddressType   IPAddressType,
   hRCIKClientIPAddress	      IPAddress,
   hRCIKIssueAction           INTEGER,
   hRCIKClientState           INTEGER,
   hRCIKRCSTimestamp          DateAndTime,
   hRCIKClientRowStatus	      RowStatus
}

hRCIKClientIPAddressType OBJECT-TYPE
    SYNTAX     IPAddressType
    MAX-ACCESS not-accessible
    STATUS     current
    DESCRIPTION
        "(U//FOUO) IP version of a RCIK Client's CT IP Address (IPv4/IPv6).   
        Note, this value determines the size and format of the associated 
        hRCIKClientIPAddress value."
    ::= { hRCIKClientTableEntry 1 }

hRCIKClientIPAddress OBJECT-TYPE
    SYNTAX     IPAddress
    MAX-ACCESS not-accessible
    STATUS     current
    DESCRIPTION
        "(U//FOUO) CT IP Address of a RCIK Client."
    ::= { hRCIKClientTableEntry 2 }
    
hRCIKIssueAction OBJECT-TYPE
    SYNTAX     INTEGER { ready(1), createRCS(2), deleteRCS(3), unlock(4),
                         lock(5) }
    MAX-ACCESS read-create
    STATUS     current
    DESCRIPTION
        "(U//FOUO)The means to issue an RCIK message to a RCIK Client.  Note, 
         upon completion of an RCIK action, the column's value is set back to 
         the default value 'ready'.  In most cases, RCIK action completion is 
         determined by the receipt of an RCIK Response message.  The exception
         to this is the RCIK Lock message."
    DEFVAL { ready }
    ::= { hRCIKClientTableEntry 3 }
    
hRCIKClientState OBJECT-TYPE
    SYNTAX     INTEGER { unknown(1), unlocked(2), locked(3) }
    MAX-ACCESS read-only
    STATUS     current
    DESCRIPTION
        "(U//FOUO)Indicates the current known RCIK Client state.  Note, the 
         actual state of the managed device may be different than what is 
         indicated in this column.  For example, an RCIK Client with the 
         Physical CIK removed will be in a locked state unbeknown to the 
         RCIK Net Controller."
    ::= { hRCIKClientTableEntry 4 }

hRCIKRCSTimestamp OBJECT-TYPE
    SYNTAX     DateAndTime
    MAX-ACCESS read-only
    STATUS     current
    DESCRIPTION
        "(U//FOUO) Time the stored RCS for the RCIK Client was received by the 
         RCIK Net Controller.  Note, this column also serves as an indicator 
         that an RCS is currently stored for the client - a value of all ZEROs 
         for the year indicates that there is currently no RCS associated."
    ::= { hRCIKClientTableEntry 5 }

hRCIKClientRowStatus OBJECT-TYPE
    SYNTAX     RowStatus
    MAX-ACCESS read-create
    STATUS     current
    DESCRIPTION
        "(U//FOUO) The status of the row, by which new entries may be created, 
         or old entries deleted from this table. 

         (U//FOUO) If values are not valid for the required columns, an 
         inconsistentName error will be returned for this object. 

         (U//FOUO) If any column is set to an invalid or unsupported value 
         (during row creation or any other time), a wrongValue error will be 
         returned for that object. 

         (U//FOUO) An active row may not be changed to an inconsistent state.
         If such an attempt is made, an inconsistentValue error will be 
         returned. In other words, any new values must be valid values for an 
         active row.
         
         (U//FOUO) At a minimum, implementations must support createAndGo and
         destroy management functions. Support for createAndWait, active,
         notInService, and notReady management functions is optional."
    ::= { hRCIKClientTableEntry 6 }



-- **********************************************************************
-- RCIK Client Control Objects
-- **********************************************************************

-- **********************************************************************
-- RCIK Client Scalars 
-- **********************************************************************

-- =========
-- RCIK Net Controller Table
-- =========
hRCIKNetControllerTableCount OBJECT-TYPE
    SYNTAX     Unsigned32
    MAX-ACCESS read-only
    STATUS     current
    DESCRIPTION
        "(U//FOUO) The number of rows in the hRCIKNetControllerTable."
    ::= { hRCIKNetControllers 1}

hRCIKNetConTableLastChanged OBJECT-TYPE
    SYNTAX     TimeStamp
    MAX-ACCESS read-only
    STATUS     current
    DESCRIPTION
        "(U//FOUO) The value of hSystemUpTime the last time any entry in the
         hRCIKNetControllerTable was modified, created, or deleted by either 
         SNMP or other management method (e.g. via an HMI).

         (U//FOUO) Managers can use this object to ensure that no changes to
         configuration of this table have happened since the last time it
         examined the table.

         (U//FOUO) A value of 0 indicates that no entry has been changed since
         the agent initialized."
    ::= { hRCIKNetControllers 2}

hRCIKNetControllerTable OBJECT-TYPE
    SYNTAX     SEQUENCE OF HRCIKNetControllerTableEntry
    MAX-ACCESS not-accessible
    STATUS     current
    DESCRIPTION
        "(U//FOUO) This table stores authorized Remote Cryptograpic Ignition Key 
         Net Controller IP Address information.  This table is supported by
         RCIK Clients.

         (U//FOUO) This table is consulted when the local HAIPE (i.e., RCIK 
         Client) receives RCIK messages through an established Security
         Association.  Namely, for such messages, RCIK Clients can only accept 
         RCIK messages from an authorized RCIK Net Controller."
    ::= { hRCIKNetControllers 3 }

hRCIKNetControllerTableEntry OBJECT-TYPE
    SYNTAX     HRCIKNetControllerTableEntry
    MAX-ACCESS not-accessible
    STATUS     current
    DESCRIPTION
        "(U//FOUO) A row in the hRCIKNetControllerTable specifying an authorized 
         RCIK Net Controller IP address information."
    INDEX  { hRCIKNetControllerIPAddressType, hRCIKNetControllerIPAddress }
    ::= { hRCIKNetControllerTable 1 }

HRCIKNetControllerTableEntry ::= SEQUENCE
{
   hRCIKNetControllerIPAddressType   IPAddressType,
   hRCIKNetControllerIPAddress	     IPAddress,
   hRCIKNetControllerRowStatus	     RowStatus
}

hRCIKNetControllerIPAddressType OBJECT-TYPE
    SYNTAX     IPAddressType
    MAX-ACCESS not-accessible
    STATUS     current
    DESCRIPTION
        "(U//FOUO) IP version of an authorized RCIK Net Controller's CT IP 
        Address (IPv4/IPv6).   Note, this value determines the size and format 
        of the associated hRCIKNetControllerIPAddress value."
    ::= { hRCIKNetControllerTableEntry 1 }

hRCIKNetControllerIPAddress OBJECT-TYPE
    SYNTAX     IPAddress
    MAX-ACCESS not-accessible
    STATUS     current
    DESCRIPTION
        "(U//FOUO) CT IP Address of an authorized RCIK Net Controller."
    ::= { hRCIKNetControllerTableEntry 2 }

hRCIKNetControllerRowStatus OBJECT-TYPE
    SYNTAX     RowStatus
    MAX-ACCESS read-create
    STATUS     current
    DESCRIPTION
        "(U//FOUO) The status of the row, by which new entries may be created, 
         or old entries deleted from this table. 

         (U//FOUO) If values are not valid for the required columns, an 
         inconsistentName error will be returned for this object. 

         (U//FOUO) If any column is set to an invalid or unsupported value 
         (during row creation or any other time), a wrongValue error will be 
         returned for that object. 

         (U//FOUO) An active row may not be changed to an inconsistent state.
         If such an attempt is made, an inconsistentValue error will be 
         returned. In other words, any new values must be valid values for an 
         active row.
         
         (U//FOUO) At a minimum, implementations must support createAndGo and
         destroy management functions. Support for createAndWait, active,
         notInService, and notReady management functions is optional."
    ::= { hRCIKNetControllerTableEntry 3 }
    
-- **********************************************************************
-- RCIK Client Notifications 
-- **********************************************************************



END
