--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-BANDWIDTH-MANAGEMENT-MIB  DEFINITIONS  ::= BEGIN

IMPORTS
    OBJECT-TYPE, Unsigned32,
    NOTIFICATION-TYPE,
    MODULE-IDENTITY                     FROM SNMPv2-SMI                         
    SnmpAdminString                     FROM SNMP-FRAMEWORK-MIB
    RowPointer, RowStatus, TimeStamp    FROM SNMPv2-TC
    hManualSAIndex, hIKEv2CHILDSAIndex,
    hIKEv2IKESAIndex                    FROM HAIPE-V4-TRAFFIC-PROTECTION-MIB
    hv4BandwidthManagement              FROM HAIPE-V4-FEATURE-HIERARCHY-MIB;

haipev4BandwidthManagementMIB MODULE-IDENTITY
    LAST-UPDATED "201602190530Z"
    ORGANIZATION "HAIPE PO"
    CONTACT-INFO
        "(U//FOUO) Not Available"
    DESCRIPTION
        "(U//FOUO) This MIB defines the HAIPE Bandwidth Management MIB objects.
         Note that ALL objects within this module must not exist if an
         implementation does not support Bandwidth Management."
    REVISION     "201602190530Z"
    DESCRIPTION  "(U//FOUO) MIB 4.2.3 Final"		 
    ::= { hv4BandwidthManagement 1 }

-- **********************************************************************
-- Bandwidth Management Information Segments
-- **********************************************************************

hBMControlObjects               OBJECT IDENTIFIER ::= { haipev4BandwidthManagementMIB 1 }
hBMGlobalScalars                OBJECT IDENTIFIER ::= { haipev4BandwidthManagementMIB 2 }
hBMParameters                   OBJECT IDENTIFIER ::= { haipev4BandwidthManagementMIB 3 }

hBMParametersProfiles           OBJECT IDENTIFIER ::= { hBMParameters 1 }
hEstablishedBMParameters        OBJECT IDENTIFIER ::= { hBMParameters 2 }
hEstabSABMParameters            OBJECT IDENTIFIER ::= { hEstablishedBMParameters 1 }

-- Defines all traffic protection notifications
hBMNotifications                OBJECT IDENTIFIER ::= { haipev4BandwidthManagementMIB 4 }


-- **********************************************************************
-- Bandwidth Management Control Objects
-- **********************************************************************

-- **********************************************************************
-- Bandwidth Management Global Scalars
-- **********************************************************************

-- **********************************************************************
-- Bandwidth Management Parameters
-- **********************************************************************

-- =========
-- Bandwidth Management Parameters Profile Table
-- =========

hBMParamsProfileTableCount OBJECT-TYPE
    SYNTAX     Unsigned32
    MAX-ACCESS read-only
    STATUS     current
    DESCRIPTION
        "(U//FOUO) The number of rows in the hBMParamsProfileTable."
    ::= { hBMParametersProfiles 1 }

hBMParamsProfileTableLastChanged OBJECT-TYPE
    SYNTAX     TimeStamp
    MAX-ACCESS read-only
    STATUS     current
    DESCRIPTION
        "(U//FOUO) The value of hSystemUpTime the last time any entry in the
         hBMParamsProfileTable was modified, created, or deleted by either SNMP
         or other management method (e.g. via an HMI).

         (U//FOUO) Managers can use this object to ensure that no changes to
         configuration of this table have happened since the last time it
         examined the table.

         (U//FOUO) A value of 0 indicates that no entry has been changed since
         the agent initialized."
    ::= { hBMParametersProfiles 2 }

hBMParamsProfileTable OBJECT-TYPE
    SYNTAX     SEQUENCE OF HBMParamsProfileTableEntry
    MAX-ACCESS not-accessible
    STATUS     current
    DESCRIPTION
        "(U//FOUO) This table includes the Bandwidth Management parameters that
         are transmitted in a Maximum Receive Claim [MRC] and Reservation
         Request [RR]. For an MRC, this is its Bandwidth Value. For
         an RR, this includes its Bandwidth Value, Bucket Size, Bucket Rate, and
         Timer value. Note the syntax used in each column aligns with the MRC
         and RR packet formats.

         (U//FOUO) This table is consulted when the local HAIPE wishes to send
         an MRC and/or RR in HAIPE IKEv2 exchanges (i.e., HAIPE IKEv2 IKE_AUTH 
         exchanges for first CHILD_SA creations and HAIPE IKEv2
         CREATE_CHILD_SA exchanges for new CHILD_SAs creations or CHILD_SA 
         rekeys). The values in this table will either be manually configured 
         by the manager or auto-populated by the HAIPE after internal
         calculation.

         (U//FOUO) Note that this table is consulted by the hPolicyRuleTable
         directly (via the hPolicyRuleUseBM column) to obtain the required 
         parameters for an MRC and RR."
    ::= { hBMParametersProfiles 3 }

hBMParamsProfileTableEntry OBJECT-TYPE
    SYNTAX     HBMParamsProfileTableEntry
    MAX-ACCESS not-accessible
    STATUS     current
    DESCRIPTION
        "(U//FOUO) A row in the hBMParamsProfileTable specifying one set of
         Bandwidth Management parameters used to send in an MRC and RR at the
         time of creating an IKEv2 CHILD_SA."
    INDEX  { hBMParamsProfileName }
    ::= { hBMParamsProfileTable 1 }

HBMParamsProfileTableEntry ::= SEQUENCE
{
   hBMParamsProfileName            SnmpAdminString,
   hBMProfileMRCBMValue            OCTET STRING,
   hBMProfileRRBMValue             OCTET STRING,
   hBMProfileRRTimer               Unsigned32,
   hBMProfileRRBucketSize          OCTET STRING,
   hBMProfileRRBucketRate          OCTET STRING,
   hBMProfileRowStatus             RowStatus
}

hBMParamsProfileName OBJECT-TYPE
    SYNTAX     SnmpAdminString (SIZE(1..32))
    MAX-ACCESS not-accessible
    STATUS     current
    DESCRIPTION
        "(U//FOUO) The unique administrative name for one set of Bandwidth
         Management parameters. This column is the primary index column for the
         hBMParamsProfileTable."
    ::= { hBMParamsProfileTableEntry 1 }

hBMProfileMRCBMValue OBJECT-TYPE
    SYNTAX     OCTET STRING (SIZE(4))
    UNITS      "bytes/second"
    MAX-ACCESS read-create
    STATUS     current
    DESCRIPTION
        "(U//FOUO) Represented in bytes per second, this indicates the maximum
         allowed transmission rate for the given SA. The value in this column is
         used to populate the 'Bandwidth Value' field in a Maximum Receive Claim
         [MRC].

         (U//FOUO) If this object is populated, MRC will be signaled during SA
         negotiation (e.g., HAIPE IKEv2 CHILD_SA creation negotiations) for the 
         associated rule entry.
         
         (U//FOUO) The value in this column is expressed as a 32-bit IEEE
         floating-point number."
    ::= { hBMParamsProfileTableEntry 2 }

hBMProfileRRBMValue OBJECT-TYPE
    SYNTAX     OCTET STRING (SIZE(4))
    UNITS      "bytes/second"
    MAX-ACCESS read-create
    STATUS     current
    DESCRIPTION
        "(U//FOUO) Represented in bytes per second, this indicates the peak
         transmission rate (i.e. how much of the peer's bandwidth should be
         reserved for the given SA). The value in this column is used to
         populate the 'Bandwidth Value' field in a Reservation Request [RR].

         (U//FOUO) If this object is not populated, then an RR will not be 
         negotiated.
         
         (U//FOUO) The value in this column is expressed as a 32-bit IEEE
         floating-point number."
    ::= { hBMParamsProfileTableEntry 3 }

hBMProfileRRTimer OBJECT-TYPE
    SYNTAX     Unsigned32
    UNITS      "seconds"
    MAX-ACCESS read-create
    STATUS     current
    DESCRIPTION
        "(U//FOUO) The length of time, in seconds, for which the resource
         reservation is requested. The value in this column is used to populate
         the 'Timer' field in a Reservation Request [RR].

         (U//FOUO) If this object is not populated or set to 0, then an RR will
         not be negotiated.
         
         (U//FOUO) Note that the largest Unsigned32 value, 4294967295,
         indicates that the lifetime of the RR is 'infinity'."
    ::= { hBMParamsProfileTableEntry 4 }

hBMProfileRRBucketSize OBJECT-TYPE
    SYNTAX     OCTET STRING (SIZE(4))
    UNITS      "bytes"
    MAX-ACCESS read-create
    STATUS     current
    DESCRIPTION
        "(U//FOUO) A measure, in bytes, of the sender's Token Bucket.
         The value in this column is used to populate the 'Bucket
         Size' field in a Reservation Request [RR].

         (U//FOUO) If this object is not populated, then an RR will not be 
         negotiated.
         
         (U//FOUO) The value in this column is expressed as a 32-bit IEEE
         floating-point number."
    ::= { hBMParamsProfileTableEntry 5 }

hBMProfileRRBucketRate OBJECT-TYPE
    SYNTAX     OCTET STRING (SIZE(4))
    UNITS      "bytes/second"
    MAX-ACCESS read-create
    STATUS     current
    DESCRIPTION
        "(U//FOUO) The rate, in bytes per second, at which tokens are deposited
         in the bucket. The value in this column is used to populate
         the 'Bucket Rate' field in a Reservation Request [RR].

         (U//FOUO) If this object is not populated, then an RR will not be 
         negotiated.        
         
         (U//FOUO) The value in this column is expressed as a 32-bit IEEE
         floating-point number."
    ::= { hBMParamsProfileTableEntry 6 }

hBMProfileRowStatus OBJECT-TYPE
    SYNTAX     RowStatus
    MAX-ACCESS read-create
    STATUS     current
    DESCRIPTION
        "(U//FOUO) The status of the row, by which new entries may be created, 
         or old entries deleted from this table. 

         (U//FOUO) If a Maximum Receive Claim is to be sent for the CHILD_SA, 
         the hBMProfileMRCBMValue column must include a valid value before the 
         row is set to 'createAndGo'. If a Reservation Request [RR] 
         is to be sent, the following columns must include values before the row
         is set to 'createAndGo': hBMProfileRRBMValue, hBMProfileRRTimer, 
         hBMProfileRRBucketSize, and hBMProfileRRBucketRate. If values are not
         valid for the required columns, an inconsistentName error will be 
         returned for this object. 

         (U//FOUO) If any column is set to an invalid or unsupported value 
         (during row creation or any other time), a wrongValue error will be 
         returned for that object. 

         (U//FOUO) An active row may not be changed to an inconsistent state.
         If such an attempt is made, an inconsistentValue error will be 
         returned. In other words, any new values must be valid values for an 
         active row.
         
         (U//FOUO) At a minimum, implementations must support createAndGo and
         destroy management functions. Support for createAndWait, active,
         notInService, and notReady management functions is optional."
    ::= { hBMParamsProfileTableEntry 7 }

-- =========
-- Established SA Bandwidth Management Parameters Table
-- =========

hEstBMParamTableCount OBJECT-TYPE
    SYNTAX     Unsigned32
    MAX-ACCESS read-only
    STATUS     current
    DESCRIPTION
        "(U//FOUO) The number of rows in the hEstBMParamTable."
    ::= { hEstabSABMParameters 1 }

hEstBMParamTableLastChanged OBJECT-TYPE
    SYNTAX     TimeStamp
    MAX-ACCESS read-only
    STATUS     current
    DESCRIPTION
        "(U//FOUO) The value of hSystemUpTime the last time any entry in the
         hEstBMParamTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hEstabSABMParameters 2 }

hEstBMParamTable OBJECT-TYPE
    SYNTAX     SEQUENCE OF HEstBMParamTableEntry
    MAX-ACCESS not-accessible
    STATUS     current
    DESCRIPTION
        "(U//FOUO) For Manual SAs, this table includes the Maximum Receive 
	 Bandwidth Value that has been negotiated out of band. For IKEv2
	 CHILD_SAs, this table includes the communication characteristics that 
	 have been negotiated via the Maximum Receive Claim [MRC] and 
	 Reservation Request [RR] messages, specifically during the IKEv2 
	 IKE_AUTH, CREATE_CHILD_SA, or INFORMATIONAL exchanges.
	 
         (U//FOUO) The parameters listed in this table should be interpreted
         differently depending on the SA direction. See each individual column
         for more details."
    ::= { hEstabSABMParameters 3 }

hEstBMParamTableEntry OBJECT-TYPE
    SYNTAX     HEstBMParamTableEntry
    MAX-ACCESS not-accessible
    STATUS     current
    DESCRIPTION
        "(U//FOUO) A row in the hEstBMParamTable specifying one set of
         Bandwidth Management parameters that has been negotiated. For a
	 Manual SA, this includes the Maximum Receive Bandwidth Value parameter
	 negotiated out of band. For an IKEv2 CHILD_SA, this includes all the
	 communication characteristics negotiated via the Maximum Receive Claim 
	 [MRC] and Reservation Request [RR] messages.
	 
         (U//FOUO) For an IKEv2 CHILD_SA, any manager modification to the local 
	 parameters in an entry should initiate a renegotiation of the 
	 parameters."
    INDEX  { hEstBMParamIndex }
    ::= { hEstBMParamTable 1 }

HEstBMParamTableEntry ::= SEQUENCE
{
   hEstBMParamIndex         SnmpAdminString,
   hEstMRCBMValue           OCTET STRING,
   hEstRRBMValue            OCTET STRING,
   hEstRRTimer              Unsigned32,
   hEstRRBucketSize         OCTET STRING,
   hEstRRBucketRate         OCTET STRING,
   hEstBMParamRowStatus     RowStatus
}

hEstBMParamIndex OBJECT-TYPE
    SYNTAX     SnmpAdminString (SIZE(1..32))
    MAX-ACCESS not-accessible
    STATUS     current
    DESCRIPTION
        "(U//FOUO)  A unique index for a row entry in the hEstBMParamTable.
         Note, for IKEv2 CHILD_SAs, this column is populated internally and 
	 can not be read or configured."
    ::= { hEstBMParamTableEntry 1 }

hEstMRCBMValue OBJECT-TYPE
    SYNTAX     OCTET STRING (SIZE(4))
    UNITS      "bytes/second"
    MAX-ACCESS read-create
    STATUS     current
    DESCRIPTION
        "(U//FOUO) Represented in bytes per second, this indicates the maximum
         allowed transmission rate on the given Manual or IKEv2 CHILD_SA. For 
	 incoming SAs, this value represents the rate at which the local HAIPE 
	 will process packets on the SA. For outgoing SAs, this value represents
	 the rate at which the remote HAIPE will process packets on the SA. 
	 
	 (U//FOUO) For incoming IKEv2 CHILD_SAs, this value also represents the 
	 acknowledged value the local HAIPE sent in a Maximum Receive Claim 
	 [MRC]. For outgoing IKEv2 CHILD_SAs, this value also represents the 
	 acknowledged value the remote HAIPE sent in an MRC.  

         (U//FOUO) The value in this column is expressed as a 32-bit IEEE
         floating-point number."
    ::= { hEstBMParamTableEntry 2 }

hEstRRBMValue OBJECT-TYPE
    SYNTAX     OCTET STRING (SIZE(4))
    UNITS      "bytes/second"
    MAX-ACCESS read-create
    STATUS     current
    DESCRIPTION
        "(U//FOUO) Represented in bytes per second, this indicates the peak
         transmission rate or the amount of bandwidth reserved for a given IKEv2
         CHILD_SA. For incoming SAs, the value in this column represents the
         acknowledged 'Bandwidth Value' in the Reservation Request [RR] the
         remote HAIPE sent. It also signifies how much of the local HAIPE's
         bandwidth the peer has reserved. For outgoing SAs, it represents the
         acknowledged 'Bandwidth Value' in the RR the local HAIPE sent. It also
         signifies how much of the remote HAIPE's bandwidth the local HAIPE has
         reserved.
	 
	 (U//FOUO) This column is solely applicable to IKEv2 CHILD_SAs, and
	 must not exist for Manual SAs.

         (U//FOUO) The value in this column is expressed as a 32-bit IEEE
         floating-point number."
    ::= { hEstBMParamTableEntry 3 }

hEstRRTimer OBJECT-TYPE
    SYNTAX     Unsigned32
    UNITS      "seconds"
    MAX-ACCESS read-create
    STATUS     current
    DESCRIPTION
        "(U//FOUO) The length of time, in seconds, for which the resource
         reservation is requested. For incoming SAs, the value in this column
         represents the respective value the remote HAIPE sent in a Reservation
         Request [RR]. For outgoing SAs, the value in this column
         represents the respective value the local HAIPE sent in a Reservation
         Request [RR].
	 
	 (U//FOUO) This column is solely applicable to IKEv2 CHILD_SAs, and
	 must not exist for Manual SAs.	 

         (U//FOUO) Note that the largest Unsigned32 value, 4294967295,
         indicates that the lifetime of the RR is 'infinity'."
    ::= { hEstBMParamTableEntry 4 }

hEstRRBucketSize OBJECT-TYPE
    SYNTAX     OCTET STRING (SIZE(4))
    UNITS      "bytes"
    MAX-ACCESS read-create
    STATUS     current
    DESCRIPTION
        "(U//FOUO) A measure, in bytes, of the sender's Token Bucket.
         For incoming SAs, the value in this column represents the
         respective value the remote HAIPE sent in a Reservation Request [RR]
         For outgoing SAs, the value in this column represents the
         respective value the local HAIPE sent in a Reservation Request [RR].

	 (U//FOUO) This column is solely applicable to IKEv2 CHILD_SAs, and
	 must not exist for Manual SAs. 
	 
         (U//FOUO) The value in this column is expressed as a 32-bit IEEE
         floating-point number."
    ::= { hEstBMParamTableEntry 5 }

hEstRRBucketRate OBJECT-TYPE
    SYNTAX     OCTET STRING (SIZE(4))
    UNITS      "bytes/second"
    MAX-ACCESS read-create
    STATUS     current
    DESCRIPTION
        "(U//FOUO) The rate, in bytes per second, at which tokens are deposited
         in the bucket. For incoming SAs, the value in this column
         represents the respective value the remote HAIPE sent in a Reservation
         Request [RR]. For outgoing SAs, the value in this column
         represents the respective value the local HAIPE sent in a Reservation
         Request [RR].

	 (U//FOUO) This column is solely applicable to IKEv2 CHILD_SAs, and
	 must not exist for Manual SAs.	 
	 
         (U//FOUO) The value in this column is expressed as a 32-bit IEEE
         floating-point number."
    ::= { hEstBMParamTableEntry 6 }

hEstBMParamRowStatus OBJECT-TYPE
    SYNTAX     RowStatus
    MAX-ACCESS read-create
    STATUS     current
    DESCRIPTION
        "(U//FOUO) The status of the row, by which new entries may be created,
         or old entries deleted from this table.

         (U//FOUO) The following columns must include valid values before the
         row is set to 'createAndGo' or 'active': hEstMRCBMValue,
         hEstSARRBMValue, hEstSARRTimer, hEstSARRBucketSize and
         hEstSARRBucketRate. If values are not valid for the required columns,
         an inconsistentName error will be returned for this object.
	 
         (U//FOUO) If any column is set to an invalid or unsupported value
         (during row creation or any other time), a wrongValue error will be
         returned for that object.

         (U//FOUO) An active row may not be changed to an inconsistent state. If
         such an atttempt is made, an inconsistentValue error will be returned.
         In other words, any new values must be valid values for an active row.
         
         (U//FOUO) At a minimum, implementations must support createAndGo, 
	 active, and destroy management functions. Support for createAndWait,
         notInService, and notReady management functions is optional."
    ::= { hEstBMParamTableEntry 7 }

    
-- **********************************************************************
-- Bandwidth Management Notifications
-- **********************************************************************


END
