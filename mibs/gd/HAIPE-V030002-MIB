HAIPE-V030002-MIB DEFINITIONS ::= BEGIN
IMPORTS
    MODULE-IDENTITY                 FROM SNMPv2-SMI
    MODULE-COMPLIANCE, OBJECT-GROUP FROM SNMPv2-CONF
    haipeComplianceMIB              FROM HAIPE-COMPLIANCE-MIB
    usmAesCfb128Protocol, snmpUsmAesMIB
      FROM SNMP-USM-AES-MIB
    ipSystemStatsInOctets, ipIfStatsHCOutMcastPkts, ipv6RouterAdvertDefaultLifetime, ipIfStatsInTruncatedPkts, ipIfStatsRefreshRate, ipSystemStatsHCInMcastPkts, ipSystemStatsHCInOctets, ipv6IpForwarding, ipv6ScopeZoneIndexSiteLocal, ipIfStatsInBcastPkts, ipv6IpDefaultHopLimit, ipIfStatsHCOutMcastOctets, ipIfStatsOutTransmits, ipIfStatsInUnknownProtos, ipv6RouterAdvertManagedFlag, ipSystemStatsOutFragOKs, ipv4InterfaceEnableStatus, ipSystemStatsHCInForwDatagrams, ipv6ScopeZoneIndexA, ipSystemStatsOutFragFails, ipForwarding, ipv6InterfaceForwarding, ipv6InterfaceRetransmitTime, ipAddressIfIndex, ipSystemStatsHCInBcastPkts, ipIfStatsInDiscards, ipIfStatsOutFragOKs, ipIfStatsOutDiscards, ipIfStatsOutRequests, ipNetToPhysicalRowStatus, ipSystemStatsInReceives, ipv6ScopeZoneIndexLinkLocal, ipSystemStatsInForwDatagrams, ipIfStatsInNoRoutes, ipSystemStatsOutFragReqds, ipReasmTimeout, ipIfStatsReasmOKs, ipv6InterfaceReachableTime, ipv6RouterAdvertCurHopLimit, ipSystemStatsOutBcastPkts, ipv6RouterAdvertReachableTime, ipv4InterfaceRetransmitTime, ipSystemStatsHCOutMcastPkts, ipv6RouterAdvertRowStatus, ipv6RouterAdvertMaxInterval, ipSystemStatsOutTransmits, ipSystemStatsOutFragCreates, ipIfStatsReasmFails, ipv6InterfaceEnableStatus, ipSystemStatsOutMcastOctets, ipSystemStatsOutOctets, ipAddressStorageType, ipSystemStatsHCInReceives, ipAddressStatus, ipIfStatsOutMcastPkts, ipIfStatsReasmReqds, ipSystemStatsRefreshRate, ipIfStatsInMcastPkts, ipIfStatsOutFragCreates, ipSystemStatsOutRequests, ipSystemStatsHCOutForwDatagrams, ipSystemStatsHCInMcastOctets, ipSystemStatsOutMcastPkts, ipIfStatsInOctets, ipIfStatsOutFragFails, ipIfStatsOutBcastPkts, ipIfStatsOutOctets, ipNetToPhysicalState, ipIfStatsHCInMcastOctets, ipv6RouterAdvertSpinLock, ipv6ScopeZoneIndexC, ipAddressOrigin, ipSystemStatsInDiscards, ipSystemStatsInTruncatedPkts, ipv6ScopeZoneIndex7, ipIfStatsHCOutBcastPkts, ipIfStatsHCInOctets, ipIfStatsHCOutOctets, ipv6RouterAdvertLinkMTU, ipSystemStatsInMcastPkts, ipIfStatsOutForwDatagrams, ipv4InterfaceReasmMaxSize, ipIfStatsHCInDelivers, ipSystemStatsOutDiscards, ipSystemStatsHCOutRequests, ipSystemStatsInMcastOctets, ipv6ScopeZoneIndexAdminLocal, ipv6ScopeZoneIndex9, ipIfStatsHCInBcastPkts, ipv6ScopeZoneIndex6, ipIfStatsHCOutForwDatagrams, ipNetToPhysicalType, ipNetToPhysicalPhysAddress, ipSystemStatsReasmOKs, ipIfStatsTableLastChange, ipv6InterfaceTable, ipIfStatsHCInForwDatagrams, ipSystemStatsHCOutTransmits, ipSystemStatsHCOutOctets, ipv6InterfaceReasmMaxSize, ipv4InterfaceTable, ipSystemStatsHCOutBcastPkts, ipSystemStatsReasmReqds, ipNetToPhysicalLastUpdated, ipAddressSpinLock, ipAddressLastChanged, ipSystemStatsHCInDelivers, ipAddressRowStatus, ipAddressType, ipv6InterfaceIdentifier, ipSystemStatsInDelivers, ipIfStatsHCOutTransmits, ipv6RouterAdvertMinInterval, ipDefaultTTL, ipIfStatsHCInReceives, ipIfStatsInForwDatagrams, ipv6ScopeZoneIndex3, ipIfStatsDiscontinuityTime, ipIfStatsOutFragReqds, ipSystemStatsOutNoRoutes, ipSystemStatsInHdrErrors, ipv6RouterAdvertOtherConfigFlag, ipSystemStatsInUnknownProtos, ipIfStatsHCInMcastPkts, ipv6ScopeZoneIndexD, ipAddressPrefix, ipSystemStatsOutForwDatagrams, ipv6RouterAdvertRetransmitTime, ipv6RouterAdvertSendAdverts, ipSystemStatsHCOutMcastOctets, ipSystemStatsReasmFails, ipAddressCreated, ipIfStatsInDelivers, ipSystemStatsInBcastPkts, ipIfStatsOutMcastOctets, ipv6ScopeZoneIndexOrganizationLocal, ipIfStatsInMcastOctets, ipIfStatsHCOutRequests, ipv6ScopeZoneIndexB, ipIfStatsInAddrErrors, ipIfStatsInHdrErrors, ipSystemStatsDiscontinuityTime, ipIfStatsInReceives, ipSystemStatsInNoRoutes, ipSystemStatsInAddrErrors
      FROM IP-MIB
    hBatteryLevelPercentage, hFdsLoginName, hAudThrottleCfgRowStatus, hAudCfgNotifEnabled, hTFTPDesiredTimeoutInterval, hAudCfgThrottlingEnabled, hFirmwareDownloadAdminStatus, hAudNotificationLogWarning, hAudCfgLogThrottled, hGenericAuditNotification, hBatteryTable, hAudNotificationLogFull, hAudCfgNotifThrottleCfg, hNotificationLogPartialReset, hFirmwareDownloadOperStatus, hBatteryOK, hCurrentState, hAudCfgLogCount, hSecurityLevel, hTFTPMaximumFileTransferSize, hAudThrottleCfgInterval, hAudThrottleConfigTableCount, hAudThrottleCfgThreshold, hdvName, hAudCfgNotifCount, hAudCfgNotifThrottled, hNotificationLogFullBehavior, hBatteryNumber, hHMISpinLock, hNotificationLogCapacityPercentage, hFirmwareInstallSucceeded, hAudCfgNotifThrottleStatus, hSecurityAuthority, hFdsPassword, hBatteryLevelWarningPercentage, hNotificationLogReset, hFdsRowStatus, hFdsPriority, hFdsLastChanged, hAudCfgLogThrottleCfg, hAudThrottleConfigTableLastChanged, hAudThrottleCfgLastChanged, hFdsURI, hBatteryOperStatus, hAudNotificationLogOk, hDeviceVersionTableCount, hFirmwareDownloadServersTableLastChanged, haipeSanitizeDevice, hFdsSide, hSpinLock, hDeviceVersionTableLastChanged, hLastChanged, hAudThrottleCfgName, hTFTPDesiredBlockSize, hAudCfgLogThrottleStatus, hAudCfgRowStatus, hAuditConfigTableCount, hFirmwareDownloadServersTableCount, hFdErrorCode, hFirmwareDownloadSuccess, hAuditConfigTableLastChanged, hStationID, hNotificationLogWarningPercentage, hFirmwareInstallFailed, hdvVersion, hAudCfgID, haipeResetDevice, hBatteryLow, hFirmwareDownloadError, hFdErrorDetail, hBatteryChangeDate
      FROM HAIPE-MANAGEMENT-MIB
    snmpMPDStats, snmpMPDCompliance, snmpUnknownPDUHandlers, snmpMPDAdmin, snmpUnknownSecurityModels, snmpMPDMIBConformance, snmpMPDGroup, snmpMPDMIBGroups, snmpMPDMIBCompliances, snmpInvalidMsgs, snmpMPDMIB, snmpMPDMIBObjects
      FROM SNMP-MPD-MIB
    hrSystemUptime, hrSystemDate
      FROM HOST-RESOURCES-MIB
    ifOperStatus, ifHCOutUcastPkts, ifInDiscards, ifHCInMulticastPkts, ifAdminStatus, ifOutMulticastPkts, ifOutErrors, ifIndex, ifOutNUcastPkts, ifHCOutOctets, ifHCInUcastPkts, ifInBroadcastPkts, ifOutDiscards, ifOutQLen, linkUp, ifCounterDiscontinuityTime, ifSpecific, ifInOctets, ifAlias, ifInMulticastPkts, ifHCOutMulticastPkts, ifOutUcastPkts, ifHCInOctets, ifType, ifInUnknownProtos, ifMtu, ifPhysAddress, ifDescr, ifConnectorPresent, ifInUcastPkts, ifLastChange, ifInNUcastPkts, ifLinkUpDownTrapEnable, ifHCOutBroadcastPkts, ifInErrors, linkDown, ifHighSpeed, ifSpeed, ifOutOctets, ifNumber, ifName, ifPromiscuousMode, ifOutBroadcastPkts, ifHCInBroadcastPkts
      FROM IF-MIB
    udpHCInDatagrams, udpInErrors, udpHCOutDatagrams, udpNoPorts, udpEndpointProcess
      FROM UDP-MIB
    snmpInPkts, sysORID, sysORLastChange, snmpInBadCommunityNames, sysServices, sysName, warmStart, snmpTrapOID, sysLocation, snmpInASNParseErrs, sysDescr, authenticationFailure, snmpTrapEnterprise, sysUpTime, snmpEnableAuthenTraps, snmpSetSerialNo, sysORUpTime, snmpInBadCommunityUses, coldStart, snmpSilentDrops, snmpInBadVersions, sysObjectID, sysORDescr, snmpProxyDrops, sysContact
      FROM SNMPv2-MIB
    vacmSecurityToGroupStorageType, vacmMIBGroups, vacmMIBViews, vacmAccessWriteViewName, vacmAccessNotifyViewName, vacmAccessStorageType, vacmViewTreeFamilyType, vacmAccessStatus, vacmViewTreeFamilyMask, vacmAccessReadViewName, vacmMIBConformance, vacmViewTreeFamilyStorageType, snmpVacmMIB, vacmBasicGroup, vacmMIBObjects, vacmGroupName, vacmAccessContextMatch, vacmViewTreeFamilyStatus, vacmViewSpinLock, vacmMIBCompliance, vacmContextName, vacmMIBCompliances, vacmSecurityToGroupStatus
      FROM SNMP-VIEW-BASED-ACM-MIB
    tcpConnectionState, tcpAttemptFails, tcpInSegs, tcpInErrs, tcpOutSegs, tcpMaxConn, tcpCurrEstab, tcpEstabResets, tcpRtoMax, tcpActiveOpens, tcpHCInSegs, tcpConnectionProcess, tcpPassiveOpens, tcpHCOutSegs, tcpOutRsts, tcpRtoMin, tcpRtoAlgorithm, tcpListenerProcess, tcpRetransSegs
      FROM TCP-MIB
    snmpFrameworkMIB, snmpFrameworkMIBObjects, snmpEngineID, snmpPrivProtocols, snmpEngineGroup, snmpFrameworkMIBCompliances, snmpFrameworkMIBConformance, snmpAuthProtocols, snmpFrameworkMIBGroups, snmpFrameworkMIBCompliance, snmpEngineMaxMessageSize, snmpEngine, snmpFrameworkAdmin, snmpEngineBoots, snmpEngineTime
      FROM SNMP-FRAMEWORK-MIB
    snmpTargetGroups, snmpTargetConformance, snmpTargetAddrTAddress, snmpTargetResponseGroup, snmpTargetObjects, snmpTargetParamsSecurityLevel, snmpTargetBasicGroup, snmpUnavailableContexts, snmpTargetAddrTagList, snmpTargetAddrRetryCount, snmpTargetCommandResponderGroup, snmpTargetCompliances, snmpUnknownContexts, snmpTargetSpinLock, snmpTargetAddrStorageType, snmpTargetMIB, snmpTargetCommandResponderCompliance, snmpTargetParamsMPModel, snmpTargetAddrTimeout, snmpTargetAddrParams, snmpTargetParamsRowStatus, snmpTargetParamsSecurityName, snmpTargetParamsSecurityModel, snmpTargetAddrTDomain, snmpTargetParamsStorageType, snmpTargetAddrRowStatus
      FROM SNMP-TARGET-MIB
    mgmdRouterInterfaceQuerier, mgmdRouterInterfaceVersion, mgmdHostCacheUpTime, mgmdRouterSrcListHostAddress, mgmdHostInterfaceStatus, mgmdHostInterfaceVersion2QuerierTimer, mgmdRouterInterfaceQuerierExpiryTime, mgmdRouterInterfaceLastMembQueryIntvl, mgmdHostSrcListHostAddress, mgmdHostInterfaceVersion3Robustness, mgmdHostInterfaceQuerier, mgmdRouterCacheExpiryTime, mgmdRouterCacheVersion2HostTimer, mgmdRouterInterfaceGroups, mgmdRouterInterfaceQuerierUpTime, mgmdHostCacheSourceFilterMode, mgmdRouterInterfaceRobustness, mgmdRouterCacheVersion1HostTimer, mgmdRouterInterfaceStartupQueryCount, mgmdRouterCacheUpTime, mgmdRouterInterfaceStartupQueryInterval, mgmdRouterInterfaceJoins, mgmdRouterInterfaceQueryMaxResponseTime, mgmdRouterInterfaceStatus, mgmdHostCacheLastReporter, mgmdRouterInterfaceLastMembQueryCount, mgmdRouterCacheSourceFilterMode, mgmdRouterInterfaceWrongVersionQueries, mgmdRouterSrcListExpire, mgmdRouterCacheExcludeModeExpiryTimer, mgmdHostInterfaceVersion1QuerierTimer, mgmdRouterCacheLastReporter, mgmdRouterInterfaceQueryInterval, mgmdHostInterfaceVersion, mgmdRouterInterfaceProxyIfIndex
      FROM MGMD-STD-MIB
    hMLDMode, hIfv6BaseReachableTime, hIfv4OutputPacketFixedSize, hiaaType, hIfAddrAssignmentTable, hv6APAddressPrefixOrigin, hIfv6NextHeaderSkipList, hIfv4HaipeTableCount, hIfv4OutputPacketPadding, hIfv6OutputPacketPadding, hNetDuplicateAddressDetected, hNetDuplicateAddressCheck, hv6APAdvertisePrefix, hIfv4TTL, hIfv4LowPMTUThreshold, hIfv6HaipeTableLastChanged, hIfv6InterfaceIdentifier, hIfv6HopLimit, hv6AddressPrefixTable, hIfv6MTU, hv6APAddressPrefixAdvValidLifetime, hIfv6RetransmitTime, hIfv6DupAddressRecoveryID, hiaaPrefixLen, hIfv6OutputPacketFixedSize, hIfv6LowPMTUThreshold, hIfv4LastChanged, hNetDuplicateAddressIfDown, hIGMPMode, hv6APTableLastChanged, hv6APAddressPrefixAdvPreferredLifetime, hIfv4MTU, hIfv6TrymeSA, hv6APAddressPrefixOnLinkFlag, hIfv4HaipeTableLastChanged, hIfv6AddressAutoConfig, hIfv6RouterSolicitation, hIfv4Side, hNetSourceAddress, hiaaAddress, hIfv6Side, hIfv6HaipeTableCount, hIfv6DupAddressDetection, hNetSourceAddressType, hiaaInterface, hIfv6PMTUResetPeriod, hIfv6DiscardUnauthRed, hv6APAddressPrefixAutonomousFlag, hIfv6UseDepAddress, hIfv4PMTUResetPeriod, hiaaRowStatus, hIfv6LastChanged, hIfv6ReachableTime, hv6APRowStatus
      FROM HAIPE-NETWORKING-MIB
    inetCidrRouteType, inetCidrRouteProto, inetCidrRouteIfIndex, inetCidrRouteMetric4, inetCidrRouteDiscards, inetCidrRouteMetric3, inetCidrRouteNumber, inetCidrRouteAge, inetCidrRouteMetric2, inetCidrRouteMetric1, inetCidrRouteStatus, inetCidrRouteMetric5, inetCidrRouteNextHopAS
      FROM IP-FORWARD-MIB
    hrcStatus, hTopologyTableCount, hDiscRegistrationTableLastChanged, hDiscoverySolicitationRetry, hTopologyDestHaipePTAddr, hDiscSolRcvSide, hTopologyMethod, hRIPConfTableLastChanged, hrcSrcAddress, hDiscSearchStartAddress, hTopologyTableLastChanged, hDiscSolRcvAddressType, hDiscSolReceptionTableCount, hDiscoveryRegistrationRetry, hDiscRegPriority, hDiscDelivPTAddress, hDiscDelivStatus, hDiscoveryProbeRetry, hDiscSearchEndAddress, hTopologyDestAdminCost, hDiscDelivType, hrcAuthType, hDiscRegStatus, hDiscoveryProbeTimeout, hDiscoveryAdvertiseAdminCost, hDiscoveryMessageConfig, hDiscoveryRegistrationTimeout, hrcReceive, hDiscRegPTAddressType, hDiscDelivPriority, hTopologyDestHaipeCTAddr, hrcAddr, hTopologyDestHostAddrType, hTopologyLifetime, hTopologyDestHaipePTAddrType, hDiscDelivPTPort, hDiscSolRcvType, hDiscRegPTPort, hDiscRegistrationDefaultLifetime, hDiscSolRcvStatus, hDiscSearchAddressType, hDiscSolRcvAddress, hrcDefaultMetric, hrcAuthKey, hDiscoveryEnabled, hTopologyDestHostPTPfxLen, hTopologyDestHost, hDiscSolRcvPort, hrcFilterDefaultRoutes, hrcAdvertising, hrcAddrType, hDiscoveryDeliveryTableLastChanged, hDiscDelivPTAddressType, hDiscSolReceptionTableLastChanged, hrcSend, hDiscoveryDeliveryTableCount, hDiscoverySolicitationTimeout, hRIPConfTableCount, hDiscRegistrationTableCount, hTopologyDestHaipeCTAddrType, hDiscRegPTAddress, hTopologyRowStatus
      FROM HAIPE-NETWORKING-DISCOVERY-MIB
    usmUserPublic, usmStatsDecryptionErrors, usmUserAuthProtocol, usmUserCloneFrom, usmUserSpinLock, usmUserStatus, usmUserPrivKeyChange, usmStatsUnsupportedSecLevels, usmNoAuthProtocol, usmStatsNotInTimeWindows, usmMIBBasicGroup, usmStats, usmUserPrivProtocol, snmpUsmMIB, usmMIBObjects, usmUserStorageType, usmUserOwnPrivKeyChange, usmMIBCompliance, usmMIBConformance, usmDESPrivProtocol, usmHMACSHAAuthProtocol, usmStatsUnknownEngineIDs, usmHMACMD5AuthProtocol, usmUser, usmStatsUnknownUserNames, usmMIBCompliances, usmUserSecurityName, usmStatsWrongDigests, usmNoPrivProtocol, usmUserAuthKeyChange, usmUserOwnAuthKeyChange, usmMIBGroups
      FROM SNMP-USER-BASED-SM-MIB
    nlmLogVariableValueType, nlmStatsGlobalNotificationsBumped, nlmLogEngineTAddress, nlmLogVariableOpaqueVal, nlmLogVariableOctetStringVal, nlmLogEngineTDomain, nlmStatsLogNotificationsLogged, nlmLogVariableIpAddressVal, nlmConfigGlobalEntryLimit, nlmLogContextEngineID, nlmLogVariableUnsigned32Val, nlmLogVariableID, nlmStatsGlobalNotificationsLogged, nlmLogVariableInteger32Val, nlmLogContextName, nlmLogVariableTimeTicksVal, nlmLogVariableCounter64Val, nlmStatsLogNotificationsBumped, nlmLogTime, nlmLogDateAndTime, nlmLogVariableOidVal, nlmLogEngineID, nlmLogVariableCounter32Val, nlmLogNotificationID
      FROM NOTIFICATION-LOG-MIB
    hPPKEKTableMaxCount, hIPhFFSATransformLastChanged, hUniversalCKLVersion, hTPSAIntegrityAlgorithm, hPPKEffectiveDate, hTPSAEndTime, hIPhSelectorNextHeaderOpt1End, hTPSARemoteCAName, hTPSALocalCAName, hFFExpiration, hIPhFFSATransformKeyUpdateMethod, hPPKChainRowStatus, hTPSAPTAddressType, hTPiphFFSAKey, hIPhSelectorTableLastChanged, hIPhFFSATransformAuthenticationAlgorithm, hIPhFFSATransformsTableCount, hPPKKeyExpirationWarningCount, hIPhSelectorSrcAddressEnd, hTPSAConnectionType, hTPSASelectorNextHeaderOpt2End, hIPhFFSADFBit, hIPhFFSATransformHashAlgorithm, hPPKChainPPK, hTPSADSCPValue, hTPTransportMapTableLastChanged, hIPhSelectorNextHeaderStart, hFFMaterialType, hPPKRegister, hTPSAProcessFlowlabel, hFFKMID, hPPKAuthority, hTPSARemotePTAddress, hIPhSelectorSrcAddressBegin, hIPhSelectorNextHeaderEnd, hIPhFFSATransformKeyUpdateFrequency, hFFZeroizeKey, hFFNextVector, hPPKEKKeyType, hPreplacedKeyTableLastChanged, hIPhRuleLastChanged, hIPhFFSATransformCryptoBlockSize, haipeZeroizeAllKeys, hPPKSecurityLevel, hTPSACryptoBlockSize, hTPSACreationReason, hTPSADirection, hIPhSelectorIPVersion, hTPiDestinationAddress, hTPSAFlowLabel, hFireflyTableLastChanged, hTPiphFFSA, hIPhFFSATableCount, hTPSAHCOctets, hTPSAPMTU, hIPhFFSAFFUniversal, hPPKZeroizeKey, hPPKChainID, hPPKChainOrder, hTPiDestinationAddressType, hTPSAHCUcastPkts, hFFPartitionCode, hTPSASelectorNextHeaderOpt1Start, hLocalCKListRowStatus, hTPnSACreated, hTPTransMapDestPTAddress, hTPnSADestroyed, hIPhFFSATransformsTableLastChanged, hUniversalCKLDate, hIPhFFSATransformEncryptAlgorithm, hIPhFFSAProcessFlowlabel, hIPhRuleActionIndex, hPPKTrafficTable, hTPAddressMapTable, hPPKLastChanged, hIPhFFSAConnectionType, hFFASCIIID, hTPiSADestroyedReason, hTPSAHCBrdcastPkts, hFFAlgorithmPrivilege, hLocalCKListReason, hTPSAAddressSrcOrDest, hTPSARowStatus, hIPhFFSAFFUniversalEdition, hIPhFFSADSCP, hLocalCKListKMIDEnd, hIPhFFSAECN, hFFKeyExpirationWarning, hFFAuthority, hTPSASelectorNextHeaderStart, hUniversalTable, hIPhSelectorNextHeaderOpt1Start, hIPhFFSATransformESN, hTPTransportMapTableCount, hIPhFFSAFlowLabelValue, hPPKUsageType, hIPhFFSADSCPValue, hTPSADecrementTTL, hTPTransMapRowStatus, hIPhFFSARetryICMPCount, hTPSAAddressRowStatus, hTPSARemoteCredentialType, hIPhFFSACTOutAddressType, hIPhFFSATransformICV, hTPAddMapCTAddress, hTPSAesn, hIPhFFSATransformsName, hTPSAHCMcastPkts, hTPSADSCP, hTPSAspi, hPPKTrafficIntegrityAlgorithm, hIPhSelectorDSCP, hFFUniversalEdition, hLocalCKListKMIDBegin, hIPhRuleTableLastChanged, hIPhFFSALastChanged, hTPSASelectorNextHeaderOpt2Start, hPPKChainEffectiveDate, hTPSALocalPTAddress, hTPiphFFSATransforms, hIPhRuleAdminStatus, hTPAddMapRowStatus, hTPSAECN, hPPKChainIntegrityAlgorithm, hTPSAAddressSelectorTable, hIPhSelectorNextHeaderOpt2End, hIPhFFSADecrementTTL, hTPSADFBit, hTPSARetryICMPCount, hIPhFFSAPHRDRate, hIPhFFSARowStatus, hPreplacedKeyTableCapacity, hFFUniversalID, hIPhFFSATransformRowStatus, hTPSARemoteCTAddress, hFFSecurityLevels, hTPSALocalCredentialType, hTPSAFlowLabelValue, hTPSAEncryptAlgorithm, hIPhSelectorRowStatus, hTPTransMapSourcePTAddress, hIPhFFSAPDUNEnabled, hTPSALocalCTAddress, hIPhFFSATransformIntegrityAlgorithm, hTPSAPDUNEnabled, hIPhFFSADIndexType, hTPAddMapLastChanged, hFFEnhancedFFTag, hTPSASelectorNextHeaderEnd, hPPKTrafficTableMaxCount, hTPSATableCount, hIPhFFSATableLastChanged, hTPiSPI, hPreplacedKeyTableCount, hIPhSelectorDstAddressEnd, hTPSASelectorType, hPPKEKUniversalID, hIPhRuleAction, hLocalCKListUniversal, hTPSALocalCredentialID, hIPhSelectorNextHeaderOpt2Start, hIPhRuleRowStatus, hTPSAStartTime, hLocalCompromisedKeyListTable, hFFLastChanged, hIPhSelectorDstAddressBegin, hFFIsTestKey, hTPTransMapLastChanged, hTPSADIndexType, hTPSASelectorNextHeaderOpt1End, hTPSATableLastChanged, hIPhFFSAFF, hPPKTrafficEncryptAlgorithm, hTPSARemoteCredentialID, hIPhFFSAFlowLabel, hPPKKeyExpirationWarning, hTPSAPPK, hIPhFFSACTOutAddress, hIPhRuleSelectorName, hIPhSelectorOpaques, hIPhFFSAPopulateFromPacket, hTPSASecurityPayloadType, hIPhRuleName, hIPhRuleTableCount, hLocalCKListUniversalEdition, hFireflyTableCount, hTPSAAddressEnd, hTPSAAddressType, hUniversalID, hPPKEKTable, hIPhSelectorLastChanged, hTPSAPHRDRate, hLocalCKListDate, hTPSAAddressStart, hTPSAICV, hPPKChainTableLastChanged, hIPhSelectorType, hTPiphSATransforms, hPPKChainTableCount, hPPKChainEncryptionAlgorithm, hIPhSelectorTableCount
      FROM HAIPE-TRAFFIC-PROTECTION-MIB
    snmpNotifyStorageType, snmpNotificationMIB, snmpNotifyFullCompliance, snmpNotifyBasicFiltersCompliance, snmpNotifyType, snmpNotifyObjects, snmpNotifyTag, snmpNotifyFilterRowStatus, snmpNotifyFilterGroup, snmpNotifyFilterType, snmpNotifyBasicCompliance, snmpNotifyFilterProfileName, snmpNotifyGroups, snmpNotifyCompliances, snmpNotifyRowStatus, snmpNotifyFilterProfileRowStatus, snmpNotifyFilterStorageType, snmpNotifyGroup, snmpNotifyFilterProfileStorType, snmpNotifyFilterMask, snmpNotifyConformance
      FROM SNMP-NOTIFICATION-MIB
;

haipeV030002ComplianceMIB MODULE-IDENTITY
    LAST-UPDATED "200701222239Z"
    ORGANIZATION "HAIPE PO"
    CONTACT-INFO
         "(U//FOUO) Not Available"
    DESCRIPTION
        "(U//FOUO) This MIB defines compliance statements which
        define the levels of conformance required by the various HAIPE
        Version 3.0.2 IS documents.

        (U//FOUO) This MIB is not entirely conformant to SMIv2 parsing
        rules. Specifically, object groups are only allowed to
        reference objects defined in the local MIB, and in this file
        we're importing a large number of objects from other MIBs
        rather than importing their particular object groups."
    ::= { haipeComplianceMIB 3 0 2 }

haipeV030002Conformance OBJECT IDENTIFIER ::= { haipeV030002ComplianceMIB 1 }
haipeV030002Groups      OBJECT IDENTIFIER ::= { haipeV030002ComplianceMIB 2 }

--
-- Objects referenced by the Granular Selector Capability IS
--
hGranularSelectorCapabilityGroup OBJECT-GROUP
    OBJECTS {
                hIfv6NextHeaderSkipList,
                hIPhSelectorType,
                hIPhSelectorOpaques,
                hIPhSelectorIPVersion,
                hIPhSelectorSrcAddressBegin,
                hIPhSelectorSrcAddressEnd,
                hIPhSelectorDstAddressBegin,
                hIPhSelectorDstAddressEnd,
                hIPhSelectorNextHeaderStart,
                hIPhSelectorNextHeaderEnd,
                hIPhSelectorNextHeaderOpt1Start,
                hIPhSelectorNextHeaderOpt1End,
                hIPhSelectorNextHeaderOpt2Start,
                hIPhSelectorNextHeaderOpt2End,
                hIPhSelectorDSCP,
                hTPSASelectorType
            }
    STATUS    current
    DESCRIPTION
        "(U//FOUO) Objects for the 'Granular Selector Capability' document"
    ::= { haipeV030002Groups 1 }

--
-- Conformance levels required by the Granular Selector Capability IS
--
hGranularSelectorCapabilityCompliance MODULE-COMPLIANCE
    STATUS    current
    DESCRIPTION
        "(U//FOUO) Compliance levels for objects required by the
          'Granular Selector Capability' document"
    MODULE -- this module
    MANDATORY-GROUPS { hGranularSelectorCapabilityGroup }

    OBJECT		hIPhSelectorNextHeaderOpt2Start
    MIN-ACCESS	read-write
    DESCRIPTION
        "(U//FOUO) Implementation of this object can be as low
         as read-write depending on which
         IS Objective or MIB desired requirements are
         not being met by the implementation."

    OBJECT		hIPhSelectorNextHeaderStart
    MIN-ACCESS	read-write
    DESCRIPTION
        "(U//FOUO) Implementation of this object can be as low
         as read-write depending on which
         IS Objective or MIB desired requirements are
         not being met by the implementation."

    OBJECT		hIfv6NextHeaderSkipList
    MIN-ACCESS	read-write
    DESCRIPTION
        "(U//FOUO) Implementation of this object can be as low
         as read-write depending on which
         IS Objective or MIB desired requirements are
         not being met by the implementation."

    OBJECT		hIPhSelectorDstAddressBegin
    MIN-ACCESS	read-write
    DESCRIPTION
        "(U//FOUO) Implementation of this object can be as low
         as read-write depending on which
         IS Objective or MIB desired requirements are
         not being met by the implementation."

    OBJECT		hIPhSelectorSrcAddressBegin
    MIN-ACCESS	read-write
    DESCRIPTION
        "(U//FOUO) Implementation of this object can be as low
         as read-write depending on which
         IS Objective or MIB desired requirements are
         not being met by the implementation."

    OBJECT		hIPhSelectorNextHeaderEnd
    MIN-ACCESS	read-write
    DESCRIPTION
        "(U//FOUO) Implementation of this object can be as low
         as read-write depending on which
         IS Objective or MIB desired requirements are
         not being met by the implementation."

    OBJECT		hIPhSelectorDSCP
    MIN-ACCESS	not-accessible
    DESCRIPTION
        "(U//FOUO) Implementation of this object can be as low
         as not-accessible depending on which
         IS Objective or MIB desired requirements are
         not being met by the implementation."

    OBJECT		hIPhSelectorNextHeaderOpt1End
    MIN-ACCESS	read-write
    DESCRIPTION
        "(U//FOUO) Implementation of this object can be as low
         as read-write depending on which
         IS Objective or MIB desired requirements are
         not being met by the implementation."

    OBJECT		hIPhSelectorNextHeaderOpt1Start
    MIN-ACCESS	read-write
    DESCRIPTION
        "(U//FOUO) Implementation of this object can be as low
         as read-write depending on which
         IS Objective or MIB desired requirements are
         not being met by the implementation."

    OBJECT		hIPhSelectorNextHeaderOpt2End
    MIN-ACCESS	read-write
    DESCRIPTION
        "(U//FOUO) Implementation of this object can be as low
         as read-write depending on which
         IS Objective or MIB desired requirements are
         not being met by the implementation."

    OBJECT		hIPhSelectorDstAddressEnd
    MIN-ACCESS	read-write
    DESCRIPTION
        "(U//FOUO) Implementation of this object can be as low
         as read-write depending on which
         IS Objective or MIB desired requirements are
         not being met by the implementation."

    OBJECT		hIPhSelectorType
    MIN-ACCESS	read-write
    DESCRIPTION
        "(U//FOUO) Implementation of this object can be as low
         as read-write depending on which
         IS Objective or MIB desired requirements are
         not being met by the implementation."

    OBJECT		hIPhSelectorIPVersion
    MIN-ACCESS	read-write
    DESCRIPTION
        "(U//FOUO) Implementation of this object can be as low
         as read-write depending on which
         IS Objective or MIB desired requirements are
         not being met by the implementation."

    OBJECT		hIPhSelectorOpaques
    MIN-ACCESS	read-write
    DESCRIPTION
        "(U//FOUO) Implementation of this object can be as low
         as read-write depending on which
         IS Objective or MIB desired requirements are
         not being met by the implementation."

    OBJECT		hTPSASelectorType
    MIN-ACCESS	read-write
    DESCRIPTION
        "(U//FOUO) Implementation of this object can be as low
         as read-write depending on which
         IS Objective or MIB desired requirements are
         not being met by the implementation."

    OBJECT		hIPhSelectorSrcAddressEnd
    MIN-ACCESS	read-write
    DESCRIPTION
        "(U//FOUO) Implementation of this object can be as low
         as read-write depending on which
         IS Objective or MIB desired requirements are
         not being met by the implementation."
::= { haipeV030002Conformance 1 }

--
-- Objects referenced by the Networking IS
--
hNetworkingGroup OBJECT-GROUP
    OBJECTS {
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hIfv4LowPMTUThreshold,
                hIfv4PMTUResetPeriod,
                hIfv4MTU,
                hIfv6Side,
                hIfv6AddressAutoConfig,
                hIfv6DupAddressDetection,
                hIfv6DupAddressRecoveryID,
                hIfv6UseDepAddress,
                hIfv6RouterSolicitation,
                hIfv6DiscardUnauthRed,
                hIfv6TrymeSA,
                hIfv6LowPMTUThreshold,
                hIfv6PMTUResetPeriod,
                hIfv6LastChanged,
                hIfv6MTU,
                hIfv6HopLimit,
                hIfv6BaseReachableTime,
                hIfv6ReachableTime,
                hIfv6RetransmitTime,
                hIfv6NextHeaderSkipList,
                hIfv6InterfaceIdentifier,
--                hv6AddressPrefixTable,
--                hv6AddressPrefixTable,
                hv6APAddressPrefixOrigin,
                hv6APAddressPrefixOnLinkFlag,
                hv6APAddressPrefixAutonomousFlag,
                hv6APAddressPrefixAdvPreferredLifetime,
                hv6APAddressPrefixAdvValidLifetime,
                hv6APAdvertisePrefix,
                hv6APRowStatus,
                hv6APTableLastChanged,
--                hIfAddrAssignmentTable,
--                hIfAddrAssignmentTable,
                hiaaInterface,
                hiaaType,
                hiaaAddress,
                hiaaPrefixLen,
                hiaaRowStatus,
                hIGMPMode,
                hMLDMode,
--                hNetDuplicateAddressCheck,
--                hNetDuplicateAddressDetected,
--                hNetDuplicateAddressIfDown,
                hNetSourceAddressType,
                hNetSourceAddress,
                hIPhRuleName,
                hIPhRuleSelectorName,
                hIPhRuleAction,
                hIPhRuleActionIndex,
                hIPhRuleAdminStatus,
                hIPhRuleLastChanged,
                hIPhRuleRowStatus,
                hIPhSelectorTableCount,
                hIPhSelectorTableLastChanged,
                hIPhSelectorType,
                hIPhSelectorIPVersion,
                hIPhSelectorSrcAddressBegin,
                hIPhSelectorSrcAddressEnd,
                hIPhSelectorDstAddressBegin,
                hIPhSelectorDstAddressEnd,
                hIPhSelectorLastChanged,
                hIPhSelectorRowStatus,
--                hTPAddressMapTable,
--                hTPAddressMapTable,
                hTPAddMapCTAddress,
                hTPAddMapLastChanged,
                hTPAddMapRowStatus,
                ifNumber,
                ifIndex,
                ifDescr,
                ifType,
                ifMtu,
                ifSpeed,
                ifPhysAddress,
                ifAdminStatus,
                ifOperStatus,
                ifLastChange,
                ifInOctets,
                ifInUcastPkts,
                ifInNUcastPkts,
                ifInDiscards,
                ifInErrors,
                ifInUnknownProtos,
                ifOutOctets,
                ifOutUcastPkts,
                ifOutNUcastPkts,
                ifOutDiscards,
                ifOutErrors,
                ifOutQLen,
                ifSpecific,
                ifIndex,
                ifName,
                ifInMulticastPkts,
                ifInBroadcastPkts,
                ifOutMulticastPkts,
                ifOutBroadcastPkts,
                ifHCInOctets,
                ifHCInUcastPkts,
                ifHCInMulticastPkts,
                ifHCInBroadcastPkts,
                ifHCOutOctets,
                ifHCOutUcastPkts,
                ifHCOutMulticastPkts,
                ifHCOutBroadcastPkts,
                ifLinkUpDownTrapEnable,
                ifHighSpeed,
                ifPromiscuousMode,
                ifConnectorPresent,
                ifAlias,
                ifCounterDiscontinuityTime,
                ifIndex,
                ifIndex,
--                ipv6InterfaceTable,
                ipv6InterfaceReasmMaxSize,
                ipv6InterfaceIdentifier,
                ipv6InterfaceEnableStatus,
                ipv6InterfaceReachableTime,
                ipv6InterfaceRetransmitTime,
                ipv6InterfaceForwarding,
                ipAddressIfIndex,
                ipAddressType,
                ipAddressPrefix,
                ipAddressOrigin,
                ipAddressStatus,
                ipAddressCreated,
                ipAddressLastChanged,
                ipAddressRowStatus,
                ipAddressStorageType,
                ipv6ScopeZoneIndexLinkLocal,
                ipv6ScopeZoneIndex3,
                ipv6ScopeZoneIndexAdminLocal,
                ipv6ScopeZoneIndexSiteLocal,
                ipv6ScopeZoneIndex6,
                ipv6ScopeZoneIndex7,
                ipv6ScopeZoneIndexOrganizationLocal,
                ipv6ScopeZoneIndex9,
                ipv6ScopeZoneIndexA,
                ipv6ScopeZoneIndexB,
                ipv6ScopeZoneIndexC,
                ipv6ScopeZoneIndexD,
                ipv6RouterAdvertSpinLock,
                ipv6RouterAdvertSendAdverts,
                ipv6RouterAdvertMaxInterval,
                ipv6RouterAdvertMinInterval,
                ipv6RouterAdvertManagedFlag,
                ipv6RouterAdvertOtherConfigFlag,
                ipv6RouterAdvertLinkMTU,
                ipv6RouterAdvertReachableTime,
                ipv6RouterAdvertRetransmitTime,
                ipv6RouterAdvertCurHopLimit,
                ipv6RouterAdvertDefaultLifetime,
                ipv6RouterAdvertRowStatus
            }
    STATUS    current
    DESCRIPTION
        "(U//FOUO) Objects for the 'Networking' document"
    ::= { haipeV030002Groups 2 }

--
-- Conformance levels required by the Networking IS
--
hNetworkingCompliance MODULE-COMPLIANCE
    STATUS    current
    DESCRIPTION
        "(U//FOUO) Compliance levels for objects required by the
          'Networking' document"
    MODULE -- this module
    MANDATORY-GROUPS { hNetworkingGroup }

    OBJECT		hMLDMode
    MIN-ACCESS	read-write
    DESCRIPTION
        "(U//FOUO) Implementation of this object can be as low
         as read-write depending on which
         IS Objective or MIB desired requirements are
         not being met by the implementation."

    OBJECT		ifInDiscards
    MIN-ACCESS	not-accessible
    DESCRIPTION
        "(U//FOUO) Implementation of this object can be as low
         as not-accessible depending on which
         IS Objective or MIB desired requirements are
         not being met by the implementation."

    OBJECT		hv6APAddressPrefixOrigin
    MIN-ACCESS	read-write
    DESCRIPTION
        "(U//FOUO) Implementation of this object can be as low
         as read-write depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		ifOutNUcastPkts
    MIN-ACCESS	not-accessible
    DESCRIPTION
        "(U//FOUO) Implementation of this object can be as low
         as not-accessible depending on which
         IS Objective or MIB desired requirements are
         not being met by the implementation."

    OBJECT		ipv6RouterAdvertDefaultLifetime
    MIN-ACCESS	read-write
    DESCRIPTION
        "(U//FOUO) Implementation of this object can be as low
         as read-write depending on which
         IS Objective or MIB desired requirements are
         not being met by the implementation."

--    OBJECT		hNetDuplicateAddressCheck
--    MIN-ACCESS	not-accessible
--    DESCRIPTION
--        "(U//FOUO) Implementation of this object can be as low
--         as not-accessible depending on which
--         IS Objective or MIB desired requirements are
--         not being met by the implementation."

    OBJECT		ipv6ScopeZoneIndexSiteLocal
    MIN-ACCESS	read-only
    DESCRIPTION
        "(U//FOUO) Implementation of this object can be as low
         as read-only depending on which
         IS Objective or MIB desired requirements are
         not being met by the implementation."

    OBJECT		ifHCOutOctets
    MIN-ACCESS	read-only
    DESCRIPTION
        "(U//FOUO) Implementation of this object can be as low
         as read-only depending on which
         IS Objective or MIB desired requirements are
         not being met by the implementation."

    OBJECT		ifOutDiscards
    MIN-ACCESS	not-accessible
    DESCRIPTION
        "(U//FOUO) Implementation of this object can be as low
         as not-accessible depending on which
         IS Objective or MIB desired requirements are
         not being met by the implementation."

    OBJECT		hIPhSelectorTableLastChanged
    MIN-ACCESS	not-accessible
    DESCRIPTION
        "(U//FOUO) Implementation of this object can be as low
         as not-accessible depending on which
         IS Objective or MIB desired requirements are
         not being met by the implementation."

    OBJECT		hIfv4LowPMTUThreshold
    MIN-ACCESS	not-accessible
    DESCRIPTION
        "(U//FOUO) Implementation of this object can be as low
         as not-accessible depending on which
         IS Objective or MIB desired requirements are
         not being met by the implementation."

    OBJECT		ifOutQLen
    MIN-ACCESS	not-accessible
    DESCRIPTION
        "(U//FOUO) Implementation of this object can be as low
         as not-accessible depending on which
         IS Objective or MIB desired requirements are
         not being met by the implementation."

    OBJECT		hIfv6InterfaceIdentifier
    MIN-ACCESS	read-write
    DESCRIPTION
        "(U//FOUO) Implementation of this object can be as low
         as read-write depending on which
         IS Objective or MIB desired requirements are
         not being met by the implementation."

    OBJECT		ifSpecific
    MIN-ACCESS	not-accessible
    DESCRIPTION
        "(U//FOUO) Implementation of this object can be as low
         as not-accessible depending on which
         IS Objective or MIB desired requirements are
         not being met by the implementation."

    OBJECT		ifInOctets
    MIN-ACCESS	not-accessible
    DESCRIPTION
        "(U//FOUO) Implementation of this object can be as low
         as not-accessible depending on which
         IS Objective or MIB desired requirements are
         not being met by the implementation."

    OBJECT		hIfv6DupAddressRecoveryID
    MIN-ACCESS	read-write
    DESCRIPTION
        "(U//FOUO) Implementation of this object can be as low
         as read-write depending on which
         IS Objective or MIB desired requirements are
         not being met by the implementation."

    OBJECT		ipv6RouterAdvertManagedFlag
    MIN-ACCESS	read-write
    DESCRIPTION
        "(U//FOUO) Implementation of this object can be as low
         as read-write depending on which
         IS Objective or MIB desired requirements are
         not being met by the implementation."

    OBJECT		ifAlias
    MIN-ACCESS	read-only
    DESCRIPTION
        "(U//FOUO) Implementation of this object can be as low
         as read-only depending on which
         IS Objective or MIB desired requirements are
         not being met by the implementation."

    OBJECT		ifOutUcastPkts
    MIN-ACCESS	not-accessible
    DESCRIPTION
        "(U//FOUO) Implementation of this object can be as low
         as not-accessible depending on which
         IS Objective or MIB desired requirements are
         not being met by the implementation."

    OBJECT		hIPhSelectorSrcAddressEnd
    MIN-ACCESS	not-accessible
    DESCRIPTION
        "(U//FOUO) Implementation of this object can be as low
         as not-accessible depending on which
         IS Objective or MIB desired requirements are
         not being met by the implementation."

    OBJECT		ifMtu
    MIN-ACCESS	read-only
    DESCRIPTION
        "(U//FOUO) Implementation of this object can be as low
         as read-only depending on which
         IS Objective or MIB desired requirements are
         not being met by the implementation."

    OBJECT		ipv6ScopeZoneIndexA
    MIN-ACCESS	read-only
    DESCRIPTION
        "(U//FOUO) Implementation of this object can be as low
         as read-only depending on which
         IS Objective or MIB desired requirements are
         not being met by the implementation."

    OBJECT		ipv6InterfaceForwarding
    MIN-ACCESS	read-only
    DESCRIPTION
        "(U//FOUO) Implementation of this object can be as low
         as read-only depending on which
         IS Objective or MIB desired requirements are
         not being met by the implementation."

    OBJECT		ipv6InterfaceRetransmitTime
    MIN-ACCESS	read-only
    DESCRIPTION
        "(U//FOUO) Implementation of this object can be as low
         as read-only depending on which
         IS Objective or MIB desired requirements are
         not being met by the implementation."

    OBJECT		ipAddressIfIndex
    MIN-ACCESS	read-only
    DESCRIPTION
        "(U//FOUO) Implementation of this object can be as low
         as read-only depending on which
         IS Objective or MIB desired requirements are
         not being met by the implementation."

    OBJECT		ifLastChange
    MIN-ACCESS	read-only
    DESCRIPTION
        "(U//FOUO) Implementation of this object can be as low
         as read-only depending on which
         IS Objective or MIB desired requirements are
         not being met by the implementation."

    OBJECT		ifLinkUpDownTrapEnable
    MIN-ACCESS	not-accessible
    DESCRIPTION
        "(U//FOUO) Implementation of this object can be as low
         as not-accessible depending on which
         IS Objective or MIB desired requirements are
         not being met by the implementation."

    OBJECT		ifHCOutBroadcastPkts
    MIN-ACCESS	read-only
    DESCRIPTION
        "(U//FOUO) Implementation of this object can be as low
         as read-only depending on which
         IS Objective or MIB desired requirements are
         not being met by the implementation."

    OBJECT		ifInErrors
    MIN-ACCESS	not-accessible
    DESCRIPTION
        "(U//FOUO) Implementation of this object can be as low
         as not-accessible depending on which
         IS Objective or MIB desired requirements are
         not being met by the implementation."

    OBJECT		hIPhSelectorSrcAddressBegin
    MIN-ACCESS	not-accessible
    DESCRIPTION
        "(U//FOUO) Implementation of this object can be as low
         as not-accessible depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hIfv6DupAddressDetection
    MIN-ACCESS	read-write
    DESCRIPTION
        "(U//FOUO) Implementation of this object can be as low
         as read-write depending on which
         IS Objective or MIB desired requirements are
         not being met by the implementation."

    OBJECT		ipv6ScopeZoneIndexLinkLocal
    MIN-ACCESS	read-only
    DESCRIPTION
        "(U//FOUO) Implementation of this object can be as low
         as read-only depending on which
         IS Objective or MIB desired requirements are
         not being met by the implementation."

    OBJECT		hIPhRuleLastChanged
    MIN-ACCESS	not-accessible
    DESCRIPTION
        "(U//FOUO) Implementation of this object can be as low
         as not-accessible depending on which
         IS Objective or MIB desired requirements are
         not being met by the implementation."

    OBJECT		ipv6InterfaceReachableTime
    MIN-ACCESS	read-only
    DESCRIPTION
        "(U//FOUO) Implementation of this object can be as low
         as read-only depending on which
         IS Objective or MIB desired requirements are
         not being met by the implementation."

    OBJECT		ipv6RouterAdvertCurHopLimit
    MIN-ACCESS	read-write
    DESCRIPTION
        "(U//FOUO) Implementation of this object can be as low
         as read-write depending on which
         IS Objective or MIB desired requirements are
         not being met by the implementation."

    OBJECT		ifHCInBroadcastPkts
    MIN-ACCESS	read-only
    DESCRIPTION
        "(U//FOUO) Implementation of this object can be as low
         as read-only depending on which
         IS Objective or MIB desired requirements are
         not being met by the implementation."

    OBJECT		hIPhSelectorIPVersion
    MIN-ACCESS	not-accessible
    DESCRIPTION
        "(U//FOUO) Implementation of this object can be as low
         as not-accessible depending on which
         IS Objective or MIB desired requirements are
         not being met by the implementation."

    OBJECT		ipv6RouterAdvertReachableTime
    MIN-ACCESS	read-write
    DESCRIPTION
        "(U//FOUO) Implementation of this object can be as low
         as read-write depending on which
         IS Objective or MIB desired requirements are
         not being met by the implementation."

    OBJECT		ifOperStatus
    MIN-ACCESS	read-only
    DESCRIPTION
        "(U//FOUO) Implementation of this object can be as low
         as read-only depending on which
         IS Objective or MIB desired requirements are
         not being met by the implementation."

    OBJECT		ifHCOutUcastPkts
    MIN-ACCESS	read-only
    DESCRIPTION
        "(U//FOUO) Implementation of this object can be as low
         as read-only depending on which
         IS Objective or MIB desired requirements are
         not being met by the implementation."

    OBJECT		ipv6RouterAdvertRowStatus
    MIN-ACCESS	read-write
    DESCRIPTION
        "(U//FOUO) Implementation of this object can be as low
         as read-write depending on which
         IS Objective or MIB desired requirements are
         not being met by the implementation."

    OBJECT		hIfv6BaseReachableTime
    MIN-ACCESS	read-write
    DESCRIPTION
        "(U//FOUO) Implementation of this object can be as low
         as read-write depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hiaaType
    MIN-ACCESS	read-write
    DESCRIPTION
        "(U//FOUO) Implementation of this object can be as low
         as read-write depending on which
         IS Objective or MIB desired requirements are
         not being met by the implementation."

    OBJECT		ipv6RouterAdvertMaxInterval
    MIN-ACCESS	read-write
    DESCRIPTION
        "(U//FOUO) Implementation of this object can be as low
         as read-write depending on which
         IS Objective or MIB desired requirements are
         not being met by the implementation."

    OBJECT		ifIndex
    MIN-ACCESS	read-only
    DESCRIPTION
        "(U//FOUO) Implementation of this object can be as low
         as read-only depending on which
         IS Objective or MIB desired requirements are
         not being met by the implementation."

    OBJECT		ipv6InterfaceEnableStatus
    MIN-ACCESS	read-only
    DESCRIPTION
        "(U//FOUO) Implementation of this object can be as low
         as read-only depending on which
         IS Objective or MIB desired requirements are
         not being met by the implementation."

    OBJECT		ipAddressStorageType
    MIN-ACCESS	read-only
    DESCRIPTION
        "(U//FOUO) Implementation of this object can be as low
         as read-only depending on which
         IS Objective or MIB desired requirements are
         not being met by the implementation."

    OBJECT		ipAddressStatus
    MIN-ACCESS	read-only
    DESCRIPTION
        "(U//FOUO) Implementation of this object can be as low
         as read-only depending on which
         IS Objective or MIB desired requirements are
         not being met by the implementation."

    OBJECT		hIPhRuleActionIndex
    MIN-ACCESS	not-accessible
    DESCRIPTION
        "(U//FOUO) Implementation of this object can be as low
         as not-accessible depending on which
         IS Objective or MIB desired requirements are
         not being met by the implementation."

--    OBJECT		hTPAddressMapTable
--    MIN-ACCESS	read-only
--    DESCRIPTION
--        "(U//FOUO) Implementation of this object can be as low
--         as read-only depending on which
--         IS Objective or MIB desired requirements are
--         not being met by the implementation."

    OBJECT		hv6APAddressPrefixAdvValidLifetime
    MIN-ACCESS	read-write
    DESCRIPTION
        "(U//FOUO) Implementation of this object can be as low
         as read-write depending on which
         IS Objective or MIB desired requirements are
         not being met by the implementation."

    OBJECT		hiaaPrefixLen
    MIN-ACCESS	read-write
    DESCRIPTION
        "(U//FOUO) Implementation of this object can be as low
         as read-write depending on which
         IS Objective or MIB desired requirements are
         not being met by the implementation."

--    OBJECT		hNetDuplicateAddressIfDown
--    MIN-ACCESS	not-accessible
--    DESCRIPTION
--        "(U//FOUO) Implementation of this object can be as low
--         as not-accessible depending on which
--         IS Objective or MIB desired requirements are
--         not being met by the implementation."

    OBJECT		ifInUnknownProtos
    MIN-ACCESS	not-accessible
    DESCRIPTION
        "(U//FOUO) Implementation of this object can be as low
         as not-accessible depending on which
         IS Objective or MIB desired requirements are
         not being met by the implementation."

    OBJECT		ifType
    MIN-ACCESS	read-only
    DESCRIPTION
        "(U//FOUO) Implementation of this object can be as low
         as read-only depending on which
         IS Objective or MIB desired requirements are
         not being met by the implementation."

    OBJECT		hIGMPMode
    MIN-ACCESS	read-write
    DESCRIPTION
        "(U//FOUO) Implementation of this object can be as low
         as read-write depending on which
         IS Objective or MIB desired requirements are
         not being met by the implementation."

    OBJECT		ipv6RouterAdvertSpinLock
    MIN-ACCESS	not-accessible
    DESCRIPTION
        "(U//FOUO) Implementation of this object can be as low
         as not-accessible depending on which
         IS Objective or MIB desired requirements are
         not being met by the implementation."

    OBJECT		ifPhysAddress
    MIN-ACCESS	read-only
    DESCRIPTION
        "(U//FOUO) Implementation of this object can be as low
         as read-only depending on which
         IS Objective or MIB desired requirements are
         not being met by the implementation."

    OBJECT		ifDescr
    MIN-ACCESS	read-only
    DESCRIPTION
        "(U//FOUO) Implementation of this object can be as low
         as read-only depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		ifConnectorPresent
    MIN-ACCESS	read-only
    DESCRIPTION
        "(U//FOUO) Implementation of this object can be as low
         as read-only depending on which
         IS Objective or MIB desired requirements are
         not being met by the implementation."

    OBJECT		ipv6ScopeZoneIndexC
    MIN-ACCESS	read-only
    DESCRIPTION
        "(U//FOUO) Implementation of this object can be as low
         as read-only depending on which
         IS Objective or MIB desired requirements are
         not being met by the implementation."

    OBJECT		ipAddressOrigin
    MIN-ACCESS	read-only
    DESCRIPTION
        "(U//FOUO) Implementation of this object can be as low
         as read-only depending on which
         IS Objective or MIB desired requirements are
         not being met by the implementation."

    OBJECT		ipv6ScopeZoneIndex7
    MIN-ACCESS	read-only
    DESCRIPTION
        "(U//FOUO) Implementation of this object can be as low
         as read-only depending on which
         IS Objective or MIB desired requirements are
         not being met by the implementation."

    OBJECT		ifOutOctets
    MIN-ACCESS	not-accessible
    DESCRIPTION
        "(U//FOUO) Implementation of this object can be as low
         as not-accessible depending on which
         IS Objective or MIB desired requirements are
         not being met by the implementation."

    OBJECT		ifSpeed
    MIN-ACCESS	read-only
    DESCRIPTION
        "(U//FOUO) Implementation of this object can be as low
         as read-only depending on which
         IS Objective or MIB desired requirements are
         not being met by the implementation."

    OBJECT		hIfv6PMTUResetPeriod
    MIN-ACCESS	not-accessible
    DESCRIPTION
        "(U//FOUO) Implementation of this object can be as low
         as not-accessible depending on which
         IS Objective or MIB desired requirements are
         not being met by the implementation."

    OBJECT		ipv6RouterAdvertLinkMTU
    MIN-ACCESS	read-write
    DESCRIPTION
        "(U//FOUO) Implementation of this object can be as low
         as read-write depending on which
         IS Objective or MIB desired requirements are
         not being met by the implementation."

    OBJECT		ifPromiscuousMode
    MIN-ACCESS	not-accessible
    DESCRIPTION
        "(U//FOUO) Implementation of this object can be as low
         as not-accessible depending on which
         IS Objective or MIB desired requirements are
         not being met by the implementation."

    OBJECT		hv6APRowStatus
    MIN-ACCESS	read-write
    DESCRIPTION
        "(U//FOUO) Implementation of this object can be as low
         as read-write depending on which
         IS Objective or MIB desired requirements are
         not being met by the implementation."

    OBJECT		ipv6ScopeZoneIndexAdminLocal
    MIN-ACCESS	read-only
    DESCRIPTION
        "(U//FOUO) Implementation of this object can be as low
         as read-only depending on which
         IS Objective or MIB desired requirements are
         not being met by the implementation."

    OBJECT		ipv6ScopeZoneIndex9
    MIN-ACCESS	read-only
    DESCRIPTION
        "(U//FOUO) Implementation of this object can be as low
         as read-only depending on which
         IS Objective or MIB desired requirements are
         not being met by the implementation."

--    OBJECT		hIfAddrAssignmentTable
--    MIN-ACCESS	read-only
--    DESCRIPTION
--        "(U//FOUO) Implementation of this object can be as low
--         as read-only depending on which
--         IS Objective or MIB desired requirements are
--         not being met by the implementation."

    OBJECT		ipv6ScopeZoneIndex6
    MIN-ACCESS	read-only
    DESCRIPTION
        "(U//FOUO) Implementation of this object can be as low
         as read-only depending on which
         IS Objective or MIB desired requirements are
         not being met by the implementation."

    OBJECT		ifOutMulticastPkts
    MIN-ACCESS	not-accessible
    DESCRIPTION
        "(U//FOUO) Implementation of this object can be as low
         as not-accessible depending on which
         IS Objective or MIB desired requirements are
         not being met by the implementation."

    OBJECT		hTPAddMapCTAddress
    MIN-ACCESS	read-write
    DESCRIPTION
        "(U//FOUO) Implementation of this object can be as low
         as read-write depending on which
         IS Objective or MIB desired requirements are
         not being met by the implementation."

--    OBJECT		hNetDuplicateAddressDetected
--    MIN-ACCESS	not-accessible
--    DESCRIPTION
--        "(U//FOUO) Implementation of this object can be as low
--         as not-accessible depending on which
--         IS Objective or MIB desired requirements are
--         not being met by the implementation."

--    OBJECT		ipv6InterfaceTable
--    MIN-ACCESS	read-only
--    DESCRIPTION
--        "(U//FOUO) Implementation of this object can be as low
--         as read-only depending on which
--         IS Objective or MIB desired requirements are
--         not being met by the implementation."

    OBJECT		ifInBroadcastPkts
    MIN-ACCESS	not-accessible
    DESCRIPTION
        "(U//FOUO) Implementation of this object can be as low
         as not-accessible depending on which
         IS Objective or MIB desired requirements are
         not being met by the implementation."

    OBJECT		ifHCInUcastPkts
    MIN-ACCESS	read-only
    DESCRIPTION
        "(U//FOUO) Implementation of this object can be as low
         as read-only depending on which
         IS Objective or MIB desired requirements are
         not being met by the implementation."

    OBJECT		hIPhRuleAdminStatus
    MIN-ACCESS	not-accessible
    DESCRIPTION
        "(U//FOUO) Implementation of this object can be as low
         as not-accessible depending on which
         IS Objective or MIB desired requirements are
         not being met by the implementation."

    OBJECT		hTPAddMapRowStatus
    MIN-ACCESS	read-write
    DESCRIPTION
        "(U//FOUO) Implementation of this object can be as low
         as read-write depending on which
         IS Objective or MIB desired requirements are
         not being met by the implementation."

    OBJECT		ipv6InterfaceReasmMaxSize
    MIN-ACCESS	read-only
    DESCRIPTION
        "(U//FOUO) Implementation of this object can be as low
         as read-only depending on which
         IS Objective or MIB desired requirements are
         not being met by the implementation."

--    OBJECT		hv6AddressPrefixTable
--    MIN-ACCESS	read-only
--    DESCRIPTION
--        "(U//FOUO) Implementation of this object can be as low
--         as read-only depending on which
--         IS Objective or MIB desired requirements are
--         not being met by the implementation."

    OBJECT		hIfv6RetransmitTime
    MIN-ACCESS	read-write
    DESCRIPTION
        "(U//FOUO) Implementation of this object can be as low
         as read-write depending on which
         IS Objective or MIB desired requirements are
         not being met by the implementation."

    OBJECT		ifCounterDiscontinuityTime
    MIN-ACCESS	not-accessible
    DESCRIPTION
        "(U//FOUO) Implementation of this object can be as low
         as not-accessible depending on which
         IS Objective or MIB desired requirements are
         not being met by the implementation."

    OBJECT		hIfv6LowPMTUThreshold
    MIN-ACCESS	not-accessible
    DESCRIPTION
        "(U//FOUO) Implementation of this object can be as low
         as not-accessible depending on which
         IS Objective or MIB desired requirements are
         not being met by the implementation."

    OBJECT		ifHCOutMulticastPkts
    MIN-ACCESS	read-only
    DESCRIPTION
        "(U//FOUO) Implementation of this object can be as low
         as read-only depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		ifInNUcastPkts
    MIN-ACCESS	not-accessible
    DESCRIPTION
        "(U//FOUO) Implementation of this object can be as low
         as not-accessible depending on which
         IS Objective or MIB desired requirements are
         not being met by the implementation."

    OBJECT		hIfv6RouterSolicitation
    MIN-ACCESS	read-write
    DESCRIPTION
        "(U//FOUO) Implementation of this object can be as low
         as read-write depending on which
         IS Objective or MIB desired requirements are
         not being met by the implementation."

    OBJECT		hIPhSelectorRowStatus
    MIN-ACCESS	not-accessible
    DESCRIPTION
        "(U//FOUO) Implementation of this object can be as low
         as not-accessible depending on which
         IS Objective or MIB desired requirements are
         not being met by the implementation."

    OBJECT		hiaaAddress
    MIN-ACCESS	read-write
    DESCRIPTION
        "(U//FOUO) Implementation of this object can be as low
         as read-write depending on which
         IS Objective or MIB desired requirements are
         not being met by the implementation."

    OBJECT		hIfv6Side
    MIN-ACCESS	read-only
    DESCRIPTION
        "(U//FOUO) Implementation of this object can be as low
         as read-only depending on which
         IS Objective or MIB desired requirements are
         not being met by the implementation."

    OBJECT		ipAddressLastChanged
    MIN-ACCESS	read-only
    DESCRIPTION
        "(U//FOUO) Implementation of this object can be as low
         as read-only depending on which
         IS Objective or MIB desired requirements are
         not being met by the implementation."

    OBJECT		hTPAddMapLastChanged
    MIN-ACCESS	read-only
    DESCRIPTION
        "(U//FOUO) Implementation of this object can be as low
         as read-only depending on which
         IS Objective or MIB desired requirements are
         not being met by the implementation."

    OBJECT		ipAddressRowStatus
    MIN-ACCESS	read-only
    DESCRIPTION
        "(U//FOUO) Implementation of this object can be as low
         as read-only depending on which
         IS Objective or MIB desired requirements are
         not being met by the implementation."

    OBJECT		ipAddressType
    MIN-ACCESS	read-only
    DESCRIPTION
        "(U//FOUO) Implementation of this object can be as low
         as read-only depending on which
         IS Objective or MIB desired requirements are
         not being met by the implementation."

    OBJECT		ipv6InterfaceIdentifier
    MIN-ACCESS	read-only
    DESCRIPTION
        "(U//FOUO) Implementation of this object can be as low
         as read-only depending on which
         IS Objective or MIB desired requirements are
         not being met by the implementation."

    OBJECT		ifNumber
    MIN-ACCESS	read-only
    DESCRIPTION
        "(U//FOUO) Implementation of this object can be as low
         as read-only depending on which
         IS Objective or MIB desired requirements are
         not being met by the implementation."

    OBJECT		ifName
    MIN-ACCESS	read-only
    DESCRIPTION
        "(U//FOUO) Implementation of this object can be as low
         as read-only depending on which
         IS Objective or MIB desired requirements are
         not being met by the implementation."

    OBJECT		ifOutBroadcastPkts
    MIN-ACCESS	not-accessible
    DESCRIPTION
        "(U//FOUO) Implementation of this object can be as low
         as not-accessible depending on which
         IS Objective or MIB desired requirements are
         not being met by the implementation."

    OBJECT		hv6APAddressPrefixAutonomousFlag
    MIN-ACCESS	read-write
    DESCRIPTION
        "(U//FOUO) Implementation of this object can be as low
         as read-write depending on which
         IS Objective or MIB desired requirements are
         not being met by the implementation."

    OBJECT		ipv6RouterAdvertMinInterval
    MIN-ACCESS	read-write
    DESCRIPTION
        "(U//FOUO) Implementation of this object can be as low
         as read-write depending on which
         IS Objective or MIB desired requirements are
         not being met by the implementation."

    OBJECT		hIfv6UseDepAddress
    MIN-ACCESS	read-write
    DESCRIPTION
        "(U//FOUO) Implementation of this object can be as low
         as read-write depending on which
         IS Objective or MIB desired requirements are
         not being met by the implementation."

    OBJECT		hIPhSelectorDstAddressEnd
    MIN-ACCESS	not-accessible
    DESCRIPTION
        "(U//FOUO) Implementation of this object can be as low
         as not-accessible depending on which
         IS Objective or MIB desired requirements are
         not being met by the implementation."

    OBJECT		ipv6ScopeZoneIndex3
    MIN-ACCESS	read-only
    DESCRIPTION
        "(U//FOUO) Implementation of this object can be as low
         as read-only depending on which
         IS Objective or MIB desired requirements are
         not being met by the implementation."

    OBJECT		hIfv6ReachableTime
    MIN-ACCESS	read-write
    DESCRIPTION
        "(U//FOUO) Implementation of this object can be as low
         as read-write depending on which
         IS Objective or MIB desired requirements are
         not being met by the implementation."

    OBJECT		hIPhRuleAction
    MIN-ACCESS	not-accessible
    DESCRIPTION
        "(U//FOUO) Implementation of this object can be as low
         as not-accessible depending on which
         IS Objective or MIB desired requirements are
         not being met by the implementation."

    OBJECT		hIPhRuleRowStatus
    MIN-ACCESS	not-accessible
    DESCRIPTION
        "(U//FOUO) Implementation of this object can be as low
         as not-accessible depending on which
         IS Objective or MIB desired requirements are
         not being met by the implementation."

    OBJECT		ifAdminStatus
    MIN-ACCESS	read-write
    DESCRIPTION
        "(U//FOUO) Implementation of this object can be as low
         as read-write depending on which
         IS Objective or MIB desired requirements are
         not being met by the implementation."

    OBJECT		ifHCInMulticastPkts
    MIN-ACCESS	read-only
    DESCRIPTION
        "(U//FOUO) Implementation of this object can be as low
         as read-only depending on which
         IS Objective or MIB desired requirements are
         not being met by the implementation."

    OBJECT		hIfv6NextHeaderSkipList
    MIN-ACCESS	read-write
    DESCRIPTION
        "(U//FOUO) Implementation of this object can be as low
         as read-write depending on which
         IS Objective or MIB desired requirements are
         not being met by the implementation."

    OBJECT		ifOutErrors
    MIN-ACCESS	not-accessible
    DESCRIPTION
        "(U//FOUO) Implementation of this object can be as low
         as not-accessible depending on which
         IS Objective or MIB desired requirements are
         not being met by the implementation."

    OBJECT		hIPhSelectorDstAddressBegin
    MIN-ACCESS	not-accessible
    DESCRIPTION
        "(U//FOUO) Implementation of this object can be as low
         as not-accessible depending on which
         IS Objective or MIB desired requirements are
         not being met by the implementation."

    OBJECT		ipv6RouterAdvertOtherConfigFlag
    MIN-ACCESS	read-write
    DESCRIPTION
        "(U//FOUO) Implementation of this object can be as low
         as read-write depending on which
         IS Objective or MIB desired requirements are
         not being met by the implementation."

    OBJECT		ipv6ScopeZoneIndexD
    MIN-ACCESS	read-only
    DESCRIPTION
        "(U//FOUO) Implementation of this object can be as low
         as read-only depending on which
         IS Objective or MIB desired requirements are
         not being met by the implementation."

    OBJECT		ipAddressPrefix
    MIN-ACCESS	read-only
    DESCRIPTION
        "(U//FOUO) Implementation of this object can be as low
         as read-only depending on which
         IS Objective or MIB desired requirements are
         not being met by the implementation."

    OBJECT		ipv6RouterAdvertRetransmitTime
    MIN-ACCESS	read-write
    DESCRIPTION
        "(U//FOUO) Implementation of this object can be as low
         as read-write depending on which
         IS Objective or MIB desired requirements are
         not being met by the implementation."

    OBJECT		ipv6RouterAdvertSendAdverts
    MIN-ACCESS	read-write
    DESCRIPTION
        "(U//FOUO) Implementation of this object can be as low
         as read-write depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		ipAddressCreated
    MIN-ACCESS	read-only
    DESCRIPTION
        "(U//FOUO) Implementation of this object can be as low
         as read-only depending on which
         IS Objective or MIB desired requirements are
         not being met by the implementation."

    OBJECT		hv6APAdvertisePrefix
    MIN-ACCESS	read-write
    DESCRIPTION
        "(U//FOUO) Implementation of this object can be as low
         as read-write depending on which
         IS Objective or MIB desired requirements are
         not being met by the implementation."

    OBJECT		hIfv6HopLimit
    MIN-ACCESS	read-only
    DESCRIPTION
        "(U//FOUO) Implementation of this object can be as low
         as read-only depending on which
         IS Objective or MIB desired requirements are
         not being met by the implementation."

    OBJECT		hIfv6MTU
    MIN-ACCESS	read-write
    DESCRIPTION
        "(U//FOUO) Implementation of this object can be as low
         as read-write depending on which
         IS Objective or MIB desired requirements are
         not being met by the implementation."

    OBJECT		hIPhRuleSelectorName
    MIN-ACCESS	not-accessible
    DESCRIPTION
        "(U//FOUO) Implementation of this object can be as low
         as not-accessible depending on which
         IS Objective or MIB desired requirements are
         not being met by the implementation."

    OBJECT		ifInMulticastPkts
    MIN-ACCESS	not-accessible
    DESCRIPTION
        "(U//FOUO) Implementation of this object can be as low
         as not-accessible depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		ifHCInOctets
    MIN-ACCESS	read-only
    DESCRIPTION
        "(U//FOUO) Implementation of this object can be as low
         as read-only depending on which
         IS Objective or MIB desired requirements are
         not being met by the implementation."

    OBJECT		ipv6ScopeZoneIndexOrganizationLocal
    MIN-ACCESS	read-only
    DESCRIPTION
        "(U//FOUO) Implementation of this object can be as low
         as read-only depending on which
         IS Objective or MIB desired requirements are
         not being met by the implementation."

    OBJECT		hv6APTableLastChanged
    MIN-ACCESS	read-only
    DESCRIPTION
        "(U//FOUO) Implementation of this object can be as low
         as read-only depending on which
         IS Objective or MIB desired requirements are
         not being met by the implementation."

    OBJECT		hv6APAddressPrefixAdvPreferredLifetime
    MIN-ACCESS	read-write
    DESCRIPTION
        "(U//FOUO) Implementation of this object can be as low
         as read-write depending on which
         IS Objective or MIB desired requirements are
         not being met by the implementation."

    OBJECT		hIfv4MTU
    MIN-ACCESS	not-accessible
    DESCRIPTION
        "(U//FOUO) Implementation of this object can be as low
         as not-accessible depending on which
         IS Objective or MIB desired requirements are
         not being met by the implementation."

    OBJECT		ifInUcastPkts
    MIN-ACCESS	not-accessible
    DESCRIPTION
        "(U//FOUO) Implementation of this object can be as low
         as not-accessible depending on which
         IS Objective or MIB desired requirements are
         not being met by the implementation."

    OBJECT		hIfv6TrymeSA
    MIN-ACCESS	not-accessible
    DESCRIPTION
        "(U//FOUO) Implementation of this object can be as low
         as not-accessible depending on which
         IS Objective or MIB desired requirements are
         not being met by the implementation."

    OBJECT		hIPhRuleName
    MIN-ACCESS	not-accessible
    DESCRIPTION
        "(U//FOUO) Implementation of this object can be as low
         as not-accessible depending on which
         IS Objective or MIB desired requirements are
         not being met by the implementation."

    OBJECT		hv6APAddressPrefixOnLinkFlag
    MIN-ACCESS	read-write
    DESCRIPTION
        "(U//FOUO) Implementation of this object can be as low
         as read-write depending on which
         IS Objective or MIB desired requirements are
         not being met by the implementation."

    OBJECT		hIfv6AddressAutoConfig
    MIN-ACCESS	read-write
    DESCRIPTION
        "(U//FOUO) Implementation of this object can be as low
         as read-write depending on which
         IS Objective or MIB desired requirements are
         not being met by the implementation."

    OBJECT		ipv6ScopeZoneIndexB
    MIN-ACCESS	read-only
    DESCRIPTION
        "(U//FOUO) Implementation of this object can be as low
         as read-only depending on which
         IS Objective or MIB desired requirements are
         not being met by the implementation."

    OBJECT		hNetSourceAddress
    MIN-ACCESS	not-accessible
    DESCRIPTION
        "(U//FOUO) Implementation of this object can be as low
         as not-accessible depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hIPhSelectorLastChanged
    MIN-ACCESS	not-accessible
    DESCRIPTION
        "(U//FOUO) Implementation of this object can be as low
         as not-accessible depending on which
         IS Objective or MIB desired requirements are
         not being met by the implementation."

    OBJECT		hNetSourceAddressType
    MIN-ACCESS	not-accessible
    DESCRIPTION
        "(U//FOUO) Implementation of this object can be as low
         as not-accessible depending on which
         IS Objective or MIB desired requirements are
         not being met by the implementation."

    OBJECT		ifHighSpeed
    MIN-ACCESS	read-only
    DESCRIPTION
        "(U//FOUO) Implementation of this object can be as low
         as read-only depending on which
         IS Objective or MIB desired requirements are
         not being met by the implementation."

    OBJECT		hiaaInterface
    MIN-ACCESS	read-write
    DESCRIPTION
        "(U//FOUO) Implementation of this object can be as low
         as read-write depending on which
         IS Objective or MIB desired requirements are
         not being met by the implementation."

    OBJECT		hIfv6DiscardUnauthRed
    MIN-ACCESS	read-only
    DESCRIPTION
        "(U//FOUO) Implementation of this object can be as low
         as read-only depending on which
         IS Objective or MIB desired requirements are
         not being met by the implementation."

    OBJECT		hIPhSelectorType
    MIN-ACCESS	not-accessible
    DESCRIPTION
        "(U//FOUO) Implementation of this object can be as low
         as not-accessible depending on which
         IS Objective or MIB desired requirements are
         not being met by the implementation."

    OBJECT		hIfv4PMTUResetPeriod
    MIN-ACCESS	not-accessible
    DESCRIPTION
        "(U//FOUO) Implementation of this object can be as low
         as not-accessible depending on which
         IS Objective or MIB desired requirements are
         not being met by the implementation."

    OBJECT		hiaaRowStatus
    MIN-ACCESS	read-write
    DESCRIPTION
        "(U//FOUO) Implementation of this object can be as low
         as read-write depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hIfv6LastChanged
    MIN-ACCESS	read-only
    DESCRIPTION
        "(U//FOUO) Implementation of this object can be as low
         as read-only depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."

    OBJECT		hIPhSelectorTableCount
    MIN-ACCESS	not-accessible
    DESCRIPTION
        "(U//FOUO) Implementation of this object can be as low
         as not-accessible depending on which
         IS Objective or MIB desired requirements are
         not being met by the implementation."
::= { haipeV030002Conformance 2 }

--
-- Objects referenced by the Management IS
--
hManagementGroup OBJECT-GROUP
    OBJECTS {
                hStationID,
                hCurrentState,
                hSecurityAuthority,
                hSecurityLevel,
                hDeviceVersionTableCount,
                hDeviceVersionTableLastChanged,
                hdvName,
                hdvVersion,
                hSpinLock,
                hHMISpinLock,
                hLastChanged,
--                hBatteryLow,
--                hBatteryOK,
                hBatteryLevelWarningPercentage,
--                hBatteryTable,
                hBatteryNumber,
                hBatteryLevelPercentage,
                hBatteryOperStatus,
                hBatteryChangeDate,
                haipeResetDevice,
                haipeSanitizeDevice,
--                hAudNotificationLogWarning,
--                hAudNotificationLogFull,
--                hAudNotificationLogOk,
--                hGenericAuditNotification,
                hNotificationLogCapacityPercentage,
                hNotificationLogWarningPercentage,
                hNotificationLogFullBehavior,
                hNotificationLogReset,
                hNotificationLogPartialReset,
                hAuditConfigTableCount,
                hAuditConfigTableLastChanged,
                hAudCfgID,
                hAudCfgThrottlingEnabled,
                hAudCfgLogThrottleCfg,
                hAudCfgLogThrottleStatus,
                hAudCfgLogCount,
                hAudCfgLogThrottled,
                hAudCfgNotifEnabled,
                hAudCfgNotifThrottleCfg,
                hAudCfgNotifThrottleStatus,
                hAudCfgNotifCount,
                hAudCfgNotifThrottled,
                hAudCfgRowStatus,
                hAudThrottleConfigTableCount,
                hAudThrottleConfigTableLastChanged,
                hAudThrottleCfgName,
                hAudThrottleCfgThreshold,
                hAudThrottleCfgInterval,
                hAudThrottleCfgLastChanged,
                hAudThrottleCfgRowStatus,
                hTFTPDesiredBlockSize,
                hTFTPDesiredTimeoutInterval,
                hTFTPMaximumFileTransferSize,
                hFirmwareDownloadServersTableCount,
                hFirmwareDownloadServersTableLastChanged,
                hFdsPriority,
                hFdsURI,
                hFdsSide,
                hFdsLoginName,
                hFdsPassword,
                hFdsLastChanged,
                hFdsRowStatus,
                hFirmwareDownloadAdminStatus,
                hFirmwareDownloadOperStatus,
--                hFirmwareDownloadError,
--                hFirmwareDownloadSuccess,
--                hFirmwareInstallFailed,
--                hFirmwareInstallSucceeded,
                hFdErrorCode,
                hFdErrorDetail,
                hTopologyTableCount,
                hTopologyTableLastChanged,
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hIfv4HaipeTableCount,
                hIfv4HaipeTableLastChanged,
                hIfv4Side,
                hIfv4LastChanged,
                hIfv6HaipeTableCount,
                hIfv6HaipeTableLastChanged,
                hIfv6Side,
                hIfv6LastChanged,
--                hIfAddrAssignmentTable,
--                hIfAddrAssignmentTable,
                hiaaInterface,
                hiaaType,
                hiaaAddress,
                hiaaPrefixLen,
                hiaaRowStatus,
                haipeZeroizeAllKeys,
                hPreplacedKeyTableCount,
                hPreplacedKeyTableCapacity,
                hPreplacedKeyTableLastChanged,
                hPPKUsageType,
                hPPKEffectiveDate,
                hPPKSecurityLevel,
                hPPKZeroizeKey,
                hPPKRegister,
                hPPKAuthority,
                hPPKLastChanged,
--                hPPKEKTable,
                hPPKEKTableMaxCount,
--                hPPKEKTable,
                hPPKEKKeyType,
                hPPKEKUniversalID,
                hPPKChainTableCount,
                hPPKChainTableLastChanged,
                hPPKChainID,
                hPPKChainOrder,
                hPPKChainPPK,
                hPPKChainEffectiveDate,
                hPPKChainIntegrityAlgorithm,
                hPPKChainEncryptionAlgorithm,
                hPPKChainRowStatus,
--                hLocalCompromisedKeyListTable,
--                hLocalCompromisedKeyListTable,
                hLocalCKListUniversal,
                hLocalCKListKMIDBegin,
                hLocalCKListKMIDEnd,
                hLocalCKListUniversalEdition,
                hLocalCKListDate,
                hLocalCKListReason,
                hLocalCKListRowStatus,
--                hPPKKeyExpirationWarning,
                hPPKKeyExpirationWarningCount,
                hIPhRuleTableCount,
                hIPhRuleTableLastChanged,
                hIPhRuleName,
                hIPhRuleSelectorName,
                hIPhRuleAction,
                hIPhRuleActionIndex,
                hIPhRuleAdminStatus,
                hIPhRuleLastChanged,
                hIPhRuleRowStatus,
                hIPhSelectorTableCount,
                hIPhSelectorTableLastChanged,
                hIPhSelectorType,
                hIPhSelectorLastChanged,
                hIPhSelectorRowStatus,
                hIPhFFSATableCount,
                hIPhFFSATableLastChanged,
                hIPhFFSAFF,
                hIPhFFSATransformsName,
                hIPhFFSADSCP,
                hIPhFFSADSCPValue,
                hIPhFFSAECN,
                hIPhFFSAFlowLabel,
                hIPhFFSAFlowLabelValue,
                hIPhFFSADecrementTTL,
                hIPhFFSADIndexType,
                hIPhFFSALastChanged,
                hIPhFFSARowStatus,
                hIPhFFSAPDUNEnabled,
                hIPhFFSAPHRDRate,
                hIPhFFSADFBit,
                hIPhFFSAProcessFlowlabel,
                hIPhFFSARetryICMPCount,
                hIPhFFSAConnectionType,
                hIPhFFSACTOutAddressType,
                hIPhFFSACTOutAddress,
                hIPhFFSAPopulateFromPacket,
                hIPhFFSAFFUniversal,
                hIPhFFSAFFUniversalEdition,
                hTPSATableCount,
                hTPSATableLastChanged,
                hTPSAspi,
                hTPSAAddressType,
                hTPSALocalCTAddress,
                hTPSARemoteCTAddress,
                hTPSAPTAddressType,
                hTPSALocalPTAddress,
                hTPSARemotePTAddress,
                hTPSADirection,
                hTPSASelectorNextHeaderStart,
                hTPSASelectorNextHeaderEnd,
                hTPSASelectorNextHeaderOpt1Start,
                hTPSASelectorNextHeaderOpt1End,
                hTPSASelectorNextHeaderOpt2Start,
                hTPSASelectorNextHeaderOpt2End,
                hTPSAConnectionType,
                hTPSASecurityPayloadType,
                hTPSAStartTime,
                hTPSAEndTime,
                hTPSAPPK,
                hTPSACreationReason,
                hTPSAEncryptAlgorithm,
                hTPSAIntegrityAlgorithm,
                hTPSAICV,
                hTPSACryptoBlockSize,
                hTPSADSCP,
                hTPSADSCPValue,
                hTPSAPMTU,
                hTPSAECN,
                hTPSAFlowLabel,
                hTPSAFlowLabelValue,
                hTPSADecrementTTL,
                hTPSADIndexType,
                hTPSAPDUNEnabled,
                hTPSAPHRDRate,
                hTPSADFBit,
                hTPSAProcessFlowlabel,
                hTPSARetryICMPCount,
                hTPSAesn,
                hTPSAHCOctets,
                hTPSAHCUcastPkts,
                hTPSAHCMcastPkts,
                hTPSAHCBrdcastPkts,
                hTPSARowStatus,
                hTPSALocalCredentialID,
                hTPSALocalCredentialType,
                hTPSALocalCAName,
                hTPSARemoteCredentialID,
                hTPSARemoteCredentialType,
                hTPSARemoteCAName,
--                hTPnSADestroyed,
--                hTPnSACreated,
                hTPiDestinationAddressType,
                hTPiDestinationAddress,
                hTPiSPI,
                hTPiSADestroyedReason,
                hrSystemUptime,
                hrSystemDate,
                ifNumber,
                ifIndex,
                ifDescr,
                ifType,
                ifMtu,
                ifSpeed,
                ifPhysAddress,
                ifAdminStatus,
                ifOperStatus,
                ifLastChange,
                ifInOctets,
                ifInUcastPkts,
                ifInNUcastPkts,
                ifInDiscards,
                ifInErrors,
                ifInUnknownProtos,
                ifOutOctets,
                ifOutUcastPkts,
                ifOutNUcastPkts,
                ifOutDiscards,
                ifOutErrors,
                ifOutQLen,
                ifSpecific,
                ifIndex,
                ifName,
                ifInMulticastPkts,
                ifInBroadcastPkts,
                ifOutMulticastPkts,
                ifOutBroadcastPkts,
                ifHCInOctets,
                ifHCInUcastPkts,
                ifHCInMulticastPkts,
                ifHCInBroadcastPkts,
                ifHCOutOctets,
                ifHCOutUcastPkts,
                ifHCOutMulticastPkts,
                ifHCOutBroadcastPkts,
                ifLinkUpDownTrapEnable,
                ifHighSpeed,
                ifPromiscuousMode,
                ifConnectorPresent,
                ifAlias,
                ifCounterDiscontinuityTime,
                ifIndex,
                ifIndex,
                inetCidrRouteNumber,
                inetCidrRouteIfIndex,
                inetCidrRouteType,
                inetCidrRouteProto,
                inetCidrRouteAge,
                inetCidrRouteNextHopAS,
                inetCidrRouteMetric1,
                inetCidrRouteMetric2,
                inetCidrRouteMetric3,
                inetCidrRouteMetric4,
                inetCidrRouteMetric5,
                inetCidrRouteStatus,
                inetCidrRouteDiscards,
                ipForwarding,
                ipDefaultTTL,
                ipReasmTimeout,
                ipv6IpForwarding,
                ipv6IpDefaultHopLimit,
--                ipv4InterfaceTable,
                ipv4InterfaceReasmMaxSize,
                ipv4InterfaceEnableStatus,
                ipv4InterfaceRetransmitTime,
--                ipv6InterfaceTable,
                ipv6InterfaceReasmMaxSize,
                ipv6InterfaceIdentifier,
                ipv6InterfaceEnableStatus,
                ipv6InterfaceReachableTime,
                ipv6InterfaceRetransmitTime,
                ipv6InterfaceForwarding,
                ipSystemStatsInReceives,
                ipSystemStatsHCInReceives,
                ipSystemStatsInOctets,
                ipSystemStatsHCInOctets,
                ipSystemStatsInHdrErrors,
                ipSystemStatsInNoRoutes,
                ipSystemStatsInAddrErrors,
                ipSystemStatsInUnknownProtos,
                ipSystemStatsInTruncatedPkts,
                ipSystemStatsInForwDatagrams,
                ipSystemStatsHCInForwDatagrams,
                ipSystemStatsReasmReqds,
                ipSystemStatsReasmOKs,
                ipSystemStatsReasmFails,
                ipSystemStatsInDiscards,
                ipSystemStatsInDelivers,
                ipSystemStatsHCInDelivers,
                ipSystemStatsOutRequests,
                ipSystemStatsHCOutRequests,
                ipSystemStatsOutNoRoutes,
                ipSystemStatsOutForwDatagrams,
                ipSystemStatsHCOutForwDatagrams,
                ipSystemStatsOutDiscards,
                ipSystemStatsOutFragReqds,
                ipSystemStatsOutFragOKs,
                ipSystemStatsOutFragFails,
                ipSystemStatsOutFragCreates,
                ipSystemStatsOutTransmits,
                ipSystemStatsHCOutTransmits,
                ipSystemStatsOutOctets,
                ipSystemStatsHCOutOctets,
                ipSystemStatsInMcastPkts,
                ipSystemStatsHCInMcastPkts,
                ipSystemStatsInMcastOctets,
                ipSystemStatsHCInMcastOctets,
                ipSystemStatsOutMcastPkts,
                ipSystemStatsHCOutMcastPkts,
                ipSystemStatsOutMcastOctets,
                ipSystemStatsHCOutMcastOctets,
                ipSystemStatsInBcastPkts,
                ipSystemStatsHCInBcastPkts,
                ipSystemStatsOutBcastPkts,
                ipSystemStatsHCOutBcastPkts,
                ipSystemStatsDiscontinuityTime,
                ipSystemStatsRefreshRate,
                ipIfStatsTableLastChange,
                ipIfStatsInReceives,
                ipIfStatsHCInReceives,
                ipIfStatsInOctets,
                ipIfStatsHCInOctets,
                ipIfStatsInHdrErrors,
                ipIfStatsInNoRoutes,
                ipIfStatsInAddrErrors,
                ipIfStatsInUnknownProtos,
                ipIfStatsInTruncatedPkts,
                ipIfStatsInForwDatagrams,
                ipIfStatsHCInForwDatagrams,
                ipIfStatsReasmReqds,
                ipIfStatsReasmOKs,
                ipIfStatsReasmFails,
                ipIfStatsInDiscards,
                ipIfStatsInDelivers,
                ipIfStatsHCInDelivers,
                ipIfStatsOutRequests,
                ipIfStatsHCOutRequests,
                ipIfStatsOutForwDatagrams,
                ipIfStatsHCOutForwDatagrams,
                ipIfStatsOutDiscards,
                ipIfStatsOutFragReqds,
                ipIfStatsOutFragOKs,
                ipIfStatsOutFragFails,
                ipIfStatsOutFragCreates,
                ipIfStatsOutTransmits,
                ipIfStatsHCOutTransmits,
                ipIfStatsOutOctets,
                ipIfStatsHCOutOctets,
                ipIfStatsInMcastPkts,
                ipIfStatsHCInMcastPkts,
                ipIfStatsInMcastOctets,
                ipIfStatsHCInMcastOctets,
                ipIfStatsOutMcastPkts,
                ipIfStatsHCOutMcastPkts,
                ipIfStatsOutMcastOctets,
                ipIfStatsHCOutMcastOctets,
                ipIfStatsInBcastPkts,
                ipIfStatsHCInBcastPkts,
                ipIfStatsOutBcastPkts,
                ipIfStatsHCOutBcastPkts,
                ipIfStatsDiscontinuityTime,
                ipIfStatsRefreshRate,
                ipAddressSpinLock,
                ipNetToPhysicalPhysAddress,
                ipNetToPhysicalLastUpdated,
                ipNetToPhysicalType,
                ipNetToPhysicalState,
                ipNetToPhysicalRowStatus,
                mgmdHostInterfaceQuerier,
                mgmdHostInterfaceStatus,
                mgmdHostInterfaceVersion,
                mgmdHostInterfaceVersion1QuerierTimer,
                mgmdHostInterfaceVersion2QuerierTimer,
                mgmdHostInterfaceVersion3Robustness,
                mgmdRouterInterfaceQuerier,
                mgmdRouterInterfaceQueryInterval,
                mgmdRouterInterfaceStatus,
                mgmdRouterInterfaceVersion,
                mgmdRouterInterfaceQueryMaxResponseTime,
                mgmdRouterInterfaceQuerierUpTime,
                mgmdRouterInterfaceQuerierExpiryTime,
                mgmdRouterInterfaceWrongVersionQueries,
                mgmdRouterInterfaceJoins,
                mgmdRouterInterfaceProxyIfIndex,
                mgmdRouterInterfaceGroups,
                mgmdRouterInterfaceRobustness,
                mgmdRouterInterfaceLastMembQueryIntvl,
                mgmdRouterInterfaceLastMembQueryCount,
                mgmdRouterInterfaceStartupQueryCount,
                mgmdRouterInterfaceStartupQueryInterval,
                mgmdHostCacheUpTime,
                mgmdHostCacheLastReporter,
                mgmdHostCacheSourceFilterMode,
                mgmdRouterCacheLastReporter,
                mgmdRouterCacheUpTime,
                mgmdRouterCacheExpiryTime,
                mgmdRouterCacheExcludeModeExpiryTimer,
                mgmdRouterCacheVersion1HostTimer,
                mgmdRouterCacheVersion2HostTimer,
                mgmdRouterCacheSourceFilterMode,
                mgmdHostSrcListHostAddress,
                mgmdRouterSrcListHostAddress,
                mgmdRouterSrcListExpire,
                nlmConfigGlobalEntryLimit,
                nlmStatsGlobalNotificationsLogged,
                nlmStatsGlobalNotificationsBumped,
                nlmStatsLogNotificationsLogged,
                nlmStatsLogNotificationsBumped,
                nlmLogTime,
                nlmLogDateAndTime,
                nlmLogEngineID,
                nlmLogEngineTAddress,
                nlmLogEngineTDomain,
                nlmLogContextEngineID,
                nlmLogContextName,
                nlmLogNotificationID,
                nlmLogVariableID,
                nlmLogVariableValueType,
                nlmLogVariableCounter32Val,
                nlmLogVariableUnsigned32Val,
                nlmLogVariableTimeTicksVal,
                nlmLogVariableInteger32Val,
                nlmLogVariableOctetStringVal,
                nlmLogVariableIpAddressVal,
                nlmLogVariableOidVal,
                nlmLogVariableCounter64Val,
                nlmLogVariableOpaqueVal,
--                snmpFrameworkMIB,
--                snmpFrameworkAdmin,
--                snmpAuthProtocols,
--                usmNoAuthProtocol,
--                usmHMACMD5AuthProtocol,
--                usmHMACSHAAuthProtocol,
--                snmpPrivProtocols,
--                usmNoPrivProtocol,
--                usmDESPrivProtocol,
--                usmAesCfb128Protocol,
--                snmpFrameworkMIBObjects,
--                snmpEngine,
                snmpEngineID,
                snmpEngineBoots,
                snmpEngineTime,
                snmpEngineMaxMessageSize,
--                snmpFrameworkMIBConformance,
--                snmpFrameworkMIBCompliances,
--                snmpFrameworkMIBCompliance,
--                snmpFrameworkMIBGroups,
--                snmpEngineGroup,
--                snmpMPDMIB,
--                snmpMPDAdmin,
--                snmpMPDMIBObjects,
--                snmpMPDStats,
                snmpUnknownSecurityModels,
                snmpInvalidMsgs,
                snmpUnknownPDUHandlers,
--                snmpMPDMIBConformance,
--                snmpMPDMIBCompliances,
--                snmpMPDCompliance,
--                snmpMPDMIBGroups,
--                snmpMPDGroup,
--                snmpNotificationMIB,
--                snmpNotifyObjects,
                snmpNotifyTag,
                snmpNotifyType,
                snmpNotifyStorageType,
                snmpNotifyRowStatus,
                snmpNotifyFilterProfileName,
                snmpNotifyFilterProfileStorType,
                snmpNotifyFilterProfileRowStatus,
                snmpNotifyFilterProfileName,
                snmpNotifyFilterMask,
                snmpNotifyFilterType,
                snmpNotifyFilterStorageType,
                snmpNotifyFilterRowStatus,
--                snmpNotifyConformance,
--                snmpNotifyCompliances,
--                snmpNotifyBasicCompliance,
--                snmpNotifyBasicFiltersCompliance,
--                snmpNotifyFullCompliance,
--                snmpNotifyGroups,
--                snmpNotifyGroup,
--                snmpNotifyFilterGroup,
--                snmpTargetMIB,
--                snmpTargetObjects,
                snmpTargetSpinLock,
                snmpTargetAddrTDomain,
                snmpTargetAddrTAddress,
                snmpTargetAddrTimeout,
                snmpTargetAddrRetryCount,
                snmpTargetAddrTagList,
                snmpTargetAddrParams,
                snmpTargetAddrStorageType,
                snmpTargetAddrRowStatus,
                snmpTargetParamsMPModel,
                snmpTargetParamsSecurityModel,
                snmpTargetParamsSecurityName,
                snmpTargetParamsSecurityLevel,
                snmpTargetParamsStorageType,
                snmpTargetParamsRowStatus,
                snmpUnavailableContexts,
                snmpUnknownContexts,
--                snmpTargetConformance,
--                snmpTargetCompliances,
--                snmpTargetCommandResponderCompliance,
--                snmpTargetGroups,
--                snmpTargetBasicGroup,
--                snmpTargetResponseGroup,
--                snmpTargetCommandResponderGroup,
--                snmpUsmMIB,
--                usmMIBObjects,
--                usmStats,
                usmStatsUnsupportedSecLevels,
                usmStatsNotInTimeWindows,
                usmStatsUnknownUserNames,
                usmStatsUnknownEngineIDs,
                usmStatsWrongDigests,
                usmStatsDecryptionErrors,
--                usmUser,
                usmUserSpinLock,
                usmUserSecurityName,
                usmUserCloneFrom,
                usmUserAuthProtocol,
                usmUserAuthKeyChange,
                usmUserOwnAuthKeyChange,
                usmUserPrivProtocol,
                usmUserPrivKeyChange,
                usmUserOwnPrivKeyChange,
                usmUserPublic,
                usmUserStorageType,
                usmUserStatus,
--                usmMIBConformance,
--                usmMIBCompliances,
--                usmMIBCompliance,
--                usmMIBGroups,
--                usmMIBBasicGroup,
--                snmpUsmAesMIB,
--                snmpVacmMIB,
--                vacmMIBObjects,
                vacmContextName,
                vacmGroupName,
                vacmSecurityToGroupStorageType,
                vacmSecurityToGroupStatus,
                vacmGroupName,
                vacmAccessContextMatch,
                vacmAccessReadViewName,
                vacmAccessWriteViewName,
                vacmAccessNotifyViewName,
                vacmAccessStorageType,
                vacmAccessStatus,
--                vacmMIBViews,
                vacmViewSpinLock,
                vacmViewTreeFamilyMask,
                vacmViewTreeFamilyType,
                vacmViewTreeFamilyStorageType,
                vacmViewTreeFamilyStatus,
--                vacmMIBConformance,
--                vacmMIBCompliances,
--                vacmMIBCompliance,
--                vacmMIBGroups,
--                vacmBasicGroup,
                sysDescr,
                sysObjectID,
                sysUpTime,
                sysContact,
                sysName,
                sysLocation,
                sysServices,
                sysORLastChange,
                sysORID,
                sysORDescr,
                sysORUpTime,
                snmpTrapOID,
                snmpTrapEnterprise,
--                coldStart,
--                warmStart,
--                linkDown,
--                linkUp,
--                authenticationFailure,
                snmpSetSerialNo,
                snmpInPkts,
                snmpInBadVersions,
                snmpInBadCommunityNames,
                snmpInBadCommunityUses,
                snmpInASNParseErrs,
                snmpEnableAuthenTraps,
                snmpSilentDrops,
                snmpProxyDrops,
                tcpRtoAlgorithm,
                tcpRtoMin,
                tcpRtoMax,
                tcpMaxConn,
                tcpActiveOpens,
                tcpPassiveOpens,
                tcpAttemptFails,
                tcpEstabResets,
                tcpCurrEstab,
                tcpInSegs,
                tcpOutSegs,
                tcpRetransSegs,
                tcpInErrs,
                tcpOutRsts,
                tcpHCInSegs,
                tcpHCOutSegs,
                tcpConnectionState,
                tcpConnectionProcess,
                tcpListenerProcess,
                udpNoPorts,
                udpInErrors,
                udpEndpointProcess,
                udpHCInDatagrams,
                udpHCOutDatagrams
            }
    STATUS    current
    DESCRIPTION
        "(U//FOUO) Objects for the 'Management' document"
    ::= { haipeV030002Groups 3 }

--
-- Conformance levels required by the Management IS
--
hManagementCompliance MODULE-COMPLIANCE
    STATUS    current
    DESCRIPTION
        "(U//FOUO) Compliance levels for objects required by the
          'Management' document"
    MODULE -- this module
    MANDATORY-GROUPS { hManagementGroup }

    OBJECT		tcpAttemptFails
    MIN-ACCESS	read-only
    DESCRIPTION
        "(U//FOUO) Implementation of this object can be as low
         as read-only depending on which
         IS Objective or MIB desired requirements are
         not being met by the implementation."

    OBJECT		vacmSecurityToGroupStorageType
    MIN-ACCESS	read-write
    DESCRIPTION
        "(U//FOUO) Implementation of this object can be as low
         as read-write depending on which
         IS Objective or MIB desired requirements are
         not being met by the implementation."

    OBJECT		hTopologyTableCount
    MIN-ACCESS	read-only
    DESCRIPTION
        "(U//FOUO) Implementation of this object can be as low
         as read-only depending on which
         IS Objective or MIB desired requirements are
         not being met by the implementation."

--    OBJECT		snmpPrivProtocols
--    MIN-ACCESS	read-write
--    DESCRIPTION
--        "(U//FOUO) Implementation of this object can be as low
--         as read-write depending on which
--         IS Objective or MIB desired requirements are
--         not being met by the implementation."

    OBJECT		hFdsLoginName
    MIN-ACCESS	read-write
    DESCRIPTION
        "(U//FOUO) Implementation of this object can be as low
         as read-write depending on which
         IS Objective or MIB desired requirements are
         not being met by the implementation."

--    OBJECT		snmpTargetCompliances
--    MIN-ACCESS	read-write
--    DESCRIPTION
--        "(U//FOUO) Implementation of this object can be as low
--         as read-write depending on which
--         IS Objective or MIB desired requirements are
--         not being met by the implementation."

    OBJECT		hPPKEffectiveDate
    MIN-ACCESS	read-only
    DESCRIPTION
        "(U//FOUO) Implementation of this object can be as low
         as read-only depending on which
         IS Objective or MIB desired requirements are
         not being met by the implementation."

--    OBJECT		snmpTargetMIB
--    MIN-ACCESS	read-write
--    DESCRIPTION
--        "(U//FOUO) Implementation of this object can be as low
--         as read-write depending on which
--         IS Objective or MIB desired requirements are
--         not being met by the implementation."

    OBJECT		ipSystemStatsHCInOctets
    MIN-ACCESS	not-accessible
    DESCRIPTION
        "(U//FOUO) Implementation of this object can be as low
         as not-accessible depending on which
         IS Objective or MIB desired requirements are
         not being met by the implementation."

    OBJECT		tcpHCInSegs
    MIN-ACCESS	read-only
    DESCRIPTION
        "(U//FOUO) Implementation of this object can be as low
         as read-only depending on which
         IS Objective or MIB desired requirements are
         not being met by the implementation."

    OBJECT		ipv6IpDefaultHopLimit
    MIN-ACCESS	read-write
    DESCRIPTION
        "(U//FOUO) Implementation of this object can be as low
         as read-write depending on which
         IS Objective or MIB desired requirements are
         not being met by the implementation."

    OBJECT		hAudCfgLogThrottled
    MIN-ACCESS	read-only
    DESCRIPTION
        "(U//FOUO) Implementation of this object can be as low
         as read-only depending on which
         IS Objective or MIB desired requirements are
         not being met by the implementation."

    OBJECT		tcpConnectionProcess
    MIN-ACCESS	read-only
    DESCRIPTION
        "(U//FOUO) Implementation of this object can be as low
         as read-only depending on which
         IS Objective or MIB desired requirements are
         not being met by the implementation."

    OBJECT		ifOutDiscards
    MIN-ACCESS	not-accessible
    DESCRIPTION
        "(U//FOUO) Implementation of this object can be as low
         as not-accessible depending on which
         IS Objective or MIB desired requirements are
         not being met by the implementation."

    OBJECT		hIPhSelectorTableLastChanged
    MIN-ACCESS	read-only
    DESCRIPTION
        "(U//FOUO) Implementation of this object can be as low
         as read-only depending on which
         IS Objective or MIB desired requirements are
         not being met by the implementation."

    OBJECT		sysObjectID
    MIN-ACCESS	read-only
    DESCRIPTION
        "(U//FOUO) Implementation of this object can be as low
         as read-only depending on which
         IS Objective or MIB desired requirements are
         not being met by the implementation."

    OBJECT		hAudCfgNotifThrottleCfg
    MIN-ACCESS	read-only
    DESCRIPTION
        "(U//FOUO) Implementation of this object can be as low
         as read-only depending on which
         IS Objective or MIB desired requirements are
         not being met by the implementation."

    OBJECT		mgmdRouterInterfaceGroups
    MIN-ACCESS	not-accessible
    DESCRIPTION
        "(U//FOUO) Implementation of this object can be as low
         as not-accessible depending on which
         IS Objective or MIB desired requirements are
         not being met by the implementation."

--    OBJECT		snmpNotifyConformance
--    MIN-ACCESS	read-write
--    DESCRIPTION
--        "(U//FOUO) Implementation of this object can be as low
--         as read-write depending on which
--         IS Objective or MIB desired requirements are
--         not being met by the implementation."

    OBJECT		ipSystemStatsHCInForwDatagrams
    MIN-ACCESS	not-accessible
    DESCRIPTION
        "(U//FOUO) Implementation of this object can be as low
         as not-accessible depending on which
         IS Objective or MIB desired requirements are
         not being met by the implementation."

    OBJECT		hTPSAConnectionType
    MIN-ACCESS	read-write
    DESCRIPTION
        "(U//FOUO) Implementation of this object can be as low
         as read-write depending on which
         IS Objective or MIB desired requirements are
         not being met by the implementation."

    OBJECT		hIPhFFSADFBit
    MIN-ACCESS	read-write
    DESCRIPTION
        "(U//FOUO) Implementation of this object can be as low
         as read-write depending on which
         IS Objective or MIB desired requirements are
         not being met by the implementation."

    OBJECT		sysORID
    MIN-ACCESS	not-accessible
    DESCRIPTION
        "(U//FOUO) Implementation of this object can be as low
         as not-accessible depending on which
         IS Objective or MIB desired requirements are
         not being met by the implementation."

    OBJECT		hTPSADSCPValue
    MIN-ACCESS	read-write
    DESCRIPTION
        "(U//FOUO) Implementation of this object can be as low
         as read-write depending on which
         IS Objective or MIB desired requirements are
         not being met by the implementation."

--    OBJECT		snmpNotifyFullCompliance
--    MIN-ACCESS	read-write
--    DESCRIPTION
--        "(U//FOUO) Implementation of this object can be as low
--         as read-write depending on which
--         IS Objective or MIB desired requirements are
--         not being met by the implementation."

    OBJECT		mgmdRouterInterfaceStartupQueryInterval
    MIN-ACCESS	not-accessible
    DESCRIPTION
        "(U//FOUO) Implementation of this object can be as low
         as not-accessible depending on which
         IS Objective or MIB desired requirements are
         not being met by the implementation."

    OBJECT		ipv6InterfaceRetransmitTime
    MIN-ACCESS	read-only
    DESCRIPTION
        "(U//FOUO) Implementation of this object can be as low
         as read-only depending on which
         IS Objective or MIB desired requirements are
         not being met by the implementation."

    OBJECT		hPPKRegister
    MIN-ACCESS	not-accessible
    DESCRIPTION
        "(U//FOUO) Implementation of this object can be as low
         as not-accessible depending on which
         IS Objective or MIB desired requirements are
         not being met by the implementation."

    OBJECT		hTPSAProcessFlowlabel
    MIN-ACCESS	not-accessible
    DESCRIPTION
        "(U//FOUO) Implementation of this object can be as low
         as not-accessible depending on which
         IS Objective or MIB desired requirements are
         not being met by the implementation."

--    OBJECT		snmpNotifyFilterGroup
--    MIN-ACCESS	read-write
--    DESCRIPTION
--        "(U//FOUO) Implementation of this object can be as low
--         as read-write depending on which
--         IS Objective or MIB desired requirements are
--         not being met by the implementation."

--    OBJECT		usmDESPrivProtocol
--    MIN-ACCESS	read-write
--    DESCRIPTION
--        "(U//FOUO) Implementation of this object can be as low
--         as read-write depending on which
--         IS Objective or MIB desired requirements are
--         not being met by the implementation."

--    OBJECT		vacmMIBConformance
--    MIN-ACCESS	read-write
--    DESCRIPTION
--        "(U//FOUO) Implementation of this object can be as low
--         as read-write depending on which
--         IS Objective or MIB desired requirements are
--         not being met by the implementation."

--    OBJECT		snmpTargetCommandResponderCompliance
--    MIN-ACCESS	read-write
--    DESCRIPTION
--        "(U//FOUO) Implementation of this object can be as low
--         as read-write depending on which
--         IS Objective or MIB desired requirements are
--         not being met by the implementation."

    OBJECT		hIfv6HaipeTableCount
    MIN-ACCESS	read-only
    DESCRIPTION
        "(U//FOUO) Implementation of this object can be as low
         as read-only depending on which
         IS Objective or MIB desired requirements are
         not being met by the implementation."

    OBJECT		ipSystemStatsInForwDatagrams
    MIN-ACCESS	not-accessible
    DESCRIPTION
        "(U//FOUO) Implementation of this object can be as low
         as not-accessible depending on which
         IS Objective or MIB desired requirements are
         not being met by the implementation."

    OBJECT		hPPKEKKeyType
    MIN-ACCESS	read-write
    DESCRIPTION
        "(U//FOUO) Implementation of this object can be as low
         as read-write depending on which
         IS Objective or MIB desired requirements are
         not being met by the implementation."

    OBJECT		ifHCInBroadcastPkts
    MIN-ACCESS	read-only
    DESCRIPTION
        "(U//FOUO) Implementation of this object can be as low
         as read-only depending on which
         IS Objective or MIB desired requirements are
         not being met by the implementation."

    OBJECT		hTPSACryptoBlockSize
    MIN-ACCESS	read-write
    DESCRIPTION
        "(U//FOUO) Implementation of this object can be as low
         as read-write depending on which
         IS Objective or MIB desired requirements are
         not being met by the implementation."

    OBJECT		hTPSADirection
    MIN-ACCESS	read-write
    DESCRIPTION
        "(U//FOUO) Implementation of this object can be as low
         as read-write depending on which
         IS Objective or MIB desired requirements are
         not being met by the implementation."

    OBJECT		snmpInvalidMsgs
    MIN-ACCESS	read-only
    DESCRIPTION
        "(U//FOUO) Implementation of this object can be as low
         as read-only depending on which
         IS Objective or MIB desired requirements are
         not being met by the implementation."

    OBJECT		nlmLogVariableCounter32Val
    MIN-ACCESS	read-only
    DESCRIPTION
        "(U//FOUO) Implementation of this object can be as low
         as read-only depending on which
         IS Objective or MIB desired requirements are
         not being met by the implementation."

    OBJECT		hIPhFFSATableCount
    MIN-ACCESS	read-only
    DESCRIPTION
        "(U//FOUO) Implementation of this object can be as low
         as read-only depending on which
         IS Objective or MIB desired requirements are
         not being met by the implementation."

    OBJECT		nlmLogEngineTAddress
    MIN-ACCESS	read-only
    DESCRIPTION
        "(U//FOUO) Implementation of this object can be as low
         as read-only depending on which
         IS Objective or MIB desired requirements are
         not being met by the implementation."

    OBJECT		hSecurityAuthority
    MIN-ACCESS	not-accessible
    DESCRIPTION
        "(U//FOUO) Implementation of this object can be as low
         as not-accessible depending on which
         IS Objective or MIB desired requirements are
         not being met by the implementation."

    OBJECT		hFdsPassword
    MIN-ACCESS	read-write
    DESCRIPTION
        "(U//FOUO) Implementation of this object can be as low
         as read-write depending on which
         IS Objective or MIB desired requirements are
         not being met by the implementation."

    OBJECT		hiaaType
    MIN-ACCESS	read-write
    DESCRIPTION
        "(U//FOUO) Implementation of this object can be as low
         as read-write depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hBatteryLevelWarningPercentage
    MIN-ACCESS	read-only
    DESCRIPTION
        "(U//FOUO) Implementation of this object can be as low
         as read-only depending on which
         IS Objective or MIB desired requirements are
         not being met by the implementation."

    OBJECT		usmUserAuthProtocol
    MIN-ACCESS	read-write
    DESCRIPTION
        "(U//FOUO) Implementation of this object can be as low
         as read-write depending on which
         IS Objective or MIB desired requirements are
         not being met by the implementation."

    OBJECT		hTPiDestinationAddressType
    MIN-ACCESS	not-accessible
    DESCRIPTION
        "(U//FOUO) Implementation of this object can be as low
         as not-accessible depending on which
         IS Objective or MIB desired requirements are
         not being met by the implementation."

    OBJECT		snmpTrapOID
    MIN-ACCESS	accessible-for-notify
    DESCRIPTION
        "(U//FOUO) Implementation of this object can be as low
         as accessible-for-notify depending on which
         IS Objective or MIB desired requirements are
         not being met by the implementation."

    OBJECT		ipSystemStatsOutMcastOctets
    MIN-ACCESS	not-accessible
    DESCRIPTION
        "(U//FOUO) Implementation of this object can be as low
         as not-accessible depending on which
         IS Objective or MIB desired requirements are
         not being met by the implementation."

--    OBJECT		snmpTargetCommandResponderGroup
--    MIN-ACCESS	read-write
--    DESCRIPTION
--        "(U//FOUO) Implementation of this object can be as low
--         as read-write depending on which
--         IS Objective or MIB desired requirements are
--         not being met by the implementation."

    OBJECT		hTPSASelectorNextHeaderOpt1Start
    MIN-ACCESS	not-accessible
    DESCRIPTION
        "(U//FOUO) Implementation of this object can be as low
         as not-accessible depending on which
         IS Objective or MIB desired requirements are
         not being met by the implementation."

    OBJECT		hLocalCKListRowStatus
    MIN-ACCESS	read-write
    DESCRIPTION
        "(U//FOUO) Implementation of this object can be as low
         as read-write depending on which
         IS Objective or MIB desired requirements are
         not being met by the implementation."

    OBJECT		tcpEstabResets
    MIN-ACCESS	read-only
    DESCRIPTION
        "(U//FOUO) Implementation of this object can be as low
         as read-only depending on which
         IS Objective or MIB desired requirements are
         not being met by the implementation."

    OBJECT		snmpEnableAuthenTraps
    MIN-ACCESS	read-write
    DESCRIPTION
        "(U//FOUO) Implementation of this object can be as low
         as read-write depending on which
         IS Objective or MIB desired requirements are
         not being met by the implementation."

--    OBJECT		snmpFrameworkMIB
--    MIN-ACCESS	read-write
--    DESCRIPTION
--        "(U//FOUO) Implementation of this object can be as low
--         as read-write depending on which
--         IS Objective or MIB desired requirements are
--         not being met by the implementation."

    OBJECT		ipSystemStatsHCInReceives
    MIN-ACCESS	not-accessible
    DESCRIPTION
        "(U//FOUO) Implementation of this object can be as low
         as not-accessible depending on which
         IS Objective or MIB desired requirements are
         not being met by the implementation."

    OBJECT		ipIfStatsOutMcastPkts
    MIN-ACCESS	not-accessible
    DESCRIPTION
        "(U//FOUO) Implementation of this object can be as low
         as not-accessible depending on which
         IS Objective or MIB desired requirements are
         not being met by the implementation."

    OBJECT		ipSystemStatsRefreshRate
    MIN-ACCESS	not-accessible
    DESCRIPTION
        "(U//FOUO) Implementation of this object can be as low
         as not-accessible depending on which
         IS Objective or MIB desired requirements are
         not being met by the implementation."

    OBJECT		nlmLogContextName
    MIN-ACCESS	read-only
    DESCRIPTION
        "(U//FOUO) Implementation of this object can be as low
         as read-only depending on which
         IS Objective or MIB desired requirements are
         not being met by the implementation."

    OBJECT		hBatteryOperStatus
    MIN-ACCESS	read-only
    DESCRIPTION
        "(U//FOUO) Implementation of this object can be as low
         as read-only depending on which
         IS Objective or MIB desired requirements are
         not being met by the implementation."

    OBJECT		ipSystemStatsOutRequests
    MIN-ACCESS	not-accessible
    DESCRIPTION
        "(U//FOUO) Implementation of this object can be as low
         as not-accessible depending on which
         IS Objective or MIB desired requirements are
         not being met by the implementation."

    OBJECT		snmpNotifyFilterProfileRowStatus
    MIN-ACCESS	read-write
    DESCRIPTION
        "(U//FOUO) Implementation of this object can be as low
         as read-write depending on which
         IS Objective or MIB desired requirements are
         not being met by the implementation."

    OBJECT		hPPKLastChanged
    MIN-ACCESS	read-only
    DESCRIPTION
        "(U//FOUO) Implementation of this object can be as low
         as read-only depending on which
         IS Objective or MIB desired requirements are
         not being met by the implementation."

    OBJECT		snmpSilentDrops
    MIN-ACCESS	not-accessible
    DESCRIPTION
        "(U//FOUO) Implementation of this object can be as low
         as not-accessible depending on which
         IS Objective or MIB desired requirements are
         not being met by the implementation."

--    OBJECT		snmpMPDAdmin
--    MIN-ACCESS	read-write
--    DESCRIPTION
--        "(U//FOUO) Implementation of this object can be as low
--         as read-write depending on which
--         IS Objective or MIB desired requirements are
--         not being met by the implementation."

--    OBJECT		snmpMPDMIBConformance
--    MIN-ACCESS	read-write
--    DESCRIPTION
--        "(U//FOUO) Implementation of this object can be as low
--         as read-write depending on which
--         IS Objective or MIB desired requirements are
--         not being met by the implementation."

    OBJECT		nlmLogVariableOidVal
    MIN-ACCESS	read-only
    DESCRIPTION
        "(U//FOUO) Implementation of this object can be as low
         as read-only depending on which
         IS Objective or MIB desired requirements are
         not being met by the implementation."

    OBJECT		hIPhFFSAFFUniversalEdition
    MIN-ACCESS	read-write
    DESCRIPTION
        "(U//FOUO) Implementation of this object can be as low
         as read-write depending on which
         IS Objective or MIB desired requirements are
         not being met by the implementation."

    OBJECT		hIPhFFSADSCP
    MIN-ACCESS	read-write
    DESCRIPTION
        "(U//FOUO) Implementation of this object can be as low
         as read-write depending on which
         IS Objective or MIB desired requirements are
         not being met by the implementation."

--    OBJECT		usmMIBConformance
--    MIN-ACCESS	read-write
--    DESCRIPTION
--        "(U//FOUO) Implementation of this object can be as low
--         as read-write depending on which
--         IS Objective or MIB desired requirements are
--         not being met by the implementation."

    OBJECT		snmpTargetAddrRetryCount
    MIN-ACCESS	read-write
    DESCRIPTION
        "(U//FOUO) Implementation of this object can be as low
         as read-write depending on which
         IS Objective or MIB desired requirements are
         not being met by the implementation."

    OBJECT		ipIfStatsHCOutBcastPkts
    MIN-ACCESS	read-only
    DESCRIPTION
        "(U//FOUO) Implementation of this object can be as low
         as read-only depending on which
         IS Objective or MIB desired requirements are
         not being met by the implementation."

    OBJECT		snmpTargetAddrStorageType
    MIN-ACCESS	read-write
    DESCRIPTION
        "(U//FOUO) Implementation of this object can be as low
         as read-write depending on which
         IS Objective or MIB desired requirements are
         not being met by the implementation."

    OBJECT		hTPSASelectorNextHeaderStart
    MIN-ACCESS	not-accessible
    DESCRIPTION
        "(U//FOUO) Implementation of this object can be as low
         as not-accessible depending on which
         IS Objective or MIB desired requirements are
         not being met by the implementation."

    OBJECT		ipIfStatsHCOutOctets
    MIN-ACCESS	read-only
    DESCRIPTION
        "(U//FOUO) Implementation of this object can be as low
         as read-only depending on which
         IS Objective or MIB desired requirements are
         not being met by the implementation."

    OBJECT		snmpTargetParamsSecurityModel
    MIN-ACCESS	read-write
    DESCRIPTION
        "(U//FOUO) Implementation of this object can be as low
         as read-write depending on which
         IS Objective or MIB desired requirements are
         not being met by the implementation."

    OBJECT		usmStatsWrongDigests
    MIN-ACCESS	read-only
    DESCRIPTION
        "(U//FOUO) Implementation of this object can be as low
         as read-only depending on which
         IS Objective or MIB desired requirements are
         not being met by the implementation."

    OBJECT		ipIfStatsHCInDelivers
    MIN-ACCESS	read-only
    DESCRIPTION
        "(U//FOUO) Implementation of this object can be as low
         as read-only depending on which
         IS Objective or MIB desired requirements are
         not being met by the implementation."

    OBJECT		ifOutMulticastPkts
    MIN-ACCESS	not-accessible
    DESCRIPTION
        "(U//FOUO) Implementation of this object can be as low
         as not-accessible depending on which
         IS Objective or MIB desired requirements are
         not being met by the implementation."

    OBJECT		ipNetToPhysicalType
    MIN-ACCESS	read-only
    DESCRIPTION
        "(U//FOUO) Implementation of this object can be as low
         as read-only depending on which
         IS Objective or MIB desired requirements are
         not being met by the implementation."

    OBJECT		hIPhFFSATransformsName
    MIN-ACCESS	read-write
    DESCRIPTION
        "(U//FOUO) Implementation of this object can be as low
         as read-write depending on which
         IS Objective or MIB desired requirements are
         not being met by the implementation."

    OBJECT		ipIfStatsTableLastChange
    MIN-ACCESS	not-accessible
    DESCRIPTION
        "(U//FOUO) Implementation of this object can be as low
         as not-accessible depending on which
         IS Objective or MIB desired requirements are
         not being met by the implementation."

    OBJECT		hAudCfgNotifEnabled
    MIN-ACCESS	read-only
    DESCRIPTION
        "(U//FOUO) Implementation of this object can be as low
         as read-only depending on which
         IS Objective or MIB desired requirements are
         not being met by the implementation."

    OBJECT		hLocalCKListKMIDBegin
    MIN-ACCESS	read-only
    DESCRIPTION
        "(U//FOUO) Implementation of this object can be as low
         as read-only depending on which
         IS Objective or MIB desired requirements are
         not being met by the implementation."

    OBJECT		snmpTargetParamsMPModel
    MIN-ACCESS	read-write
    DESCRIPTION
        "(U//FOUO) Implementation of this object can be as low
         as read-write depending on which
         IS Objective or MIB desired requirements are
         not being met by the implementation."

    OBJECT		hAudCfgThrottlingEnabled
    MIN-ACCESS	read-only
    DESCRIPTION
        "(U//FOUO) Implementation of this object can be as low
         as read-only depending on which
         IS Objective or MIB desired requirements are
         not being met by the implementation."

    OBJECT		snmpSetSerialNo
    MIN-ACCESS	read-write
    DESCRIPTION
        "(U//FOUO) Implementation of this object can be as low
         as read-write depending on which
         IS Objective or MIB desired requirements are
         not being met by the implementation."

    OBJECT		hTPSASelectorNextHeaderOpt2Start
    MIN-ACCESS	not-accessible
    DESCRIPTION
        "(U//FOUO) Implementation of this object can be as low
         as not-accessible depending on which
         IS Objective or MIB desired requirements are
         not being met by the implementation."

    OBJECT		ipIfStatsHCInForwDatagrams
    MIN-ACCESS	read-only
    DESCRIPTION
        "(U//FOUO) Implementation of this object can be as low
         as read-only depending on which
         IS Objective or MIB desired requirements are
         not being met by the implementation."

--    OBJECT		hGenericAuditNotification
--    MIN-ACCESS	not-accessible
--    DESCRIPTION
--        "(U//FOUO) Implementation of this object can be as low
--         as not-accessible depending on which
--         IS Objective or MIB desired requirements are
--         not being met by the implementation."

    OBJECT		ipv6InterfaceReasmMaxSize
    MIN-ACCESS	read-only
    DESCRIPTION
        "(U//FOUO) Implementation of this object can be as low
         as read-only depending on which
         IS Objective or MIB desired requirements are
         not being met by the implementation."

    OBJECT		hTPSAECN
    MIN-ACCESS	read-write
    DESCRIPTION
        "(U//FOUO) Implementation of this object can be as low
         as read-write depending on which
         IS Objective or MIB desired requirements are
         not being met by the implementation."

--    OBJECT		ipv4InterfaceTable
--    MIN-ACCESS	read-only
--    DESCRIPTION
--        "(U//FOUO) Implementation of this object can be as low
--         as read-only depending on which
--         IS Objective or MIB desired requirements are
--         not being met by the implementation."

--    OBJECT		snmpFrameworkAdmin
--    MIN-ACCESS	read-write
--    DESCRIPTION
--        "(U//FOUO) Implementation of this object can be as low
--         as read-write depending on which
--         IS Objective or MIB desired requirements are
--         not being met by the implementation."

    OBJECT		nlmLogEngineID
    MIN-ACCESS	read-only
    DESCRIPTION
        "(U//FOUO) Implementation of this object can be as low
         as read-only depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hFirmwareDownloadOperStatus
    MIN-ACCESS	read-only
    DESCRIPTION
        "(U//FOUO) Implementation of this object can be as low
         as read-only depending on which
         IS Objective or MIB desired requirements are
         not being met by the implementation."

    OBJECT		nlmStatsLogNotificationsLogged
    MIN-ACCESS	not-accessible
    DESCRIPTION
        "(U//FOUO) Implementation of this object can be as low
         as not-accessible depending on which
         IS Objective or MIB desired requirements are
         not being met by the implementation."

    OBJECT		nlmConfigGlobalEntryLimit
    MIN-ACCESS	read-only
    DESCRIPTION
        "(U//FOUO) Implementation of this object can be as low
         as read-only depending on which
         IS Objective or MIB desired requirements are
         not being met by the implementation."

    OBJECT		ipNetToPhysicalLastUpdated
    MIN-ACCESS	read-only
    DESCRIPTION
        "(U//FOUO) Implementation of this object can be as low
         as read-only depending on which
         IS Objective or MIB desired requirements are
         not being met by the implementation."

    OBJECT		hIPhSelectorRowStatus
    MIN-ACCESS	read-write
    DESCRIPTION
        "(U//FOUO) Implementation of this object can be as low
         as read-write depending on which
         IS Objective or MIB desired requirements are
         not being met by the implementation."

--    OBJECT		warmStart
--    MIN-ACCESS	accessible-for-notify
--    DESCRIPTION
--        "(U//FOUO) Implementation of this object can be as low
--         as accessible-for-notify depending on which
--         IS Objective or MIB desired requirements are
--         not being met by the implementation."

    OBJECT		hIPhFFSAPDUNEnabled
    MIN-ACCESS	read-write
    DESCRIPTION
        "(U//FOUO) Implementation of this object can be as low
         as read-write depending on which
         IS Objective or MIB desired requirements are
         not being met by the implementation."

    OBJECT		hIfv6Side
    MIN-ACCESS	read-only
    DESCRIPTION
        "(U//FOUO) Implementation of this object can be as low
         as read-only depending on which
         IS Objective or MIB desired requirements are
         not being met by the implementation."

    OBJECT		ipSystemStatsInDelivers
    MIN-ACCESS	not-accessible
    DESCRIPTION
        "(U//FOUO) Implementation of this object can be as low
         as not-accessible depending on which
         IS Objective or MIB desired requirements are
         not being met by the implementation."

    OBJECT		ifOutBroadcastPkts
    MIN-ACCESS	not-accessible
    DESCRIPTION
        "(U//FOUO) Implementation of this object can be as low
         as not-accessible depending on which
         IS Objective or MIB desired requirements are
         not being met by the implementation."

    OBJECT		hIPhFFSATableLastChanged
    MIN-ACCESS	read-only
    DESCRIPTION
        "(U//FOUO) Implementation of this object can be as low
         as read-only depending on which
         IS Objective or MIB desired requirements are
         not being met by the implementation."

--    OBJECT		vacmMIBCompliance
--    MIN-ACCESS	read-write
--    DESCRIPTION
--        "(U//FOUO) Implementation of this object can be as low
--         as read-write depending on which
--         IS Objective or MIB desired requirements are
--         not being met by the implementation."

    OBJECT		hNotificationLogCapacityPercentage
    MIN-ACCESS	read-only
    DESCRIPTION
        "(U//FOUO) Implementation of this object can be as low
         as read-only depending on which
         IS Objective or MIB desired requirements are
         not being met by the implementation."

    OBJECT		hHMISpinLock
    MIN-ACCESS	not-accessible
    DESCRIPTION
        "(U//FOUO) Implementation of this object can be as low
         as not-accessible depending on which
         IS Objective or MIB desired requirements are
         not being met by the implementation."

    OBJECT		hIPhRuleAction
    MIN-ACCESS	read-write
    DESCRIPTION
        "(U//FOUO) Implementation of this object can be as low
         as read-write depending on which
         IS Objective or MIB desired requirements are
         not being met by the implementation."

    OBJECT		snmpNotifyTag
    MIN-ACCESS	read-write
    DESCRIPTION
        "(U//FOUO) Implementation of this object can be as low
         as read-write depending on which
         IS Objective or MIB desired requirements are
         not being met by the implementation."

    OBJECT		mgmdHostInterfaceStatus
    MIN-ACCESS	read-write
    DESCRIPTION
        "(U//FOUO) Implementation of this object can be as low
         as read-write depending on which
         IS Objective or MIB desired requirements are
         not being met by the implementation."

    OBJECT		hFdsPriority
    MIN-ACCESS	read-write
    DESCRIPTION
        "(U//FOUO) Implementation of this object can be as low
         as read-write depending on which
         IS Objective or MIB desired requirements are
         not being met by the implementation."

    OBJECT		ipIfStatsHCInMcastPkts
    MIN-ACCESS	read-only
    DESCRIPTION
        "(U//FOUO) Implementation of this object can be as low
         as read-only depending on which
         IS Objective or MIB desired requirements are
         not being met by the implementation."

--    OBJECT		vacmBasicGroup
--    MIN-ACCESS	read-write
--    DESCRIPTION
--        "(U//FOUO) Implementation of this object can be as low
--         as read-write depending on which
--         IS Objective or MIB desired requirements are
--         not being met by the implementation."

    OBJECT		nlmLogVariableInteger32Val
    MIN-ACCESS	read-only
    DESCRIPTION
        "(U//FOUO) Implementation of this object can be as low
         as read-only depending on which
         IS Objective or MIB desired requirements are
         not being met by the implementation."

    OBJECT		ipSystemStatsHCOutMcastOctets
    MIN-ACCESS	not-accessible
    DESCRIPTION
        "(U//FOUO) Implementation of this object can be as low
         as not-accessible depending on which
         IS Objective or MIB desired requirements are
         not being met by the implementation."

    OBJECT		inetCidrRouteDiscards
    MIN-ACCESS	read-only
    DESCRIPTION
        "(U//FOUO) Implementation of this object can be as low
         as read-only depending on which
         IS Objective or MIB desired requirements are
         not being met by the implementation."

    OBJECT		hTPSAPPK
    MIN-ACCESS	read-write
    DESCRIPTION
        "(U//FOUO) Implementation of this object can be as low
         as read-write depending on which
         IS Objective or MIB desired requirements are
         not being met by the implementation."

    OBJECT		ipSystemStatsInBcastPkts
    MIN-ACCESS	not-accessible
    DESCRIPTION
        "(U//FOUO) Implementation of this object can be as low
         as not-accessible depending on which
         IS Objective or MIB desired requirements are
         not being met by the implementation."

    OBJECT		haipeSanitizeDevice
    MIN-ACCESS	read-write
    DESCRIPTION
        "(U//FOUO) Implementation of this object can be as low
         as read-write depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

--    OBJECT		snmpMPDMIB
--    MIN-ACCESS	read-write
--    DESCRIPTION
--        "(U//FOUO) Implementation of this object can be as low
--         as read-write depending on which
--         IS Objective or MIB desired requirements are
--         not being met by the implementation."

    OBJECT		nlmStatsGlobalNotificationsBumped
    MIN-ACCESS	not-accessible
    DESCRIPTION
        "(U//FOUO) Implementation of this object can be as low
         as not-accessible depending on which
         IS Objective or MIB desired requirements are
         not being met by the implementation."

    OBJECT		snmpTargetAddrTAddress
    MIN-ACCESS	read-write
    DESCRIPTION
        "(U//FOUO) Implementation of this object can be as low
         as read-write depending on which
         IS Objective or MIB desired requirements are
         not being met by the implementation."

    OBJECT		mgmdRouterCacheUpTime
    MIN-ACCESS	not-accessible
    DESCRIPTION
        "(U//FOUO) Implementation of this object can be as low
         as not-accessible depending on which
         IS Objective or MIB desired requirements are
         not being met by the implementation."

    OBJECT		ifInUcastPkts
    MIN-ACCESS	not-accessible
    DESCRIPTION
        "(U//FOUO) Implementation of this object can be as low
         as not-accessible depending on which
         IS Objective or MIB desired requirements are
         not being met by the implementation."

--    OBJECT		snmpTargetObjects
--    MIN-ACCESS	read-write
--    DESCRIPTION
--        "(U//FOUO) Implementation of this object can be as low
--         as read-write depending on which
--         IS Objective or MIB desired requirements are
--         not being met by the implementation."

    OBJECT		hAudThrottleCfgName
    MIN-ACCESS	read-only
    DESCRIPTION
        "(U//FOUO) Implementation of this object can be as low
         as read-only depending on which
         IS Objective or MIB desired requirements are
         not being met by the implementation."

    OBJECT		hLocalCKListUniversalEdition
    MIN-ACCESS	read-only
    DESCRIPTION
        "(U//FOUO) Implementation of this object can be as low
         as read-only depending on which
         IS Objective or MIB desired requirements are
         not being met by the implementation."

    OBJECT		mgmdRouterInterfaceJoins
    MIN-ACCESS	not-accessible
    DESCRIPTION
        "(U//FOUO) Implementation of this object can be as low
         as not-accessible depending on which
         IS Objective or MIB desired requirements are
         not being met by the implementation."

    OBJECT		hAudCfgRowStatus
    MIN-ACCESS	read-only
    DESCRIPTION
        "(U//FOUO) Implementation of this object can be as low
         as read-only depending on which
         IS Objective or MIB desired requirements are
         not being met by the implementation."

--    OBJECT		linkDown
--    MIN-ACCESS	accessible-for-notify
--    DESCRIPTION
--        "(U//FOUO) Implementation of this object can be as low
--         as accessible-for-notify depending on which
--         IS Objective or MIB desired requirements are
--         not being met by the implementation."

    OBJECT		snmpNotifyFilterType
    MIN-ACCESS	read-write
    DESCRIPTION
        "(U//FOUO) Implementation of this object can be as low
         as read-write depending on which
         IS Objective or MIB desired requirements are
         not being met by the implementation."

    OBJECT		vacmViewTreeFamilyType
    MIN-ACCESS	read-write
    DESCRIPTION
        "(U//FOUO) Implementation of this object can be as low
         as read-write depending on which
         IS Objective or MIB desired requirements are
         not being met by the implementation."

    OBJECT		ipIfStatsInAddrErrors
    MIN-ACCESS	read-only
    DESCRIPTION
        "(U//FOUO) Implementation of this object can be as low
         as read-only depending on which
         IS Objective or MIB desired requirements are
         not being met by the implementation."

--    OBJECT		authenticationFailure
--    MIN-ACCESS	accessible-for-notify
--    DESCRIPTION
--        "(U//FOUO) Implementation of this object can be as low
--         as accessible-for-notify depending on which
--         IS Objective or MIB desired requirements are
--         not being met by the implementation."

    OBJECT		ipSystemStatsDiscontinuityTime
    MIN-ACCESS	not-accessible
    DESCRIPTION
        "(U//FOUO) Implementation of this object can be as low
         as not-accessible depending on which
         IS Objective or MIB desired requirements are
         not being met by the implementation."

    OBJECT		hLocalCKListDate
    MIN-ACCESS	read-only
    DESCRIPTION
        "(U//FOUO) Implementation of this object can be as low
         as read-only depending on which
         IS Objective or MIB desired requirements are
         not being met by the implementation."

    OBJECT		hdvVersion
    MIN-ACCESS	read-only
    DESCRIPTION
        "(U//FOUO) Implementation of this object can be as low
         as read-only depending on which
         IS Objective or MIB desired requirements are
         not being met by the implementation."

    OBJECT		hIfv6LastChanged
    MIN-ACCESS	read-only
    DESCRIPTION
        "(U//FOUO) Implementation of this object can be as low
         as read-only depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."

    OBJECT		hPPKChainTableCount
    MIN-ACCESS	read-only
    DESCRIPTION
        "(U//FOUO) Implementation of this object can be as low
         as read-only depending on which
         IS Objective or MIB desired requirements are
         not being met by the implementation."

    OBJECT		vacmContextName
    MIN-ACCESS	read-only
    DESCRIPTION
        "(U//FOUO) Implementation of this object can be as low
         as read-only depending on which
         IS Objective or MIB desired requirements are
         not being met by the implementation."

    OBJECT		hBatteryChangeDate
    MIN-ACCESS	read-only
    DESCRIPTION
        "(U//FOUO) Implementation of this object can be as low
         as read-only depending on which
         IS Objective or MIB desired requirements are
         not being met by the implementation."

--    OBJECT		snmpNotificationMIB
--    MIN-ACCESS	read-write
--    DESCRIPTION
--        "(U//FOUO) Implementation of this object can be as low
--         as read-write depending on which
--         IS Objective or MIB desired requirements are
--         not being met by the implementation."

    OBJECT		ipIfStatsHCOutMcastPkts
    MIN-ACCESS	read-only
    DESCRIPTION
        "(U//FOUO) Implementation of this object can be as low
         as read-only depending on which
         IS Objective or MIB desired requirements are
         not being met by the implementation."

    OBJECT		ifInDiscards
    MIN-ACCESS	not-accessible
    DESCRIPTION
        "(U//FOUO) Implementation of this object can be as low
         as not-accessible depending on which
         IS Objective or MIB desired requirements are
         not being met by the implementation."

    OBJECT		udpHCInDatagrams
    MIN-ACCESS	read-only
    DESCRIPTION
        "(U//FOUO) Implementation of this object can be as low
         as read-only depending on which
         IS Objective or MIB desired requirements are
         not being met by the implementation."

    OBJECT		ifOutNUcastPkts
    MIN-ACCESS	not-accessible
    DESCRIPTION
        "(U//FOUO) Implementation of this object can be as low
         as not-accessible depending on which
         IS Objective or MIB desired requirements are
         not being met by the implementation."

    OBJECT		ipIfStatsRefreshRate
    MIN-ACCESS	read-only
    DESCRIPTION
        "(U//FOUO) Implementation of this object can be as low
         as read-only depending on which
         IS Objective or MIB desired requirements are
         not being met by the implementation."

    OBJECT		snmpTargetAddrParams
    MIN-ACCESS	read-write
    DESCRIPTION
        "(U//FOUO) Implementation of this object can be as low
         as read-write depending on which
         IS Objective or MIB desired requirements are
         not being met by the implementation."

    OBJECT		ifHCOutOctets
    MIN-ACCESS	read-only
    DESCRIPTION
        "(U//FOUO) Implementation of this object can be as low
         as read-only depending on which
         IS Objective or MIB desired requirements are
         not being met by the implementation."

--    OBJECT		coldStart
--    MIN-ACCESS	accessible-for-notify
--    DESCRIPTION
--        "(U//FOUO) Implementation of this object can be as low
--         as accessible-for-notify depending on which
--         IS Objective or MIB desired requirements are
--         not being met by the implementation."

    OBJECT		snmpNotifyFilterStorageType
    MIN-ACCESS	read-write
    DESCRIPTION
        "(U//FOUO) Implementation of this object can be as low
         as read-write depending on which
         IS Objective or MIB desired requirements are
         not being met by the implementation."

    OBJECT		ipIfStatsOutTransmits
    MIN-ACCESS	not-accessible
    DESCRIPTION
        "(U//FOUO) Implementation of this object can be as low
         as not-accessible depending on which
         IS Objective or MIB desired requirements are
         not being met by the implementation."

--    OBJECT		linkUp
--    MIN-ACCESS	accessible-for-notify
--    DESCRIPTION
--        "(U//FOUO) Implementation of this object can be as low
--         as accessible-for-notify depending on which
--         IS Objective or MIB desired requirements are
--         not being met by the implementation."

    OBJECT		snmpEngineMaxMessageSize
    MIN-ACCESS	read-only
    DESCRIPTION
        "(U//FOUO) Implementation of this object can be as low
         as read-only depending on which
         IS Objective or MIB desired requirements are
         not being met by the implementation."

--    OBJECT		hAudNotificationLogFull
--    MIN-ACCESS	accessible-for-notify
--    DESCRIPTION
--        "(U//FOUO) Implementation of this object can be as low
--         as accessible-for-notify depending on which
--         IS Objective or MIB desired requirements are
--         not being met by the implementation."

    OBJECT		nlmLogDateAndTime
    MIN-ACCESS	read-only
    DESCRIPTION
        "(U//FOUO) Implementation of this object can be as low
         as read-only depending on which
         IS Objective or MIB desired requirements are
         not being met by the implementation."

    OBJECT		ifAlias
    MIN-ACCESS	read-only
    DESCRIPTION
        "(U//FOUO) Implementation of this object can be as low
         as read-only depending on which
         IS Objective or MIB desired requirements are
         not being met by the implementation."

    OBJECT		ifOutUcastPkts
    MIN-ACCESS	not-accessible
    DESCRIPTION
        "(U//FOUO) Implementation of this object can be as low
         as not-accessible depending on which
         IS Objective or MIB desired requirements are
         not being met by the implementation."

--    OBJECT		usmStats
--    MIN-ACCESS	read-write
--    DESCRIPTION
--        "(U//FOUO) Implementation of this object can be as low
--         as read-write depending on which
--         IS Objective or MIB desired requirements are
--         not being met by the implementation."

    OBJECT		mgmdRouterCacheVersion1HostTimer
    MIN-ACCESS	not-accessible
    DESCRIPTION
        "(U//FOUO) Implementation of this object can be as low
         as not-accessible depending on which
         IS Objective or MIB desired requirements are
         not being met by the implementation."

    OBJECT		hPPKChainPPK
    MIN-ACCESS	read-write
    DESCRIPTION
        "(U//FOUO) Implementation of this object can be as low
         as read-write depending on which
         IS Objective or MIB desired requirements are
         not being met by the implementation."

    OBJECT		ipv6InterfaceForwarding
    MIN-ACCESS	read-only
    DESCRIPTION
        "(U//FOUO) Implementation of this object can be as low
         as read-only depending on which
         IS Objective or MIB desired requirements are
         not being met by the implementation."

    OBJECT		tcpMaxConn
    MIN-ACCESS	read-only
    DESCRIPTION
        "(U//FOUO) Implementation of this object can be as low
         as read-only depending on which
         IS Objective or MIB desired requirements are
         not being met by the implementation."

    OBJECT		ifLastChange
    MIN-ACCESS	read-only
    DESCRIPTION
        "(U//FOUO) Implementation of this object can be as low
         as read-only depending on which
         IS Objective or MIB desired requirements are
         not being met by the implementation."

    OBJECT		ifInErrors
    MIN-ACCESS	not-accessible
    DESCRIPTION
        "(U//FOUO) Implementation of this object can be as low
         as not-accessible depending on which
         IS Objective or MIB desired requirements are
         not being met by the implementation."

    OBJECT		ipIfStatsOutRequests
    MIN-ACCESS	not-accessible
    DESCRIPTION
        "(U//FOUO) Implementation of this object can be as low
         as not-accessible depending on which
         IS Objective or MIB desired requirements are
         not being met by the implementation."

    OBJECT		hAudThrottleConfigTableCount
    MIN-ACCESS	read-only
    DESCRIPTION
        "(U//FOUO) Implementation of this object can be as low
         as read-only depending on which
         IS Objective or MIB desired requirements are
         not being met by the implementation."

    OBJECT		hdvName
    MIN-ACCESS	read-only
    DESCRIPTION
        "(U//FOUO) Implementation of this object can be as low
         as read-only depending on which
         IS Objective or MIB desired requirements are
         not being met by the implementation."

    OBJECT		hAudThrottleCfgThreshold
    MIN-ACCESS	read-only
    DESCRIPTION
        "(U//FOUO) Implementation of this object can be as low
         as read-only depending on which
         IS Objective or MIB desired requirements are
         not being met by the implementation."

    OBJECT		usmStatsUnknownUserNames
    MIN-ACCESS	read-only
    DESCRIPTION
        "(U//FOUO) Implementation of this object can be as low
         as read-only depending on which
         IS Objective or MIB desired requirements are
         not being met by the implementation."

    OBJECT		mgmdHostInterfaceVersion1QuerierTimer
    MIN-ACCESS	read-only
    DESCRIPTION
        "(U//FOUO) Implementation of this object can be as low
         as read-only depending on which
         IS Objective or MIB desired requirements are
         not being met by the implementation."

--    OBJECT		snmpEngineGroup
--    MIN-ACCESS	read-write
--    DESCRIPTION
--        "(U//FOUO) Implementation of this object can be as low
--         as read-write depending on which
--         IS Objective or MIB desired requirements are
--         not being met by the implementation."

    OBJECT		haipeZeroizeAllKeys
    MIN-ACCESS	read-write
    DESCRIPTION
        "(U//FOUO) Implementation of this object can be as low
         as read-write depending on which
         IS Objective or MIB desired requirements are
         not being met by the implementation."

    OBJECT		ipReasmTimeout
    MIN-ACCESS	read-only
    DESCRIPTION
        "(U//FOUO) Implementation of this object can be as low
         as read-only depending on which
         IS Objective or MIB desired requirements are
         not being met by the implementation."

    OBJECT		hTPSAFlowLabel
    MIN-ACCESS	read-write
    DESCRIPTION
        "(U//FOUO) Implementation of this object can be as low
         as read-write depending on which
         IS Objective or MIB desired requirements are
         not being met by the implementation."

    OBJECT		usmUserOwnAuthKeyChange
    MIN-ACCESS	read-write
    DESCRIPTION
        "(U//FOUO) Implementation of this object can be as low
         as read-write depending on which
         IS Objective or MIB desired requirements are
         not being met by the implementation."

    OBJECT		snmpTargetAddrRowStatus
    MIN-ACCESS	read-write
    DESCRIPTION
        "(U//FOUO) Implementation of this object can be as low
         as read-write depending on which
         IS Objective or MIB desired requirements are
         not being met by the implementation."

--    OBJECT		usmAesCfb128Protocol
--    MIN-ACCESS	read-write
--    DESCRIPTION
--        "(U//FOUO) Implementation of this object can be as low
--         as read-write depending on which
--         IS Objective or MIB desired requirements are
--         not being met by the implementation."

    OBJECT		hAudCfgNotifThrottleStatus
    MIN-ACCESS	read-only
    DESCRIPTION
        "(U//FOUO) Implementation of this object can be as low
         as read-only depending on which
         IS Objective or MIB desired requirements are
         not being met by the implementation."

    OBJECT		usmStatsDecryptionErrors
    MIN-ACCESS	read-only
    DESCRIPTION
        "(U//FOUO) Implementation of this object can be as low
         as read-only depending on which
         IS Objective or MIB desired requirements are
         not being met by the implementation."

--    OBJECT		snmpNotifyBasicFiltersCompliance
--    MIN-ACCESS	read-write
--    DESCRIPTION
--        "(U//FOUO) Implementation of this object can be as low
--         as read-write depending on which
--         IS Objective or MIB desired requirements are
--         not being met by the implementation."

    OBJECT		hIPhFFSAFFUniversal
    MIN-ACCESS	read-write
    DESCRIPTION
        "(U//FOUO) Implementation of this object can be as low
         as read-write depending on which
         IS Objective or MIB desired requirements are
         not being met by the implementation."

    OBJECT		hPPKChainOrder
    MIN-ACCESS	read-write
    DESCRIPTION
        "(U//FOUO) Implementation of this object can be as low
         as read-write depending on which
         IS Objective or MIB desired requirements are
         not being met by the implementation."

    OBJECT		hTPSAHCUcastPkts
    MIN-ACCESS	not-accessible
    DESCRIPTION
        "(U//FOUO) Implementation of this object can be as low
         as not-accessible depending on which
         IS Objective or MIB desired requirements are
         not being met by the implementation."

    OBJECT		ipIfStatsReasmFails
    MIN-ACCESS	read-only
    DESCRIPTION
        "(U//FOUO) Implementation of this object can be as low
         as read-only depending on which
         IS Objective or MIB desired requirements are
         not being met by the implementation."

    OBJECT		ipv6InterfaceEnableStatus
    MIN-ACCESS	read-write
    DESCRIPTION
        "(U//FOUO) Implementation of this object can be as low
         as read-write depending on which
         IS Objective or MIB desired requirements are
         not being met by the implementation."

    OBJECT		snmpInASNParseErrs
    MIN-ACCESS	read-only
    DESCRIPTION
        "(U//FOUO) Implementation of this object can be as low
         as read-only depending on which
         IS Objective or MIB desired requirements are
         not being met by the implementation."

--    OBJECT		hTPnSACreated
--    MIN-ACCESS	not-accessible
--    DESCRIPTION
--        "(U//FOUO) Implementation of this object can be as low
--         as not-accessible depending on which
--         IS Objective or MIB desired requirements are
--         not being met by the implementation."

    OBJECT		mgmdRouterInterfaceLastMembQueryIntvl
    MIN-ACCESS	not-accessible
    DESCRIPTION
        "(U//FOUO) Implementation of this object can be as low
         as not-accessible depending on which
         IS Objective or MIB desired requirements are
         not being met by the implementation."

--    OBJECT		vacmMIBObjects
--    MIN-ACCESS	read-write
--    DESCRIPTION
--        "(U//FOUO) Implementation of this object can be as low
--         as read-write depending on which
--         IS Objective or MIB desired requirements are
--         not being met by the implementation."

--    OBJECT		hTPnSADestroyed
--    MIN-ACCESS	not-accessible
--    DESCRIPTION
--        "(U//FOUO) Implementation of this object can be as low
--         as not-accessible depending on which
--         IS Objective or MIB desired requirements are
--         not being met by the implementation."

    OBJECT		hIfv6HaipeTableLastChanged
    MIN-ACCESS	read-only
    DESCRIPTION
        "(U//FOUO) Implementation of this object can be as low
         as read-only depending on which
         IS Objective or MIB desired requirements are
         not being met by the implementation."

    OBJECT		hDeviceVersionTableCount
    MIN-ACCESS	read-only
    DESCRIPTION
        "(U//FOUO) Implementation of this object can be as low
         as read-only depending on which
         IS Objective or MIB desired requirements are
         not being met by the implementation."

    OBJECT		ipSystemStatsOutMcastPkts
    MIN-ACCESS	not-accessible
    DESCRIPTION
        "(U//FOUO) Implementation of this object can be as low
         as not-accessible depending on which
         IS Objective or MIB desired requirements are
         not being met by the implementation."

    OBJECT		ipSystemStatsHCInMcastOctets
    MIN-ACCESS	not-accessible
    DESCRIPTION
        "(U//FOUO) Implementation of this object can be as low
         as not-accessible depending on which
         IS Objective or MIB desired requirements are
         not being met by the implementation."

    OBJECT		hFdsSide
    MIN-ACCESS	read-write
    DESCRIPTION
        "(U//FOUO) Implementation of this object can be as low
         as read-write depending on which
         IS Objective or MIB desired requirements are
         not being met by the implementation."

    OBJECT		hiaaPrefixLen
    MIN-ACCESS	read-write
    DESCRIPTION
        "(U//FOUO) Implementation of this object can be as low
         as read-write depending on which
         IS Objective or MIB desired requirements are
         not being met by the implementation."

    OBJECT		snmpNotifyStorageType
    MIN-ACCESS	read-write
    DESCRIPTION
        "(U//FOUO) Implementation of this object can be as low
         as read-write depending on which
         IS Objective or MIB desired requirements are
         not being met by the implementation."

    OBJECT		hLocalCKListReason
    MIN-ACCESS	read-write
    DESCRIPTION
        "(U//FOUO) Implementation of this object can be as low
         as read-write depending on which
         IS Objective or MIB desired requirements are
         not being met by the implementation."

    OBJECT		hDeviceVersionTableLastChanged
    MIN-ACCESS	read-only
    DESCRIPTION
        "(U//FOUO) Implementation of this object can be as low
         as read-only depending on which
         IS Objective or MIB desired requirements are
         not being met by the implementation."

    OBJECT		nlmLogEngineTDomain
    MIN-ACCESS	read-only
    DESCRIPTION
        "(U//FOUO) Implementation of this object can be as low
         as read-only depending on which
         IS Objective or MIB desired requirements are
         not being met by the implementation."

    OBJECT		snmpTargetParamsSecurityLevel
    MIN-ACCESS	read-write
    DESCRIPTION
        "(U//FOUO) Implementation of this object can be as low
         as read-write depending on which
         IS Objective or MIB desired requirements are
         not being met by the implementation."

    OBJECT		hAudCfgLogThrottleStatus
    MIN-ACCESS	read-only
    DESCRIPTION
        "(U//FOUO) Implementation of this object can be as low
         as read-only depending on which
         IS Objective or MIB desired requirements are
         not being met by the implementation."

    OBJECT		hLocalCKListKMIDEnd
    MIN-ACCESS	read-only
    DESCRIPTION
        "(U//FOUO) Implementation of this object can be as low
         as read-only depending on which
         IS Objective or MIB desired requirements are
         not being met by the implementation."

    OBJECT		snmpEngineTime
    MIN-ACCESS	read-only
    DESCRIPTION
        "(U//FOUO) Implementation of this object can be as low
         as read-only depending on which
         IS Objective or MIB desired requirements are
         not being met by the implementation."

--    OBJECT		hFirmwareDownloadSuccess
--    MIN-ACCESS	accessible-for-notify
--    DESCRIPTION
--        "(U//FOUO) Implementation of this object can be as low
--         as accessible-for-notify depending on which
--         IS Objective or MIB desired requirements are
--         not being met by the implementation."

    OBJECT		hAuditConfigTableLastChanged
    MIN-ACCESS	read-only
    DESCRIPTION
        "(U//FOUO) Implementation of this object can be as low
         as read-only depending on which
         IS Objective or MIB desired requirements are
         not being met by the implementation."

    OBJECT		snmpTargetAddrTimeout
    MIN-ACCESS	read-write
    DESCRIPTION
        "(U//FOUO) Implementation of this object can be as low
         as read-write depending on which
         IS Objective or MIB desired requirements are
         not being met by the implementation."

--    OBJECT		usmUser
--    MIN-ACCESS	read-write
--    DESCRIPTION
--        "(U//FOUO) Implementation of this object can be as low
--         as read-write depending on which
--         IS Objective or MIB desired requirements are
--         not being met by the implementation."

    OBJECT		hIPhFFSAFlowLabelValue
    MIN-ACCESS	read-write
    DESCRIPTION
        "(U//FOUO) Implementation of this object can be as low
         as read-write depending on which
         IS Objective or MIB desired requirements are
         not being met by the implementation."

    OBJECT		hPPKUsageType
    MIN-ACCESS	read-only
    DESCRIPTION
        "(U//FOUO) Implementation of this object can be as low
         as read-only depending on which
         IS Objective or MIB desired requirements are
         not being met by the implementation."

    OBJECT		hBatteryLevelPercentage
    MIN-ACCESS	read-only
    DESCRIPTION
        "(U//FOUO) Implementation of this object can be as low
         as read-only depending on which
         IS Objective or MIB desired requirements are
         not being met by the implementation."

    OBJECT		mgmdRouterInterfaceVersion
    MIN-ACCESS	not-accessible
    DESCRIPTION
        "(U//FOUO) Implementation of this object can be as low
         as not-accessible depending on which
         IS Objective or MIB desired requirements are
         not being met by the implementation."

    OBJECT		tcpOutSegs
    MIN-ACCESS	read-only
    DESCRIPTION
        "(U//FOUO) Implementation of this object can be as low
         as read-only depending on which
         IS Objective or MIB desired requirements are
         not being met by the implementation."

    OBJECT		hIPhFFSACTOutAddressType
    MIN-ACCESS	read-write
    DESCRIPTION
        "(U//FOUO) Implementation of this object can be as low
         as read-write depending on which
         IS Objective or MIB desired requirements are
         not being met by the implementation."

    OBJECT		ipNetToPhysicalPhysAddress
    MIN-ACCESS	read-only
    DESCRIPTION
        "(U//FOUO) Implementation of this object can be as low
         as read-only depending on which
         IS Objective or MIB desired requirements are
         not being met by the implementation."

--    OBJECT		snmpNotifyBasicCompliance
--    MIN-ACCESS	read-write
--    DESCRIPTION
--        "(U//FOUO) Implementation of this object can be as low
--         as read-write depending on which
--         IS Objective or MIB desired requirements are
--         not being met by the implementation."

    OBJECT		sysUpTime
    MIN-ACCESS	read-only
    DESCRIPTION
        "(U//FOUO) Implementation of this object can be as low
         as read-only depending on which
         IS Objective or MIB desired requirements are
         not being met by the implementation."

    OBJECT		hTFTPDesiredTimeoutInterval
    MIN-ACCESS	not-accessible
    DESCRIPTION
        "(U//FOUO) Implementation of this object can be as low
         as not-accessible depending on which
         IS Objective or MIB desired requirements are
         not being met by the implementation."

    OBJECT		hTPSAspi
    MIN-ACCESS	read-write
    DESCRIPTION
        "(U//FOUO) Implementation of this object can be as low
         as read-write depending on which
         IS Objective or MIB desired requirements are
         not being met by the implementation."

    OBJECT		hTPSADSCP
    MIN-ACCESS	read-write
    DESCRIPTION
        "(U//FOUO) Implementation of this object can be as low
         as read-write depending on which
         IS Objective or MIB desired requirements are
         not being met by the implementation."

    OBJECT		nlmLogVariableID
    MIN-ACCESS	read-only
    DESCRIPTION
        "(U//FOUO) Implementation of this object can be as low
         as read-only depending on which
         IS Objective or MIB desired requirements are
         not being met by the implementation."

    OBJECT		hIPhFFSALastChanged
    MIN-ACCESS	read-only
    DESCRIPTION
        "(U//FOUO) Implementation of this object can be as low
         as read-only depending on which
         IS Objective or MIB desired requirements are
         not being met by the implementation."

    OBJECT		ifInBroadcastPkts
    MIN-ACCESS	not-accessible
    DESCRIPTION
        "(U//FOUO) Implementation of this object can be as low
         as not-accessible depending on which
         IS Objective or MIB desired requirements are
         not being met by the implementation."

    OBJECT		ifHCInUcastPkts
    MIN-ACCESS	read-only
    DESCRIPTION
        "(U//FOUO) Implementation of this object can be as low
         as read-only depending on which
         IS Objective or MIB desired requirements are
         not being met by the implementation."

    OBJECT		ipSystemStatsHCOutTransmits
    MIN-ACCESS	not-accessible
    DESCRIPTION
        "(U//FOUO) Implementation of this object can be as low
         as not-accessible depending on which
         IS Objective or MIB desired requirements are
         not being met by the implementation."

    OBJECT		ipSystemStatsHCOutOctets
    MIN-ACCESS	not-accessible
    DESCRIPTION
        "(U//FOUO) Implementation of this object can be as low
         as not-accessible depending on which
         IS Objective or MIB desired requirements are
         not being met by the implementation."

    OBJECT		vacmAccessContextMatch
    MIN-ACCESS	read-write
    DESCRIPTION
        "(U//FOUO) Implementation of this object can be as low
         as read-write depending on which
         IS Objective or MIB desired requirements are
         not being met by the implementation."

    OBJECT		ifCounterDiscontinuityTime
    MIN-ACCESS	not-accessible
    DESCRIPTION
        "(U//FOUO) Implementation of this object can be as low
         as not-accessible depending on which
         IS Objective or MIB desired requirements are
         not being met by the implementation."

    OBJECT		hTPSADFBit
    MIN-ACCESS	read-write
    DESCRIPTION
        "(U//FOUO) Implementation of this object can be as low
         as read-write depending on which
         IS Objective or MIB desired requirements are
         not being met by the implementation."

    OBJECT		ifHCOutMulticastPkts
    MIN-ACCESS	read-only
    DESCRIPTION
        "(U//FOUO) Implementation of this object can be as low
         as read-only depending on which
         IS Objective or MIB desired requirements are
         not being met by the implementation."

    OBJECT		hIfv4LastChanged
    MIN-ACCESS	read-only
    DESCRIPTION
        "(U//FOUO) Implementation of this object can be as low
         as read-only depending on which
         IS Objective or MIB desired requirements are
         not being met by the implementation."

    OBJECT		snmpNotifyFilterMask
    MIN-ACCESS	read-write
    DESCRIPTION
        "(U//FOUO) Implementation of this object can be as low
         as read-write depending on which
         IS Objective or MIB desired requirements are
         not being met by the implementation."

    OBJECT		inetCidrRouteNextHopAS
    MIN-ACCESS	read-write
    DESCRIPTION
        "(U//FOUO) Implementation of this object can be as low
         as read-write depending on which
         IS Objective or MIB desired requirements are
         not being met by the implementation."

    OBJECT		hNotificationLogPartialReset
    MIN-ACCESS	not-accessible
    DESCRIPTION
        "(U//FOUO) Implementation of this object can be as low
         as not-accessible depending on which
         IS Objective or MIB desired requirements are
         not being met by the implementation."

    OBJECT		hIPhFFSARowStatus
    MIN-ACCESS	read-write
    DESCRIPTION
        "(U//FOUO) Implementation of this object can be as low
         as read-write depending on which
         IS Objective or MIB desired requirements are
         not being met by the implementation."

    OBJECT		hPreplacedKeyTableCapacity
    MIN-ACCESS	read-only
    DESCRIPTION
        "(U//FOUO) Implementation of this object can be as low
         as read-only depending on which
         IS Objective or MIB desired requirements are
         not being met by the implementation."

    OBJECT		hCurrentState
    MIN-ACCESS	read-only
    DESCRIPTION
        "(U//FOUO) Implementation of this object can be as low
         as read-only depending on which
         IS Objective or MIB desired requirements are
         not being met by the implementation."

--    OBJECT		snmpUsmAesMIB
--    MIN-ACCESS	read-only
--    DESCRIPTION
--        "(U//FOUO) Implementation of this object can be as low
--         as read-only depending on which
--         IS Objective or MIB desired requirements are
--         not being met by the implementation."

    OBJECT		vacmAccessNotifyViewName
    MIN-ACCESS	read-write
    DESCRIPTION
        "(U//FOUO) Implementation of this object can be as low
         as read-write depending on which
         IS Objective or MIB desired requirements are
         not being met by the implementation."

    OBJECT		ifInNUcastPkts
    MIN-ACCESS	not-accessible
    DESCRIPTION
        "(U//FOUO) Implementation of this object can be as low
         as not-accessible depending on which
         IS Objective or MIB desired requirements are
         not being met by the implementation."

    OBJECT		hTPSAEncryptAlgorithm
    MIN-ACCESS	read-only
    DESCRIPTION
        "(U//FOUO) Implementation of this object can be as low
         as read-only depending on which
         IS Objective or MIB desired requirements are
         not being met by the implementation."

    OBJECT		snmpTargetAddrTagList
    MIN-ACCESS	read-write
    DESCRIPTION
        "(U//FOUO) Implementation of this object can be as low
         as read-write depending on which
         IS Objective or MIB desired requirements are
         not being met by the implementation."

--    OBJECT		snmpAuthProtocols
--    MIN-ACCESS	read-write
--    DESCRIPTION
--        "(U//FOUO) Implementation of this object can be as low
--         as read-write depending on which
--         IS Objective or MIB desired requirements are
--         not being met by the implementation."

    OBJECT		hIfv4Side
    MIN-ACCESS	read-only
    DESCRIPTION
        "(U//FOUO) Implementation of this object can be as low
         as read-only depending on which
         IS Objective or MIB desired requirements are
         not being met by the implementation."

    OBJECT		vacmAccessReadViewName
    MIN-ACCESS	read-write
    DESCRIPTION
        "(U//FOUO) Implementation of this object can be as low
         as read-write depending on which
         IS Objective or MIB desired requirements are
         not being met by the implementation."

    OBJECT		hTPSALocalCTAddress
    MIN-ACCESS	read-write
    DESCRIPTION
        "(U//FOUO) Implementation of this object can be as low
         as read-write depending on which
         IS Objective or MIB desired requirements are
         not being met by the implementation."

    OBJECT		ipAddressSpinLock
    MIN-ACCESS	not-accessible
    DESCRIPTION
        "(U//FOUO) Implementation of this object can be as low
         as not-accessible depending on which
         IS Objective or MIB desired requirements are
         not being met by the implementation."

    OBJECT		mgmdRouterInterfaceLastMembQueryCount
    MIN-ACCESS	not-accessible
    DESCRIPTION
        "(U//FOUO) Implementation of this object can be as low
         as not-accessible depending on which
         IS Objective or MIB desired requirements are
         not being met by the implementation."

    OBJECT		ipSystemStatsHCInDelivers
    MIN-ACCESS	not-accessible
    DESCRIPTION
        "(U//FOUO) Implementation of this object can be as low
         as not-accessible depending on which
         IS Objective or MIB desired requirements are
         not being met by the implementation."

    OBJECT		nlmStatsGlobalNotificationsLogged
    MIN-ACCESS	read-only
    DESCRIPTION
        "(U//FOUO) Implementation of this object can be as low
         as read-only depending on which
         IS Objective or MIB desired requirements are
         not being met by the implementation."

    OBJECT		ipv6InterfaceIdentifier
    MIN-ACCESS	read-only
    DESCRIPTION
        "(U//FOUO) Implementation of this object can be as low
         as read-only depending on which
         IS Objective or MIB desired requirements are
         not being met by the implementation."

    OBJECT		ifNumber
    MIN-ACCESS	read-only
    DESCRIPTION
        "(U//FOUO) Implementation of this object can be as low
         as read-only depending on which
         IS Objective or MIB desired requirements are
         not being met by the implementation."

    OBJECT		mgmdRouterCacheLastReporter
    MIN-ACCESS	not-accessible
    DESCRIPTION
        "(U//FOUO) Implementation of this object can be as low
         as not-accessible depending on which
         IS Objective or MIB desired requirements are
         not being met by the implementation."

    OBJECT		sysORDescr
    MIN-ACCESS	not-accessible
    DESCRIPTION
        "(U//FOUO) Implementation of this object can be as low
         as not-accessible depending on which
         IS Objective or MIB desired requirements are
         not being met by the implementation."

    OBJECT		ipIfStatsDiscontinuityTime
    MIN-ACCESS	read-only
    DESCRIPTION
        "(U//FOUO) Implementation of this object can be as low
         as read-only depending on which
         IS Objective or MIB desired requirements are
         not being met by the implementation."

--    OBJECT		snmpTargetConformance
--    MIN-ACCESS	read-write
--    DESCRIPTION
--        "(U//FOUO) Implementation of this object can be as low
--         as read-write depending on which
--         IS Objective or MIB desired requirements are
--         not being met by the implementation."

    OBJECT		inetCidrRouteIfIndex
    MIN-ACCESS	read-write
    DESCRIPTION
        "(U//FOUO) Implementation of this object can be as low
         as read-write depending on which
         IS Objective or MIB desired requirements are
         not being met by the implementation."

--    OBJECT		hLocalCompromisedKeyListTable
--    MIN-ACCESS	read-only
--    DESCRIPTION
--        "(U//FOUO) Implementation of this object can be as low
--         as read-only depending on which
--         IS Objective or MIB desired requirements are
--         not being met by the implementation."

    OBJECT		ifOutErrors
    MIN-ACCESS	not-accessible
    DESCRIPTION
        "(U//FOUO) Implementation of this object can be as low
         as not-accessible depending on which
         IS Objective or MIB desired requirements are
         not being met by the implementation."

    OBJECT		hIfv4HaipeTableCount
    MIN-ACCESS	read-only
    DESCRIPTION
        "(U//FOUO) Implementation of this object can be as low
         as read-only depending on which
         IS Objective or MIB desired requirements are
         not being met by the implementation."

    OBJECT		hNotificationLogReset
    MIN-ACCESS	read-write
    DESCRIPTION
        "(U//FOUO) Implementation of this object can be as low
         as read-write depending on which
         IS Objective or MIB desired requirements are
         not being met by the implementation."

    OBJECT		hFdsRowStatus
    MIN-ACCESS	read-write
    DESCRIPTION
        "(U//FOUO) Implementation of this object can be as low
         as read-write depending on which
         IS Objective or MIB desired requirements are
         not being met by the implementation."

    OBJECT		hTPSADIndexType
    MIN-ACCESS	read-write
    DESCRIPTION
        "(U//FOUO) Implementation of this object can be as low
         as read-write depending on which
         IS Objective or MIB desired requirements are
         not being met by the implementation."

    OBJECT		hAudCfgLogThrottleCfg
    MIN-ACCESS	read-only
    DESCRIPTION
        "(U//FOUO) Implementation of this object can be as low
         as read-only depending on which
         IS Objective or MIB desired requirements are
         not being met by the implementation."

    OBJECT		vacmViewTreeFamilyStorageType
    MIN-ACCESS	read-write
    DESCRIPTION
        "(U//FOUO) Implementation of this object can be as low
         as read-write depending on which
         IS Objective or MIB desired requirements are
         not being met by the implementation."

    OBJECT		ipSystemStatsInUnknownProtos
    MIN-ACCESS	not-accessible
    DESCRIPTION
        "(U//FOUO) Implementation of this object can be as low
         as not-accessible depending on which
         IS Objective or MIB desired requirements are
         not being met by the implementation."

    OBJECT		mgmdHostSrcListHostAddress
    MIN-ACCESS	read-only
    DESCRIPTION
        "(U//FOUO) Implementation of this object can be as low
         as read-only depending on which
         IS Objective or MIB desired requirements are
         not being met by the implementation."

    OBJECT		hIPhFFSAFF
    MIN-ACCESS	read-write
    DESCRIPTION
        "(U//FOUO) Implementation of this object can be as low
         as read-write depending on which
         IS Objective or MIB desired requirements are
         not being met by the implementation."

    OBJECT		snmpTargetParamsRowStatus
    MIN-ACCESS	read-write
    DESCRIPTION
        "(U//FOUO) Implementation of this object can be as low
         as read-write depending on which
         IS Objective or MIB desired requirements are
         not being met by the implementation."

    OBJECT		hAudThrottleCfgLastChanged
    MIN-ACCESS	read-only
    DESCRIPTION
        "(U//FOUO) Implementation of this object can be as low
         as read-only depending on which
         IS Objective or MIB desired requirements are
         not being met by the implementation."

    OBJECT		snmpTargetParamsSecurityName
    MIN-ACCESS	read-write
    DESCRIPTION
        "(U//FOUO) Implementation of this object can be as low
         as read-write depending on which
         IS Objective or MIB desired requirements are
         not being met by the implementation."

    OBJECT		snmpEngineID
    MIN-ACCESS	read-only
    DESCRIPTION
        "(U//FOUO) Implementation of this object can be as low
         as read-only depending on which
         IS Objective or MIB desired requirements are
         not being met by the implementation."

    OBJECT		ipSystemStatsReasmFails
    MIN-ACCESS	not-accessible
    DESCRIPTION
        "(U//FOUO) Implementation of this object can be as low
         as not-accessible depending on which
         IS Objective or MIB desired requirements are
         not being met by the implementation."

    OBJECT		hIPhFFSAFlowLabel
    MIN-ACCESS	read-write
    DESCRIPTION
        "(U//FOUO) Implementation of this object can be as low
         as read-write depending on which
         IS Objective or MIB desired requirements are
         not being met by the implementation."

    OBJECT		ipIfStatsInDelivers
    MIN-ACCESS	not-accessible
    DESCRIPTION
        "(U//FOUO) Implementation of this object can be as low
         as not-accessible depending on which
         IS Objective or MIB desired requirements are
         not being met by the implementation."

--    OBJECT		hPPKKeyExpirationWarning
--    MIN-ACCESS	accessible-for-notify
--    DESCRIPTION
--        "(U//FOUO) Implementation of this object can be as low
--         as accessible-for-notify depending on which
--         IS Objective or MIB desired requirements are
--         not being met by the implementation."

    OBJECT		hFirmwareDownloadServersTableLastChanged
    MIN-ACCESS	read-only
    DESCRIPTION
        "(U//FOUO) Implementation of this object can be as low
         as read-only depending on which
         IS Objective or MIB desired requirements are
         not being met by the implementation."

    OBJECT		hIPhRuleSelectorName
    MIN-ACCESS	read-write
    DESCRIPTION
        "(U//FOUO) Implementation of this object can be as low
         as read-write depending on which
         IS Objective or MIB desired requirements are
         not being met by the implementation."

--    OBJECT		snmpMPDMIBGroups
--    MIN-ACCESS	read-write
--    DESCRIPTION
--        "(U//FOUO) Implementation of this object can be as low
--         as read-write depending on which
--         IS Objective or MIB desired requirements are
--         not being met by the implementation."

    OBJECT		ifInMulticastPkts
    MIN-ACCESS	not-accessible
    DESCRIPTION
        "(U//FOUO) Implementation of this object can be as low
         as not-accessible depending on which
         IS Objective or MIB desired requirements are
         not being met by the implementation."

    OBJECT		mgmdRouterCacheVersion2HostTimer
    MIN-ACCESS	not-accessible
    DESCRIPTION
        "(U//FOUO) Implementation of this object can be as low
         as not-accessible depending on which
         IS Objective or MIB desired requirements are
         not being met by the implementation."

    OBJECT		mgmdRouterInterfaceQuerierUpTime
    MIN-ACCESS	not-accessible
    DESCRIPTION
        "(U//FOUO) Implementation of this object can be as low
         as not-accessible depending on which
         IS Objective or MIB desired requirements are
         not being met by the implementation."

    OBJECT		tcpRetransSegs
    MIN-ACCESS	read-only
    DESCRIPTION
        "(U//FOUO) Implementation of this object can be as low
         as read-only depending on which
         IS Objective or MIB desired requirements are
         not being met by the implementation."

    OBJECT		ifHCInOctets
    MIN-ACCESS	read-only
    DESCRIPTION
        "(U//FOUO) Implementation of this object can be as low
         as read-only depending on which
         IS Objective or MIB desired requirements are
         not being met by the implementation."

    OBJECT		usmUserPrivProtocol
    MIN-ACCESS	read-write
    DESCRIPTION
        "(U//FOUO) Implementation of this object can be as low
         as read-write depending on which
         IS Objective or MIB desired requirements are
         not being met by the implementation."

    OBJECT		hTPSASecurityPayloadType
    MIN-ACCESS	read-only
    DESCRIPTION
        "(U//FOUO) Implementation of this object can be as low
         as read-only depending on which
         IS Objective or MIB desired requirements are
         not being met by the implementation."

    OBJECT		snmpNotifyType
    MIN-ACCESS	read-write
    DESCRIPTION
        "(U//FOUO) Implementation of this object can be as low
         as read-write depending on which
         IS Objective or MIB desired requirements are
         not being met by the implementation."

    OBJECT		vacmAccessStorageType
    MIN-ACCESS	read-write
    DESCRIPTION
        "(U//FOUO) Implementation of this object can be as low
         as read-write depending on which
         IS Objective or MIB desired requirements are
         not being met by the implementation."

    OBJECT		hIPhRuleTableCount
    MIN-ACCESS	read-only
    DESCRIPTION
        "(U//FOUO) Implementation of this object can be as low
         as read-only depending on which
         IS Objective or MIB desired requirements are
         not being met by the implementation."

    OBJECT		hIPhRuleName
    MIN-ACCESS	read-write
    DESCRIPTION
        "(U//FOUO) Implementation of this object can be as low
         as read-write depending on which
         IS Objective or MIB desired requirements are
         not being met by the implementation."

    OBJECT		inetCidrRouteMetric3
    MIN-ACCESS	read-write
    DESCRIPTION
        "(U//FOUO) Implementation of this object can be as low
         as read-write depending on which
         IS Objective or MIB desired requirements are
         not being met by the implementation."

    OBJECT		snmpNotifyFilterRowStatus
    MIN-ACCESS	read-write
    DESCRIPTION
        "(U//FOUO) Implementation of this object can be as low
         as read-write depending on which
         IS Objective or MIB desired requirements are
         not being met by the implementation."

    OBJECT		snmpUnavailableContexts
    MIN-ACCESS	read-only
    DESCRIPTION
        "(U//FOUO) Implementation of this object can be as low
         as read-only depending on which
         IS Objective or MIB desired requirements are
         not being met by the implementation."

    OBJECT		snmpNotifyFilterProfileName
    MIN-ACCESS	read-write
    DESCRIPTION
        "(U//FOUO) Implementation of this object can be as low
         as read-write depending on which
         IS Objective or MIB desired requirements are
         not being met by the implementation."

    OBJECT		snmpUnknownPDUHandlers
    MIN-ACCESS	read-only
    DESCRIPTION
        "(U//FOUO) Implementation of this object can be as low
         as read-only depending on which
         IS Objective or MIB desired requirements are
         not being met by the implementation."

    OBJECT		hNotificationLogWarningPercentage
    MIN-ACCESS	read-only
    DESCRIPTION
        "(U//FOUO) Implementation of this object can be as low
         as read-only depending on which
         IS Objective or MIB desired requirements are
         not being met by the implementation."

    OBJECT		ipIfStatsInReceives
    MIN-ACCESS	not-accessible
    DESCRIPTION
        "(U//FOUO) Implementation of this object can be as low
         as not-accessible depending on which
         IS Objective or MIB desired requirements are
         not being met by the implementation."

--    OBJECT		hBatteryLow
--    MIN-ACCESS	accessible-for-notify
--    DESCRIPTION
--        "(U//FOUO) Implementation of this object can be as low
--         as accessible-for-notify depending on which
--         IS Objective or MIB desired requirements are
--         not being met by the implementation."

    OBJECT		udpHCOutDatagrams
    MIN-ACCESS	read-only
    DESCRIPTION
        "(U//FOUO) Implementation of this object can be as low
         as read-only depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

--    OBJECT		hFirmwareDownloadError
--    MIN-ACCESS	accessible-for-notify
--    DESCRIPTION
--        "(U//FOUO) Implementation of this object can be as low
--         as accessible-for-notify depending on which
--         IS Objective or MIB desired requirements are
--         not being met by the implementation."

    OBJECT		hPPKChainEncryptionAlgorithm
    MIN-ACCESS	read-write
    DESCRIPTION
        "(U//FOUO) Implementation of this object can be as low
         as read-write depending on which
         IS Objective or MIB desired requirements are
         not being met by the implementation."

    OBJECT		nlmLogVariableIpAddressVal
    MIN-ACCESS	read-only
    DESCRIPTION
        "(U//FOUO) Implementation of this object can be as low
         as read-only depending on which
         IS Objective or MIB desired requirements are
         not being met by the implementation."

    OBJECT		hTPSAIntegrityAlgorithm
    MIN-ACCESS	read-write
    DESCRIPTION
        "(U//FOUO) Implementation of this object can be as low
         as read-write depending on which
         IS Objective or MIB desired requirements are
         not being met by the implementation."

    OBJECT		hAudThrottleCfgRowStatus
    MIN-ACCESS	read-only
    DESCRIPTION
        "(U//FOUO) Implementation of this object can be as low
         as read-only depending on which
         IS Objective or MIB desired requirements are
         not being met by the implementation."

    OBJECT		snmpUnknownSecurityModels
    MIN-ACCESS	read-only
    DESCRIPTION
        "(U//FOUO) Implementation of this object can be as low
         as read-only depending on which
         IS Objective or MIB desired requirements are
         not being met by the implementation."

    OBJECT		hTPSAEndTime
    MIN-ACCESS	read-write
    DESCRIPTION
        "(U//FOUO) Implementation of this object can be as low
         as read-write depending on which
         IS Objective or MIB desired requirements are
         not being met by the implementation."

    OBJECT		mgmdRouterInterfaceQuerierExpiryTime
    MIN-ACCESS	not-accessible
    DESCRIPTION
        "(U//FOUO) Implementation of this object can be as low
         as not-accessible depending on which
         IS Objective or MIB desired requirements are
         not being met by the implementation."

    OBJECT		hTPSALocalCAName
    MIN-ACCESS	not-accessible
    DESCRIPTION
        "(U//FOUO) Implementation of this object can be as low
         as not-accessible depending on which
         IS Objective or MIB desired requirements are
         not being met by the implementation."

    OBJECT		hTPSARemoteCAName
    MIN-ACCESS	not-accessible
    DESCRIPTION
        "(U//FOUO) Implementation of this object can be as low
         as not-accessible depending on which
         IS Objective or MIB desired requirements are
         not being met by the implementation."

    OBJECT		ipIfStatsInBcastPkts
    MIN-ACCESS	not-accessible
    DESCRIPTION
        "(U//FOUO) Implementation of this object can be as low
         as not-accessible depending on which
         IS Objective or MIB desired requirements are
         not being met by the implementation."

    OBJECT		ipIfStatsHCOutMcastOctets
    MIN-ACCESS	read-only
    DESCRIPTION
        "(U//FOUO) Implementation of this object can be as low
         as read-only depending on which
         IS Objective or MIB desired requirements are
         not being met by the implementation."

    OBJECT		nlmLogVariableCounter64Val
    MIN-ACCESS	read-only
    DESCRIPTION
        "(U//FOUO) Implementation of this object can be as low
         as read-only depending on which
         IS Objective or MIB desired requirements are
         not being met by the implementation."

    OBJECT		tcpPassiveOpens
    MIN-ACCESS	read-only
    DESCRIPTION
        "(U//FOUO) Implementation of this object can be as low
         as read-only depending on which
         IS Objective or MIB desired requirements are
         not being met by the implementation."

    OBJECT		snmpInBadCommunityUses
    MIN-ACCESS	not-accessible
    DESCRIPTION
        "(U//FOUO) Implementation of this object can be as low
         as not-accessible depending on which
         IS Objective or MIB desired requirements are
         not being met by the implementation."

    OBJECT		ifInOctets
    MIN-ACCESS	not-accessible
    DESCRIPTION
        "(U//FOUO) Implementation of this object can be as low
         as not-accessible depending on which
         IS Objective or MIB desired requirements are
         not being met by the implementation."

    OBJECT		ifSpecific
    MIN-ACCESS	not-accessible
    DESCRIPTION
        "(U//FOUO) Implementation of this object can be as low
         as not-accessible depending on which
         IS Objective or MIB desired requirements are
         not being met by the implementation."

    OBJECT		ipIfStatsInUnknownProtos
    MIN-ACCESS	not-accessible
    DESCRIPTION
        "(U//FOUO) Implementation of this object can be as low
         as not-accessible depending on which
         IS Objective or MIB desired requirements are
         not being met by the implementation."

--    OBJECT		snmpMPDGroup
--    MIN-ACCESS	read-write
--    DESCRIPTION
--        "(U//FOUO) Implementation of this object can be as low
--         as read-write depending on which
--         IS Objective or MIB desired requirements are
--         not being met by the implementation."

    OBJECT		vacmViewTreeFamilyStatus
    MIN-ACCESS	read-write
    DESCRIPTION
        "(U//FOUO) Implementation of this object can be as low
         as read-write depending on which
         IS Objective or MIB desired requirements are
         not being met by the implementation."

--    OBJECT		usmMIBBasicGroup
--    MIN-ACCESS	read-write
--    DESCRIPTION
--        "(U//FOUO) Implementation of this object can be as low
--         as read-write depending on which
--         IS Objective or MIB desired requirements are
--         not being met by the implementation."

    OBJECT		hTPSASelectorNextHeaderOpt2End
    MIN-ACCESS	not-accessible
    DESCRIPTION
        "(U//FOUO) Implementation of this object can be as low
         as not-accessible depending on which
         IS Objective or MIB desired requirements are
         not being met by the implementation."

    OBJECT		nlmLogNotificationID
    MIN-ACCESS	read-only
    DESCRIPTION
        "(U//FOUO) Implementation of this object can be as low
         as read-only depending on which
         IS Objective or MIB desired requirements are
         not being met by the implementation."

--    OBJECT		vacmMIBGroups
--    MIN-ACCESS	read-write
--    DESCRIPTION
--        "(U//FOUO) Implementation of this object can be as low
--         as read-write depending on which
--         IS Objective or MIB desired requirements are
--         not being met by the implementation."

    OBJECT		ipSystemStatsOutFragFails
    MIN-ACCESS	not-accessible
    DESCRIPTION
        "(U//FOUO) Implementation of this object can be as low
         as not-accessible depending on which
         IS Objective or MIB desired requirements are
         not being met by the implementation."

    OBJECT		ipSystemStatsHCInBcastPkts
    MIN-ACCESS	not-accessible
    DESCRIPTION
        "(U//FOUO) Implementation of this object can be as low
         as not-accessible depending on which
         IS Objective or MIB desired requirements are
         not being met by the implementation."

    OBJECT		hSecurityLevel
    MIN-ACCESS	read-only
    DESCRIPTION
        "(U//FOUO) Implementation of this object can be as low
         as read-only depending on which
         IS Objective or MIB desired requirements are
         not being met by the implementation."

    OBJECT		hPPKAuthority
    MIN-ACCESS	not-accessible
    DESCRIPTION
        "(U//FOUO) Implementation of this object can be as low
         as not-accessible depending on which
         IS Objective or MIB desired requirements are
         not being met by the implementation."

    OBJECT		ifLinkUpDownTrapEnable
    MIN-ACCESS	not-accessible
    DESCRIPTION
        "(U//FOUO) Implementation of this object can be as low
         as not-accessible depending on which
         IS Objective or MIB desired requirements are
         not being met by the implementation."

    OBJECT		sysLocation
    MIN-ACCESS	read-write
    DESCRIPTION
        "(U//FOUO) Implementation of this object can be as low
         as read-write depending on which
         IS Objective or MIB desired requirements are
         not being met by the implementation."

    OBJECT		hTFTPMaximumFileTransferSize
    MIN-ACCESS	not-accessible
    DESCRIPTION
        "(U//FOUO) Implementation of this object can be as low
         as not-accessible depending on which
         IS Objective or MIB desired requirements are
         not being met by the implementation."

    OBJECT		ipNetToPhysicalRowStatus
    MIN-ACCESS	read-only
    DESCRIPTION
        "(U//FOUO) Implementation of this object can be as low
         as read-only depending on which
         IS Objective or MIB desired requirements are
         not being met by the implementation."

    OBJECT		vacmViewTreeFamilyMask
    MIN-ACCESS	read-write
    DESCRIPTION
        "(U//FOUO) Implementation of this object can be as low
         as read-write depending on which
         IS Objective or MIB desired requirements are
         not being met by the implementation."

    OBJECT		ipSystemStatsInReceives
    MIN-ACCESS	not-accessible
    DESCRIPTION
        "(U//FOUO) Implementation of this object can be as low
         as not-accessible depending on which
         IS Objective or MIB desired requirements are
         not being met by the implementation."

    OBJECT		snmpTargetSpinLock
    MIN-ACCESS	read-write
    DESCRIPTION
        "(U//FOUO) Implementation of this object can be as low
         as read-write depending on which
         IS Objective or MIB desired requirements are
         not being met by the implementation."

    OBJECT		mgmdRouterInterfaceStatus
    MIN-ACCESS	not-accessible
    DESCRIPTION
        "(U//FOUO) Implementation of this object can be as low
         as not-accessible depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hIPhRuleLastChanged
    MIN-ACCESS	read-only
    DESCRIPTION
        "(U//FOUO) Implementation of this object can be as low
         as read-only depending on which
         IS Objective or MIB desired requirements are
         not being met by the implementation."

    OBJECT		hPPKSecurityLevel
    MIN-ACCESS	read-only
    DESCRIPTION
        "(U//FOUO) Implementation of this object can be as low
         as read-only depending on which
         IS Objective or MIB desired requirements are
         not being met by the implementation."

    OBJECT		ipSystemStatsOutFragReqds
    MIN-ACCESS	not-accessible
    DESCRIPTION
        "(U//FOUO) Implementation of this object can be as low
         as not-accessible depending on which
         IS Objective or MIB desired requirements are
         not being met by the implementation."

    OBJECT		ipv6InterfaceReachableTime
    MIN-ACCESS	read-only
    DESCRIPTION
        "(U//FOUO) Implementation of this object can be as low
         as read-only depending on which
         IS Objective or MIB desired requirements are
         not being met by the implementation."

    OBJECT		ipIfStatsReasmOKs
    MIN-ACCESS	read-only
    DESCRIPTION
        "(U//FOUO) Implementation of this object can be as low
         as read-only depending on which
         IS Objective or MIB desired requirements are
         not being met by the implementation."

    OBJECT		mgmdRouterInterfaceQueryInterval
    MIN-ACCESS	not-accessible
    DESCRIPTION
        "(U//FOUO) Implementation of this object can be as low
         as not-accessible depending on which
         IS Objective or MIB desired requirements are
         not being met by the implementation."

    OBJECT		mgmdHostInterfaceVersion
    MIN-ACCESS	read-write
    DESCRIPTION
        "(U//FOUO) Implementation of this object can be as low
         as read-write depending on which
         IS Objective or MIB desired requirements are
         not being met by the implementation."

    OBJECT		snmpTargetAddrTDomain
    MIN-ACCESS	read-write
    DESCRIPTION
        "(U//FOUO) Implementation of this object can be as low
         as read-write depending on which
         IS Objective or MIB desired requirements are
         not being met by the implementation."

    OBJECT		hTPiDestinationAddress
    MIN-ACCESS	not-accessible
    DESCRIPTION
        "(U//FOUO) Implementation of this object can be as low
         as not-accessible depending on which
         IS Objective or MIB desired requirements are
         not being met by the implementation."

    OBJECT		hTPSAHCOctets
    MIN-ACCESS	not-accessible
    DESCRIPTION
        "(U//FOUO) Implementation of this object can be as low
         as not-accessible depending on which
         IS Objective or MIB desired requirements are
         not being met by the implementation."

    OBJECT		tcpInErrs
    MIN-ACCESS	read-only
    DESCRIPTION
        "(U//FOUO) Implementation of this object can be as low
         as read-only depending on which
         IS Objective or MIB desired requirements are
         not being met by the implementation."

    OBJECT		hTPSAPMTU
    MIN-ACCESS	read-only
    DESCRIPTION
        "(U//FOUO) Implementation of this object can be as low
         as read-only depending on which
         IS Objective or MIB desired requirements are
         not being met by the implementation."

    OBJECT		sysName
    MIN-ACCESS	read-write
    DESCRIPTION
        "(U//FOUO) Implementation of this object can be as low
         as read-write depending on which
         IS Objective or MIB desired requirements are
         not being met by the implementation."

    OBJECT		ifIndex
    MIN-ACCESS	read-only
    DESCRIPTION
        "(U//FOUO) Implementation of this object can be as low
         as read-only depending on which
         IS Objective or MIB desired requirements are
         not being met by the implementation."

    OBJECT		ipSystemStatsOutTransmits
    MIN-ACCESS	not-accessible
    DESCRIPTION
        "(U//FOUO) Implementation of this object can be as low
         as not-accessible depending on which
         IS Objective or MIB desired requirements are
         not being met by the implementation."

--    OBJECT		snmpEngine
--    MIN-ACCESS	read-write
--    DESCRIPTION
--        "(U//FOUO) Implementation of this object can be as low
--         as read-write depending on which
--         IS Objective or MIB desired requirements are
--         not being met by the implementation."

    OBJECT		ipSystemStatsOutOctets
    MIN-ACCESS	not-accessible
    DESCRIPTION
        "(U//FOUO) Implementation of this object can be as low
         as not-accessible depending on which
         IS Objective or MIB desired requirements are
         not being met by the implementation."

    OBJECT		hAudThrottleConfigTableLastChanged
    MIN-ACCESS	read-only
    DESCRIPTION
        "(U//FOUO) Implementation of this object can be as low
         as read-only depending on which
         IS Objective or MIB desired requirements are
         not being met by the implementation."

    OBJECT		usmUserStatus
    MIN-ACCESS	read-write
    DESCRIPTION
        "(U//FOUO) Implementation of this object can be as low
         as read-write depending on which
         IS Objective or MIB desired requirements are
         not being met by the implementation."

    OBJECT		ipIfStatsInMcastPkts
    MIN-ACCESS	not-accessible
    DESCRIPTION
        "(U//FOUO) Implementation of this object can be as low
         as not-accessible depending on which
         IS Objective or MIB desired requirements are
         not being met by the implementation."

    OBJECT		usmUserPrivKeyChange
    MIN-ACCESS	read-write
    DESCRIPTION
        "(U//FOUO) Implementation of this object can be as low
         as read-write depending on which
         IS Objective or MIB desired requirements are
         not being met by the implementation."

    OBJECT		hIPhRuleActionIndex
    MIN-ACCESS	read-write
    DESCRIPTION
        "(U//FOUO) Implementation of this object can be as low
         as read-write depending on which
         IS Objective or MIB desired requirements are
         not being met by the implementation."

    OBJECT		hIPhFFSAProcessFlowlabel
    MIN-ACCESS	not-accessible
    DESCRIPTION
        "(U//FOUO) Implementation of this object can be as low
         as not-accessible depending on which
         IS Objective or MIB desired requirements are
         not being met by the implementation."

    OBJECT		ipSystemStatsHCOutForwDatagrams
    MIN-ACCESS	not-accessible
    DESCRIPTION
        "(U//FOUO) Implementation of this object can be as low
         as not-accessible depending on which
         IS Objective or MIB desired requirements are
         not being met by the implementation."

    OBJECT		ipIfStatsOutFragCreates
    MIN-ACCESS	read-only
    DESCRIPTION
        "(U//FOUO) Implementation of this object can be as low
         as read-only depending on which
         IS Objective or MIB desired requirements are
         not being met by the implementation."

    OBJECT		udpInErrors
    MIN-ACCESS	read-only
    DESCRIPTION
        "(U//FOUO) Implementation of this object can be as low
         as read-only depending on which
         IS Objective or MIB desired requirements are
         not being met by the implementation."

    OBJECT		hIPhFFSAConnectionType
    MIN-ACCESS	read-write
    DESCRIPTION
        "(U//FOUO) Implementation of this object can be as low
         as read-write depending on which
         IS Objective or MIB desired requirements are
         not being met by the implementation."

    OBJECT		usmStatsNotInTimeWindows
    MIN-ACCESS	read-only
    DESCRIPTION
        "(U//FOUO) Implementation of this object can be as low
         as read-only depending on which
         IS Objective or MIB desired requirements are
         not being met by the implementation."

    OBJECT		ipIfStatsInOctets
    MIN-ACCESS	not-accessible
    DESCRIPTION
        "(U//FOUO) Implementation of this object can be as low
         as not-accessible depending on which
         IS Objective or MIB desired requirements are
         not being met by the implementation."

    OBJECT		vacmViewSpinLock
    MIN-ACCESS	read-write
    DESCRIPTION
        "(U//FOUO) Implementation of this object can be as low
         as read-write depending on which
         IS Objective or MIB desired requirements are
         not being met by the implementation."

    OBJECT		ipIfStatsOutBcastPkts
    MIN-ACCESS	not-accessible
    DESCRIPTION
        "(U//FOUO) Implementation of this object can be as low
         as not-accessible depending on which
         IS Objective or MIB desired requirements are
         not being met by the implementation."

    OBJECT		snmpProxyDrops
    MIN-ACCESS	not-accessible
    DESCRIPTION
        "(U//FOUO) Implementation of this object can be as low
         as not-accessible depending on which
         IS Objective or MIB desired requirements are
         not being met by the implementation."

    OBJECT		ipIfStatsHCInMcastOctets
    MIN-ACCESS	read-only
    DESCRIPTION
        "(U//FOUO) Implementation of this object can be as low
         as read-only depending on which
         IS Objective or MIB desired requirements are
         not being met by the implementation."

    OBJECT		ipNetToPhysicalState
    MIN-ACCESS	read-only
    DESCRIPTION
        "(U//FOUO) Implementation of this object can be as low
         as read-only depending on which
         IS Objective or MIB desired requirements are
         not being met by the implementation."

--    OBJECT		snmpMPDMIBObjects
--    MIN-ACCESS	read-write
--    DESCRIPTION
--        "(U//FOUO) Implementation of this object can be as low
--         as read-write depending on which
--         IS Objective or MIB desired requirements are
--         not being met by the implementation."

    OBJECT		mgmdRouterInterfaceRobustness
    MIN-ACCESS	not-accessible
    DESCRIPTION
        "(U//FOUO) Implementation of this object can be as low
         as not-accessible depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hTPSARowStatus
    MIN-ACCESS	read-write
    DESCRIPTION
        "(U//FOUO) Implementation of this object can be as low
         as read-write depending on which
         IS Objective or MIB desired requirements are
         not being met by the implementation."

    OBJECT		ifConnectorPresent
    MIN-ACCESS	read-only
    DESCRIPTION
        "(U//FOUO) Implementation of this object can be as low
         as read-only depending on which
         IS Objective or MIB desired requirements are
         not being met by the implementation."

--    OBJECT		usmMIBObjects
--    MIN-ACCESS	read-write
--    DESCRIPTION
--        "(U//FOUO) Implementation of this object can be as low
--         as read-write depending on which
--         IS Objective or MIB desired requirements are
--         not being met by the implementation."

    OBJECT		hAuditConfigTableCount
    MIN-ACCESS	read-only
    DESCRIPTION
        "(U//FOUO) Implementation of this object can be as low
         as read-only depending on which
         IS Objective or MIB desired requirements are
         not being met by the implementation."

    OBJECT		ipSystemStatsInTruncatedPkts
    MIN-ACCESS	not-accessible
    DESCRIPTION
        "(U//FOUO) Implementation of this object can be as low
         as not-accessible depending on which
         IS Objective or MIB desired requirements are
         not being met by the implementation."

    OBJECT		ipSystemStatsInDiscards
    MIN-ACCESS	not-accessible
    DESCRIPTION
        "(U//FOUO) Implementation of this object can be as low
         as not-accessible depending on which
         IS Objective or MIB desired requirements are
         not being met by the implementation."

    OBJECT		hFdErrorCode
    MIN-ACCESS	accessible-for-notify
    DESCRIPTION
        "(U//FOUO) Implementation of this object can be as low
         as accessible-for-notify depending on which
         IS Objective or MIB desired requirements are
         not being met by the implementation."

    OBJECT		ipIfStatsHCInOctets
    MIN-ACCESS	read-only
    DESCRIPTION
        "(U//FOUO) Implementation of this object can be as low
         as read-only depending on which
         IS Objective or MIB desired requirements are
         not being met by the implementation."

    OBJECT		hIPhFFSAECN
    MIN-ACCESS	read-write
    DESCRIPTION
        "(U//FOUO) Implementation of this object can be as low
         as read-write depending on which
         IS Objective or MIB desired requirements are
         not being met by the implementation."

--    OBJECT		usmHMACSHAAuthProtocol
--    MIN-ACCESS	read-write
--    DESCRIPTION
--        "(U//FOUO) Implementation of this object can be as low
--         as read-write depending on which
--         IS Objective or MIB desired requirements are
--         not being met by the implementation."

    OBJECT		usmStatsUnknownEngineIDs
    MIN-ACCESS	read-only
    DESCRIPTION
        "(U//FOUO) Implementation of this object can be as low
         as read-only depending on which
         IS Objective or MIB desired requirements are
         not being met by the implementation."

    OBJECT		ifPromiscuousMode
    MIN-ACCESS	not-accessible
    DESCRIPTION
        "(U//FOUO) Implementation of this object can be as low
         as not-accessible depending on which
         IS Objective or MIB desired requirements are
         not being met by the implementation."

    OBJECT		ipSystemStatsInMcastPkts
    MIN-ACCESS	not-accessible
    DESCRIPTION
        "(U//FOUO) Implementation of this object can be as low
         as not-accessible depending on which
         IS Objective or MIB desired requirements are
         not being met by the implementation."

    OBJECT		ipv4InterfaceReasmMaxSize
    MIN-ACCESS	read-only
    DESCRIPTION
        "(U//FOUO) Implementation of this object can be as low
         as read-only depending on which
         IS Objective or MIB desired requirements are
         not being met by the implementation."

    OBJECT		ipSystemStatsOutDiscards
    MIN-ACCESS	not-accessible
    DESCRIPTION
        "(U//FOUO) Implementation of this object can be as low
         as not-accessible depending on which
         IS Objective or MIB desired requirements are
         not being met by the implementation."

    OBJECT		hIPhFFSADSCPValue
    MIN-ACCESS	read-write
    DESCRIPTION
        "(U//FOUO) Implementation of this object can be as low
         as read-write depending on which
         IS Objective or MIB desired requirements are
         not being met by the implementation."

    OBJECT		inetCidrRouteMetric5
    MIN-ACCESS	read-write
    DESCRIPTION
        "(U//FOUO) Implementation of this object can be as low
         as read-write depending on which
         IS Objective or MIB desired requirements are
         not being met by the implementation."

    OBJECT		hFdErrorDetail
    MIN-ACCESS	accessible-for-notify
    DESCRIPTION
        "(U//FOUO) Implementation of this object can be as low
         as accessible-for-notify depending on which
         IS Objective or MIB desired requirements are
         not being met by the implementation."

    OBJECT		hIPhFFSARetryICMPCount
    MIN-ACCESS	read-write
    DESCRIPTION
        "(U//FOUO) Implementation of this object can be as low
         as read-write depending on which
         IS Objective or MIB desired requirements are
         not being met by the implementation."

    OBJECT		ipSystemStatsHCOutRequests
    MIN-ACCESS	not-accessible
    DESCRIPTION
        "(U//FOUO) Implementation of this object can be as low
         as not-accessible depending on which
         IS Objective or MIB desired requirements are
         not being met by the implementation."

    OBJECT		hTPSARemoteCredentialType
    MIN-ACCESS	not-accessible
    DESCRIPTION
        "(U//FOUO) Implementation of this object can be as low
         as not-accessible depending on which
         IS Objective or MIB desired requirements are
         not being met by the implementation."

--    OBJECT		hIfAddrAssignmentTable
--    MIN-ACCESS	read-only
--    DESCRIPTION
--        "(U//FOUO) Implementation of this object can be as low
--         as read-only depending on which
--         IS Objective or MIB desired requirements are
--         not being met by the implementation."

    OBJECT		sysServices
    MIN-ACCESS	read-only
    DESCRIPTION
        "(U//FOUO) Implementation of this object can be as low
         as read-only depending on which
         IS Objective or MIB desired requirements are
         not being met by the implementation."

    OBJECT		mgmdHostCacheUpTime
    MIN-ACCESS	read-only
    DESCRIPTION
        "(U//FOUO) Implementation of this object can be as low
         as read-only depending on which
         IS Objective or MIB desired requirements are
         not being met by the implementation."

--    OBJECT		snmpFrameworkMIBConformance
--    MIN-ACCESS	read-write
--    DESCRIPTION
--        "(U//FOUO) Implementation of this object can be as low
--         as read-write depending on which
--         IS Objective or MIB desired requirements are
--         not being met by the implementation."

    OBJECT		usmUserSpinLock
    MIN-ACCESS	read-write
    DESCRIPTION
        "(U//FOUO) Implementation of this object can be as low
         as read-write depending on which
         IS Objective or MIB desired requirements are
         not being met by the implementation."

    OBJECT		hTPSAHCMcastPkts
    MIN-ACCESS	not-accessible
    DESCRIPTION
        "(U//FOUO) Implementation of this object can be as low
         as not-accessible depending on which
         IS Objective or MIB desired requirements are
         not being met by the implementation."

    OBJECT		hIPhRuleTableLastChanged
    MIN-ACCESS	read-only
    DESCRIPTION
        "(U//FOUO) Implementation of this object can be as low
         as read-only depending on which
         IS Objective or MIB desired requirements are
         not being met by the implementation."

--    OBJECT		hAudNotificationLogWarning
--    MIN-ACCESS	accessible-for-notify
--    DESCRIPTION
--        "(U//FOUO) Implementation of this object can be as low
--         as accessible-for-notify depending on which
--         IS Objective or MIB desired requirements are
--         not being met by the implementation."

    OBJECT		hTPSALocalPTAddress
    MIN-ACCESS	read-write
    DESCRIPTION
        "(U//FOUO) Implementation of this object can be as low
         as read-write depending on which
         IS Objective or MIB desired requirements are
         not being met by the implementation."

    OBJECT		vacmGroupName
    MIN-ACCESS	read-write
    DESCRIPTION
        "(U//FOUO) Implementation of this object can be as low
         as read-write depending on which
         IS Objective or MIB desired requirements are
         not being met by the implementation."

    OBJECT		hPPKChainIntegrityAlgorithm
    MIN-ACCESS	not-accessible
    DESCRIPTION
        "(U//FOUO) Implementation of this object can be as low
         as not-accessible depending on which
         IS Objective or MIB desired requirements are
         not being met by the implementation."

--    OBJECT		usmNoAuthProtocol
--    MIN-ACCESS	read-write
--    DESCRIPTION
--        "(U//FOUO) Implementation of this object can be as low
--         as read-write depending on which
--         IS Objective or MIB desired requirements are
--         not being met by the implementation."

--    OBJECT		hBatteryTable
--    MIN-ACCESS	read-only
--    DESCRIPTION
--        "(U//FOUO) Implementation of this object can be as low
--         as read-only depending on which
--         IS Objective or MIB desired requirements are
--         not being met by the implementation."

    OBJECT		hIPhFFSADecrementTTL
    MIN-ACCESS	read-only
    DESCRIPTION
        "(U//FOUO) Implementation of this object can be as low
         as read-only depending on which
         IS Objective or MIB desired requirements are
         not being met by the implementation."

    OBJECT		tcpListenerProcess
    MIN-ACCESS	read-only
    DESCRIPTION
        "(U//FOUO) Implementation of this object can be as low
         as read-only depending on which
         IS Objective or MIB desired requirements are
         not being met by the implementation."

    OBJECT		snmpInPkts
    MIN-ACCESS	read-only
    DESCRIPTION
        "(U//FOUO) Implementation of this object can be as low
         as read-only depending on which
         IS Objective or MIB desired requirements are
         not being met by the implementation."

--    OBJECT		hBatteryOK
--    MIN-ACCESS	not-accessible
--    DESCRIPTION
--        "(U//FOUO) Implementation of this object can be as low
--         as not-accessible depending on which
--         IS Objective or MIB desired requirements are
--         not being met by the implementation."

--    OBJECT		vacmMIBViews
--    MIN-ACCESS	read-write
--    DESCRIPTION
--        "(U//FOUO) Implementation of this object can be as low
--         as read-write depending on which
--         IS Objective or MIB desired requirements are
--         not being met by the implementation."

    OBJECT		ipSystemStatsReasmReqds
    MIN-ACCESS	not-accessible
    DESCRIPTION
        "(U//FOUO) Implementation of this object can be as low
         as not-accessible depending on which
         IS Objective or MIB desired requirements are
         not being met by the implementation."

    OBJECT		hIfv4HaipeTableLastChanged
    MIN-ACCESS	read-only
    DESCRIPTION
        "(U//FOUO) Implementation of this object can be as low
         as read-only depending on which
         IS Objective or MIB desired requirements are
         not being met by the implementation."

    OBJECT		hTPSALocalCredentialType
    MIN-ACCESS	not-accessible
    DESCRIPTION
        "(U//FOUO) Implementation of this object can be as low
         as not-accessible depending on which
         IS Objective or MIB desired requirements are
         not being met by the implementation."

    OBJECT		hIPhFFSADIndexType
    MIN-ACCESS	read-write
    DESCRIPTION
        "(U//FOUO) Implementation of this object can be as low
         as read-write depending on which
         IS Objective or MIB desired requirements are
         not being met by the implementation."

    OBJECT		hTPSAPDUNEnabled
    MIN-ACCESS	read-write
    DESCRIPTION
        "(U//FOUO) Implementation of this object can be as low
         as read-write depending on which
         IS Objective or MIB desired requirements are
         not being met by the implementation."

    OBJECT		mgmdHostCacheLastReporter
    MIN-ACCESS	read-only
    DESCRIPTION
        "(U//FOUO) Implementation of this object can be as low
         as read-only depending on which
         IS Objective or MIB desired requirements are
         not being met by the implementation."

    OBJECT		snmpNotifyRowStatus
    MIN-ACCESS	read-write
    DESCRIPTION
        "(U//FOUO) Implementation of this object can be as low
         as read-write depending on which
         IS Objective or MIB desired requirements are
         not being met by the implementation."

    OBJECT		inetCidrRouteMetric4
    MIN-ACCESS	read-write
    DESCRIPTION
        "(U//FOUO) Implementation of this object can be as low
         as read-write depending on which
         IS Objective or MIB desired requirements are
         not being met by the implementation."

    OBJECT		ifName
    MIN-ACCESS	read-only
    DESCRIPTION
        "(U//FOUO) Implementation of this object can be as low
         as read-only depending on which
         IS Objective or MIB desired requirements are
         not being met by the implementation."

    OBJECT		mgmdRouterSrcListExpire
    MIN-ACCESS	not-accessible
    DESCRIPTION
        "(U//FOUO) Implementation of this object can be as low
         as not-accessible depending on which
         IS Objective or MIB desired requirements are
         not being met by the implementation."

    OBJECT		nlmLogVariableTimeTicksVal
    MIN-ACCESS	read-only
    DESCRIPTION
        "(U//FOUO) Implementation of this object can be as low
         as read-only depending on which
         IS Objective or MIB desired requirements are
         not being met by the implementation."

    OBJECT		ipIfStatsHCOutTransmits
    MIN-ACCESS	read-only
    DESCRIPTION
        "(U//FOUO) Implementation of this object can be as low
         as read-only depending on which
         IS Objective or MIB desired requirements are
         not being met by the implementation."

    OBJECT		nlmLogTime
    MIN-ACCESS	read-only
    DESCRIPTION
        "(U//FOUO) Implementation of this object can be as low
         as read-only depending on which
         IS Objective or MIB desired requirements are
         not being met by the implementation."

    OBJECT		tcpHCOutSegs
    MIN-ACCESS	read-only
    DESCRIPTION
        "(U//FOUO) Implementation of this object can be as low
         as read-only depending on which
         IS Objective or MIB desired requirements are
         not being met by the implementation."

    OBJECT		hAudCfgNotifThrottled
    MIN-ACCESS	read-only
    DESCRIPTION
        "(U//FOUO) Implementation of this object can be as low
         as read-only depending on which
         IS Objective or MIB desired requirements are
         not being met by the implementation."

    OBJECT		hTPiSPI
    MIN-ACCESS	not-accessible
    DESCRIPTION
        "(U//FOUO) Implementation of this object can be as low
         as not-accessible depending on which
         IS Objective or MIB desired requirements are
         not being met by the implementation."

    OBJECT		snmpInBadVersions
    MIN-ACCESS	read-only
    DESCRIPTION
        "(U//FOUO) Implementation of this object can be as low
         as read-only depending on which
         IS Objective or MIB desired requirements are
         not being met by the implementation."

    OBJECT		usmUserSecurityName
    MIN-ACCESS	read-only
    DESCRIPTION
        "(U//FOUO) Implementation of this object can be as low
         as read-only depending on which
         IS Objective or MIB desired requirements are
         not being met by the implementation."

    OBJECT		hPPKEKUniversalID
    MIN-ACCESS	read-write
    DESCRIPTION
        "(U//FOUO) Implementation of this object can be as low
         as read-write depending on which
         IS Objective or MIB desired requirements are
         not being met by the implementation."

    OBJECT		hBatteryNumber
    MIN-ACCESS	read-only
    DESCRIPTION
        "(U//FOUO) Implementation of this object can be as low
         as read-only depending on which
         IS Objective or MIB desired requirements are
         not being met by the implementation."

    OBJECT		ipIfStatsHCInReceives
    MIN-ACCESS	read-only
    DESCRIPTION
        "(U//FOUO) Implementation of this object can be as low
         as read-only depending on which
         IS Objective or MIB desired requirements are
         not being met by the implementation."

    OBJECT		ipIfStatsInForwDatagrams
    MIN-ACCESS	not-accessible
    DESCRIPTION
        "(U//FOUO) Implementation of this object can be as low
         as not-accessible depending on which
         IS Objective or MIB desired requirements are
         not being met by the implementation."

    OBJECT		sysContact
    MIN-ACCESS	read-write
    DESCRIPTION
        "(U//FOUO) Implementation of this object can be as low
         as read-write depending on which
         IS Objective or MIB desired requirements are
         not being met by the implementation."

    OBJECT		hLocalCKListUniversal
    MIN-ACCESS	read-only
    DESCRIPTION
        "(U//FOUO) Implementation of this object can be as low
         as read-only depending on which
         IS Objective or MIB desired requirements are
         not being met by the implementation."

    OBJECT		inetCidrRouteType
    MIN-ACCESS	read-write
    DESCRIPTION
        "(U//FOUO) Implementation of this object can be as low
         as read-write depending on which
         IS Objective or MIB desired requirements are
         not being met by the implementation."

    OBJECT		ipIfStatsOutFragReqds
    MIN-ACCESS	read-only
    DESCRIPTION
        "(U//FOUO) Implementation of this object can be as low
         as read-only depending on which
         IS Objective or MIB desired requirements are
         not being met by the implementation."

    OBJECT		udpNoPorts
    MIN-ACCESS	read-only
    DESCRIPTION
        "(U//FOUO) Implementation of this object can be as low
         as read-only depending on which
         IS Objective or MIB desired requirements are
         not being met by the implementation."

    OBJECT		ifHCInMulticastPkts
    MIN-ACCESS	read-only
    DESCRIPTION
        "(U//FOUO) Implementation of this object can be as low
         as read-only depending on which
         IS Objective or MIB desired requirements are
         not being met by the implementation."

    OBJECT		hTPSAStartTime
    MIN-ACCESS	read-write
    DESCRIPTION
        "(U//FOUO) Implementation of this object can be as low
         as read-write depending on which
         IS Objective or MIB desired requirements are
         not being met by the implementation."

    OBJECT		ipSystemStatsInHdrErrors
    MIN-ACCESS	not-accessible
    DESCRIPTION
        "(U//FOUO) Implementation of this object can be as low
         as not-accessible depending on which
         IS Objective or MIB desired requirements are
         not being met by the implementation."

    OBJECT		hTPSASelectorNextHeaderOpt1End
    MIN-ACCESS	not-accessible
    DESCRIPTION
        "(U//FOUO) Implementation of this object can be as low
         as not-accessible depending on which
         IS Objective or MIB desired requirements are
         not being met by the implementation."

    OBJECT		hFdsLastChanged
    MIN-ACCESS	read-only
    DESCRIPTION
        "(U//FOUO) Implementation of this object can be as low
         as read-only depending on which
         IS Objective or MIB desired requirements are
         not being met by the implementation."

    OBJECT		nlmLogContextEngineID
    MIN-ACCESS	read-only
    DESCRIPTION
        "(U//FOUO) Implementation of this object can be as low
         as read-only depending on which
         IS Objective or MIB desired requirements are
         not being met by the implementation."

    OBJECT		snmpTrapEnterprise
    MIN-ACCESS	accessible-for-notify
    DESCRIPTION
        "(U//FOUO) Implementation of this object can be as low
         as accessible-for-notify depending on which
         IS Objective or MIB desired requirements are
         not being met by the implementation."

    OBJECT		hTPSATableLastChanged
    MIN-ACCESS	read-only
    DESCRIPTION
        "(U//FOUO) Implementation of this object can be as low
         as read-only depending on which
         IS Objective or MIB desired requirements are
         not being met by the implementation."

    OBJECT		ipSystemStatsOutForwDatagrams
    MIN-ACCESS	not-accessible
    DESCRIPTION
        "(U//FOUO) Implementation of this object can be as low
         as not-accessible depending on which
         IS Objective or MIB desired requirements are
         not being met by the implementation."

    OBJECT		mgmdHostInterfaceVersion3Robustness
    MIN-ACCESS	read-write
    DESCRIPTION
        "(U//FOUO) Implementation of this object can be as low
         as read-write depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hTPSARemoteCredentialID
    MIN-ACCESS	not-accessible
    DESCRIPTION
        "(U//FOUO) Implementation of this object can be as low
         as not-accessible depending on which
         IS Objective or MIB desired requirements are
         not being met by the implementation."

    OBJECT		tcpRtoMin
    MIN-ACCESS	read-only
    DESCRIPTION
        "(U//FOUO) Implementation of this object can be as low
         as read-only depending on which
         IS Objective or MIB desired requirements are
         not being met by the implementation."

    OBJECT		ipIfStatsOutMcastOctets
    MIN-ACCESS	not-accessible
    DESCRIPTION
        "(U//FOUO) Implementation of this object can be as low
         as not-accessible depending on which
         IS Objective or MIB desired requirements are
         not being met by the implementation."

    OBJECT		tcpConnectionState
    MIN-ACCESS	read-only
    DESCRIPTION
        "(U//FOUO) Implementation of this object can be as low
         as read-only depending on which
         IS Objective or MIB desired requirements are
         not being met by the implementation."

    OBJECT		hSpinLock
    MIN-ACCESS	read-write
    DESCRIPTION
        "(U//FOUO) Implementation of this object can be as low
         as read-write depending on which
         IS Objective or MIB desired requirements are
         not being met by the implementation."

--    OBJECT		snmpMPDCompliance
--    MIN-ACCESS	read-write
--    DESCRIPTION
--        "(U//FOUO) Implementation of this object can be as low
--         as read-write depending on which
--         IS Objective or MIB desired requirements are
--         not being met by the implementation."

    OBJECT		sysORLastChange
    MIN-ACCESS	read-only
    DESCRIPTION
        "(U//FOUO) Implementation of this object can be as low
         as read-only depending on which
         IS Objective or MIB desired requirements are
         not being met by the implementation."

    OBJECT		snmpInBadCommunityNames
    MIN-ACCESS	not-accessible
    DESCRIPTION
        "(U//FOUO) Implementation of this object can be as low
         as not-accessible depending on which
         IS Objective or MIB desired requirements are
         not being met by the implementation."

--    OBJECT		usmMIBCompliance
--    MIN-ACCESS	read-write
--    DESCRIPTION
--        "(U//FOUO) Implementation of this object can be as low
--         as read-write depending on which
--         IS Objective or MIB desired requirements are
--         not being met by the implementation."

    OBJECT		hTPSAAddressType
    MIN-ACCESS	read-write
    DESCRIPTION
        "(U//FOUO) Implementation of this object can be as low
         as read-write depending on which
         IS Objective or MIB desired requirements are
         not being met by the implementation."

    OBJECT		vacmAccessStatus
    MIN-ACCESS	read-write
    DESCRIPTION
        "(U//FOUO) Implementation of this object can be as low
         as read-write depending on which
         IS Objective or MIB desired requirements are
         not being met by the implementation."

--    OBJECT		hPPKEKTable
--    MIN-ACCESS	read-only
--    DESCRIPTION
--        "(U//FOUO) Implementation of this object can be as low
--         as read-only depending on which
--         IS Objective or MIB desired requirements are
--         not being met by the implementation."

--    OBJECT		snmpFrameworkMIBObjects
--    MIN-ACCESS	read-write
--    DESCRIPTION
--        "(U//FOUO) Implementation of this object can be as low
--         as read-write depending on which
--         IS Objective or MIB desired requirements are
--         not being met by the implementation."

--    OBJECT		snmpNotifyGroups
--    MIN-ACCESS	read-write
--    DESCRIPTION
--        "(U//FOUO) Implementation of this object can be as low
--         as read-write depending on which
--         IS Objective or MIB desired requirements are
--         not being met by the implementation."

    OBJECT		hiaaInterface
    MIN-ACCESS	read-write
    DESCRIPTION
        "(U//FOUO) Implementation of this object can be as low
         as read-write depending on which
         IS Objective or MIB desired requirements are
         not being met by the implementation."

    OBJECT		sysORUpTime
    MIN-ACCESS	not-accessible
    DESCRIPTION
        "(U//FOUO) Implementation of this object can be as low
         as not-accessible depending on which
         IS Objective or MIB desired requirements are
         not being met by the implementation."

--    OBJECT		hFirmwareInstallFailed
--    MIN-ACCESS	accessible-for-notify
--    DESCRIPTION
--        "(U//FOUO) Implementation of this object can be as low
--         as accessible-for-notify depending on which
--         IS Objective or MIB desired requirements are
--         not being met by the implementation."

    OBJECT		hAudCfgID
    MIN-ACCESS	read-only
    DESCRIPTION
        "(U//FOUO) Implementation of this object can be as low
         as read-only depending on which
         IS Objective or MIB desired requirements are
         not being met by the implementation."

    OBJECT		hPPKChainTableLastChanged
    MIN-ACCESS	read-only
    DESCRIPTION
        "(U//FOUO) Implementation of this object can be as low
         as read-only depending on which
         IS Objective or MIB desired requirements are
         not being met by the implementation."

    OBJECT		hTPSAICV
    MIN-ACCESS	not-accessible
    DESCRIPTION
        "(U//FOUO) Implementation of this object can be as low
         as not-accessible depending on which
         IS Objective or MIB desired requirements are
         not being met by the implementation."

    OBJECT		haipeResetDevice
    MIN-ACCESS	read-write
    DESCRIPTION
        "(U//FOUO) Implementation of this object can be as low
         as read-write depending on which
         IS Objective or MIB desired requirements are
         not being met by the implementation."

    OBJECT		hIPhSelectorType
    MIN-ACCESS	read-write
    DESCRIPTION
        "(U//FOUO) Implementation of this object can be as low
         as read-write depending on which
         IS Objective or MIB desired requirements are
         not being met by the implementation."

    OBJECT		hiaaRowStatus
    MIN-ACCESS	read-write
    DESCRIPTION
        "(U//FOUO) Implementation of this object can be as low
         as read-write depending on which
         IS Objective or MIB desired requirements are
         not being met by the implementation."

    OBJECT		ipSystemStatsInNoRoutes
    MIN-ACCESS	not-accessible
    DESCRIPTION
        "(U//FOUO) Implementation of this object can be as low
         as not-accessible depending on which
         IS Objective or MIB desired requirements are
         not being met by the implementation."

    OBJECT		tcpRtoAlgorithm
    MIN-ACCESS	read-only
    DESCRIPTION
        "(U//FOUO) Implementation of this object can be as low
         as read-only depending on which
         IS Objective or MIB desired requirements are
         not being met by the implementation."

    OBJECT		snmpTargetParamsStorageType
    MIN-ACCESS	read-write
    DESCRIPTION
        "(U//FOUO) Implementation of this object can be as low
         as read-write depending on which
         IS Objective or MIB desired requirements are
         not being met by the implementation."

--    OBJECT		vacmMIBCompliances
--    MIN-ACCESS	read-write
--    DESCRIPTION
--        "(U//FOUO) Implementation of this object can be as low
--         as read-write depending on which
--         IS Objective or MIB desired requirements are
--         not being met by the implementation."

    OBJECT		hPPKEKTableMaxCount
    MIN-ACCESS	read-only
    DESCRIPTION
        "(U//FOUO) Implementation of this object can be as low
         as read-only depending on which
         IS Objective or MIB desired requirements are
         not being met by the implementation."

    OBJECT		ipSystemStatsInOctets
    MIN-ACCESS	not-accessible
    DESCRIPTION
        "(U//FOUO) Implementation of this object can be as low
         as not-accessible depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		inetCidrRouteNumber
    MIN-ACCESS	read-only
    DESCRIPTION
        "(U//FOUO) Implementation of this object can be as low
         as read-only depending on which
         IS Objective or MIB desired requirements are
         not being met by the implementation."

    OBJECT		ipIfStatsInTruncatedPkts
    MIN-ACCESS	read-only
    DESCRIPTION
        "(U//FOUO) Implementation of this object can be as low
         as read-only depending on which
         IS Objective or MIB desired requirements are
         not being met by the implementation."

    OBJECT		ipSystemStatsHCInMcastPkts
    MIN-ACCESS	not-accessible
    DESCRIPTION
        "(U//FOUO) Implementation of this object can be as low
         as not-accessible depending on which
         IS Objective or MIB desired requirements are
         not being met by the implementation."

    OBJECT		ipv6IpForwarding
    MIN-ACCESS	read-only
    DESCRIPTION
        "(U//FOUO) Implementation of this object can be as low
         as read-only depending on which
         IS Objective or MIB desired requirements are
         not being met by the implementation."

    OBJECT		hPPKChainRowStatus
    MIN-ACCESS	read-write
    DESCRIPTION
        "(U//FOUO) Implementation of this object can be as low
         as read-write depending on which
         IS Objective or MIB desired requirements are
         not being met by the implementation."

    OBJECT		hTPSAPTAddressType
    MIN-ACCESS	read-write
    DESCRIPTION
        "(U//FOUO) Implementation of this object can be as low
         as read-write depending on which
         IS Objective or MIB desired requirements are
         not being met by the implementation."

    OBJECT		ifOutQLen
    MIN-ACCESS	not-accessible
    DESCRIPTION
        "(U//FOUO) Implementation of this object can be as low
         as not-accessible depending on which
         IS Objective or MIB desired requirements are
         not being met by the implementation."

    OBJECT		mgmdRouterCacheExpiryTime
    MIN-ACCESS	not-accessible
    DESCRIPTION
        "(U//FOUO) Implementation of this object can be as low
         as not-accessible depending on which
         IS Objective or MIB desired requirements are
         not being met by the implementation."

    OBJECT		hPPKKeyExpirationWarningCount
    MIN-ACCESS	accessible-for-notify
    DESCRIPTION
        "(U//FOUO) Implementation of this object can be as low
         as accessible-for-notify depending on which
         IS Objective or MIB desired requirements are
         not being met by the implementation."

    OBJECT		ipSystemStatsOutFragOKs
    MIN-ACCESS	not-accessible
    DESCRIPTION
        "(U//FOUO) Implementation of this object can be as low
         as not-accessible depending on which
         IS Objective or MIB desired requirements are
         not being met by the implementation."

    OBJECT		ipv4InterfaceEnableStatus
    MIN-ACCESS	read-write
    DESCRIPTION
        "(U//FOUO) Implementation of this object can be as low
         as read-write depending on which
         IS Objective or MIB desired requirements are
         not being met by the implementation."

    OBJECT		ifMtu
    MIN-ACCESS	read-only
    DESCRIPTION
        "(U//FOUO) Implementation of this object can be as low
         as read-only depending on which
         IS Objective or MIB desired requirements are
         not being met by the implementation."

    OBJECT		hAudCfgLogCount
    MIN-ACCESS	read-only
    DESCRIPTION
        "(U//FOUO) Implementation of this object can be as low
         as read-only depending on which
         IS Objective or MIB desired requirements are
         not being met by the implementation."

    OBJECT		ipForwarding
    MIN-ACCESS	read-only
    DESCRIPTION
        "(U//FOUO) Implementation of this object can be as low
         as read-only depending on which
         IS Objective or MIB desired requirements are
         not being met by the implementation."

    OBJECT		nlmLogVariableOctetStringVal
    MIN-ACCESS	read-only
    DESCRIPTION
        "(U//FOUO) Implementation of this object can be as low
         as read-only depending on which
         IS Objective or MIB desired requirements are
         not being met by the implementation."

    OBJECT		ipIfStatsInDiscards
    MIN-ACCESS	read-only
    DESCRIPTION
        "(U//FOUO) Implementation of this object can be as low
         as read-only depending on which
         IS Objective or MIB desired requirements are
         not being met by the implementation."

    OBJECT		ifHCOutBroadcastPkts
    MIN-ACCESS	read-only
    DESCRIPTION
        "(U//FOUO) Implementation of this object can be as low
         as read-only depending on which
         IS Objective or MIB desired requirements are
         not being met by the implementation."

    OBJECT		ipIfStatsOutDiscards
    MIN-ACCESS	read-only
    DESCRIPTION
        "(U//FOUO) Implementation of this object can be as low
         as read-only depending on which
         IS Objective or MIB desired requirements are
         not being met by the implementation."

    OBJECT		ipIfStatsOutFragOKs
    MIN-ACCESS	read-only
    DESCRIPTION
        "(U//FOUO) Implementation of this object can be as low
         as read-only depending on which
         IS Objective or MIB desired requirements are
         not being met by the implementation."

    OBJECT		hTPSARemotePTAddress
    MIN-ACCESS	read-write
    DESCRIPTION
        "(U//FOUO) Implementation of this object can be as low
         as read-write depending on which
         IS Objective or MIB desired requirements are
         not being met by the implementation."

    OBJECT		inetCidrRouteMetric1
    MIN-ACCESS	read-write
    DESCRIPTION
        "(U//FOUO) Implementation of this object can be as low
         as read-write depending on which
         IS Objective or MIB desired requirements are
         not being met by the implementation."

    OBJECT		inetCidrRouteStatus
    MIN-ACCESS	read-write
    DESCRIPTION
        "(U//FOUO) Implementation of this object can be as low
         as read-write depending on which
         IS Objective or MIB desired requirements are
         not being met by the implementation."

    OBJECT		mgmdRouterCacheSourceFilterMode
    MIN-ACCESS	not-accessible
    DESCRIPTION
        "(U//FOUO) Implementation of this object can be as low
         as not-accessible depending on which
         IS Objective or MIB desired requirements are
         not being met by the implementation."

    OBJECT		hPreplacedKeyTableLastChanged
    MIN-ACCESS	read-only
    DESCRIPTION
        "(U//FOUO) Implementation of this object can be as low
         as read-only depending on which
         IS Objective or MIB desired requirements are
         not being met by the implementation."

    OBJECT		ipIfStatsInNoRoutes
    MIN-ACCESS	read-only
    DESCRIPTION
        "(U//FOUO) Implementation of this object can be as low
         as read-only depending on which
         IS Objective or MIB desired requirements are
         not being met by the implementation."

    OBJECT		hAudCfgNotifCount
    MIN-ACCESS	read-only
    DESCRIPTION
        "(U//FOUO) Implementation of this object can be as low
         as read-only depending on which
         IS Objective or MIB desired requirements are
         not being met by the implementation."

--    OBJECT		snmpFrameworkMIBGroups
--    MIN-ACCESS	read-write
--    DESCRIPTION
--        "(U//FOUO) Implementation of this object can be as low
--         as read-write depending on which
--         IS Objective or MIB desired requirements are
--         not being met by the implementation."

    OBJECT		hTPSACreationReason
    MIN-ACCESS	read-only
    DESCRIPTION
        "(U//FOUO) Implementation of this object can be as low
         as read-only depending on which
         IS Objective or MIB desired requirements are
         not being met by the implementation."

    OBJECT		ipSystemStatsOutBcastPkts
    MIN-ACCESS	not-accessible
    DESCRIPTION
        "(U//FOUO) Implementation of this object can be as low
         as not-accessible depending on which
         IS Objective or MIB desired requirements are
         not being met by the implementation."

    OBJECT		ifOperStatus
    MIN-ACCESS	read-only
    DESCRIPTION
        "(U//FOUO) Implementation of this object can be as low
         as read-only depending on which
         IS Objective or MIB desired requirements are
         not being met by the implementation."

    OBJECT		nlmLogVariableValueType
    MIN-ACCESS	read-only
    DESCRIPTION
        "(U//FOUO) Implementation of this object can be as low
         as read-only depending on which
         IS Objective or MIB desired requirements are
         not being met by the implementation."

    OBJECT		ipv4InterfaceRetransmitTime
    MIN-ACCESS	read-only
    DESCRIPTION
        "(U//FOUO) Implementation of this object can be as low
         as read-only depending on which
         IS Objective or MIB desired requirements are
         not being met by the implementation."

    OBJECT		ifHCOutUcastPkts
    MIN-ACCESS	read-only
    DESCRIPTION
        "(U//FOUO) Implementation of this object can be as low
         as read-only depending on which
         IS Objective or MIB desired requirements are
         not being met by the implementation."

    OBJECT		inetCidrRouteProto
    MIN-ACCESS	read-only
    DESCRIPTION
        "(U//FOUO) Implementation of this object can be as low
         as read-only depending on which
         IS Objective or MIB desired requirements are
         not being met by the implementation."

    OBJECT		ipSystemStatsHCOutMcastPkts
    MIN-ACCESS	not-accessible
    DESCRIPTION
        "(U//FOUO) Implementation of this object can be as low
         as not-accessible depending on which
         IS Objective or MIB desired requirements are
         not being met by the implementation."

    OBJECT		vacmAccessWriteViewName
    MIN-ACCESS	read-write
    DESCRIPTION
        "(U//FOUO) Implementation of this object can be as low
         as read-write depending on which
         IS Objective or MIB desired requirements are
         not being met by the implementation."

    OBJECT		hPPKChainID
    MIN-ACCESS	read-write
    DESCRIPTION
        "(U//FOUO) Implementation of this object can be as low
         as read-write depending on which
         IS Objective or MIB desired requirements are
         not being met by the implementation."

    OBJECT		hPPKZeroizeKey
    MIN-ACCESS	read-only
    DESCRIPTION
        "(U//FOUO) Implementation of this object can be as low
         as read-only depending on which
         IS Objective or MIB desired requirements are
         not being met by the implementation."

    OBJECT		ipSystemStatsOutFragCreates
    MIN-ACCESS	not-accessible
    DESCRIPTION
        "(U//FOUO) Implementation of this object can be as low
         as not-accessible depending on which
         IS Objective or MIB desired requirements are
         not being met by the implementation."

    OBJECT		sysDescr
    MIN-ACCESS	read-only
    DESCRIPTION
        "(U//FOUO) Implementation of this object can be as low
         as read-only depending on which
         IS Objective or MIB desired requirements are
         not being met by the implementation."

--    OBJECT		snmpMPDStats
--    MIN-ACCESS	read-write
--    DESCRIPTION
--        "(U//FOUO) Implementation of this object can be as low
--         as read-write depending on which
--         IS Objective or MIB desired requirements are
--         not being met by the implementation."

    OBJECT		ipIfStatsReasmReqds
    MIN-ACCESS	read-only
    DESCRIPTION
        "(U//FOUO) Implementation of this object can be as low
         as read-only depending on which
         IS Objective or MIB desired requirements are
         not being met by the implementation."

--    OBJECT		snmpNotifyCompliances
--    MIN-ACCESS	read-write
--    DESCRIPTION
--        "(U//FOUO) Implementation of this object can be as low
--         as read-write depending on which
--         IS Objective or MIB desired requirements are
--         not being met by the implementation."

    OBJECT		usmStatsUnsupportedSecLevels
    MIN-ACCESS	read-only
    DESCRIPTION
        "(U//FOUO) Implementation of this object can be as low
         as read-only depending on which
         IS Objective or MIB desired requirements are
         not being met by the implementation."

--    OBJECT		hAudNotificationLogOk
--    MIN-ACCESS	accessible-for-notify
--    DESCRIPTION
--        "(U//FOUO) Implementation of this object can be as low
--         as accessible-for-notify depending on which
--         IS Objective or MIB desired requirements are
--         not being met by the implementation."

    OBJECT		inetCidrRouteAge
    MIN-ACCESS	read-only
    DESCRIPTION
        "(U//FOUO) Implementation of this object can be as low
         as read-only depending on which
         IS Objective or MIB desired requirements are
         not being met by the implementation."

    OBJECT		hTPiSADestroyedReason
    MIN-ACCESS	not-accessible
    DESCRIPTION
        "(U//FOUO) Implementation of this object can be as low
         as not-accessible depending on which
         IS Objective or MIB desired requirements are
         not being met by the implementation."

    OBJECT		hTPSAHCBrdcastPkts
    MIN-ACCESS	not-accessible
    DESCRIPTION
        "(U//FOUO) Implementation of this object can be as low
         as not-accessible depending on which
         IS Objective or MIB desired requirements are
         not being met by the implementation."

    OBJECT		ipIfStatsOutFragFails
    MIN-ACCESS	read-only
    DESCRIPTION
        "(U//FOUO) Implementation of this object can be as low
         as read-only depending on which
         IS Objective or MIB desired requirements are
         not being met by the implementation."

    OBJECT		ipIfStatsOutOctets
    MIN-ACCESS	not-accessible
    DESCRIPTION
        "(U//FOUO) Implementation of this object can be as low
         as not-accessible depending on which
         IS Objective or MIB desired requirements are
         not being met by the implementation."

    OBJECT		ifInUnknownProtos
    MIN-ACCESS	not-accessible
    DESCRIPTION
        "(U//FOUO) Implementation of this object can be as low
         as not-accessible depending on which
         IS Objective or MIB desired requirements are
         not being met by the implementation."

    OBJECT		ifType
    MIN-ACCESS	read-only
    DESCRIPTION
        "(U//FOUO) Implementation of this object can be as low
         as read-only depending on which
         IS Objective or MIB desired requirements are
         not being met by the implementation."

    OBJECT		ifPhysAddress
    MIN-ACCESS	read-only
    DESCRIPTION
        "(U//FOUO) Implementation of this object can be as low
         as read-only depending on which
         IS Objective or MIB desired requirements are
         not being met by the implementation."

    OBJECT		ifDescr
    MIN-ACCESS	read-only
    DESCRIPTION
        "(U//FOUO) Implementation of this object can be as low
         as read-only depending on which
         IS Objective or MIB desired requirements are
         not being met by the implementation."

    OBJECT		mgmdRouterInterfaceStartupQueryCount
    MIN-ACCESS	not-accessible
    DESCRIPTION
        "(U//FOUO) Implementation of this object can be as low
         as not-accessible depending on which
         IS Objective or MIB desired requirements are
         not being met by the implementation."

    OBJECT		hTFTPDesiredBlockSize
    MIN-ACCESS	not-accessible
    DESCRIPTION
        "(U//FOUO) Implementation of this object can be as low
         as not-accessible depending on which
         IS Objective or MIB desired requirements are
         not being met by the implementation."

--    OBJECT		snmpNotifyObjects
--    MIN-ACCESS	read-write
--    DESCRIPTION
--        "(U//FOUO) Implementation of this object can be as low
--         as read-write depending on which
--         IS Objective or MIB desired requirements are
--         not being met by the implementation."

    OBJECT		hrSystemUptime
    MIN-ACCESS	not-accessible
    DESCRIPTION
        "(U//FOUO) Implementation of this object can be as low
         as not-accessible depending on which
         IS Objective or MIB desired requirements are
         not being met by the implementation."

    OBJECT		hFirmwareDownloadServersTableCount
    MIN-ACCESS	read-only
    DESCRIPTION
        "(U//FOUO) Implementation of this object can be as low
         as read-only depending on which
         IS Objective or MIB desired requirements are
         not being met by the implementation."

    OBJECT		snmpUnknownContexts
    MIN-ACCESS	read-only
    DESCRIPTION
        "(U//FOUO) Implementation of this object can be as low
         as read-only depending on which
         IS Objective or MIB desired requirements are
         not being met by the implementation."

    OBJECT		mgmdRouterInterfaceQueryMaxResponseTime
    MIN-ACCESS	not-accessible
    DESCRIPTION
        "(U//FOUO) Implementation of this object can be as low
         as not-accessible depending on which
         IS Objective or MIB desired requirements are
         not being met by the implementation."

--    OBJECT		snmpMPDMIBCompliances
--    MIN-ACCESS	read-write
--    DESCRIPTION
--        "(U//FOUO) Implementation of this object can be as low
--         as read-write depending on which
--         IS Objective or MIB desired requirements are
--         not being met by the implementation."

--    OBJECT		usmHMACMD5AuthProtocol
--    MIN-ACCESS	read-write
--    DESCRIPTION
--        "(U//FOUO) Implementation of this object can be as low
--         as read-write depending on which
--         IS Objective or MIB desired requirements are
--         not being met by the implementation."

    OBJECT		ifOutOctets
    MIN-ACCESS	not-accessible
    DESCRIPTION
        "(U//FOUO) Implementation of this object can be as low
         as not-accessible depending on which
         IS Objective or MIB desired requirements are
         not being met by the implementation."

    OBJECT		ifSpeed
    MIN-ACCESS	read-only
    DESCRIPTION
        "(U//FOUO) Implementation of this object can be as low
         as read-only depending on which
         IS Objective or MIB desired requirements are
         not being met by the implementation."

    OBJECT		mgmdRouterCacheExcludeModeExpiryTimer
    MIN-ACCESS	not-accessible
    DESCRIPTION
        "(U//FOUO) Implementation of this object can be as low
         as not-accessible depending on which
         IS Objective or MIB desired requirements are
         not being met by the implementation."

    OBJECT		ipIfStatsOutForwDatagrams
    MIN-ACCESS	not-accessible
    DESCRIPTION
        "(U//FOUO) Implementation of this object can be as low
         as not-accessible depending on which
         IS Objective or MIB desired requirements are
         not being met by the implementation."

--    OBJECT		snmpNotifyGroup
--    MIN-ACCESS	read-write
--    DESCRIPTION
--        "(U//FOUO) Implementation of this object can be as low
--         as read-write depending on which
--         IS Objective or MIB desired requirements are
--         not being met by the implementation."

--    OBJECT		usmNoPrivProtocol
--    MIN-ACCESS	read-write
--    DESCRIPTION
--        "(U//FOUO) Implementation of this object can be as low
--         as read-write depending on which
--         IS Objective or MIB desired requirements are
--         not being met by the implementation."

    OBJECT		mgmdRouterInterfaceProxyIfIndex
    MIN-ACCESS	not-accessible
    DESCRIPTION
        "(U//FOUO) Implementation of this object can be as low
         as not-accessible depending on which
         IS Objective or MIB desired requirements are
         not being met by the implementation."

--    OBJECT		usmMIBGroups
--    MIN-ACCESS	read-write
--    DESCRIPTION
--        "(U//FOUO) Implementation of this object can be as low
--         as read-write depending on which
--         IS Objective or MIB desired requirements are
--         not being met by the implementation."

    OBJECT		usmUserPublic
    MIN-ACCESS	read-write
    DESCRIPTION
        "(U//FOUO) Implementation of this object can be as low
         as read-write depending on which
         IS Objective or MIB desired requirements are
         not being met by the implementation."

    OBJECT		hTPSADecrementTTL
    MIN-ACCESS	read-only
    DESCRIPTION
        "(U//FOUO) Implementation of this object can be as low
         as read-only depending on which
         IS Objective or MIB desired requirements are
         not being met by the implementation."

    OBJECT		ipSystemStatsInMcastOctets
    MIN-ACCESS	not-accessible
    DESCRIPTION
        "(U//FOUO) Implementation of this object can be as low
         as not-accessible depending on which
         IS Objective or MIB desired requirements are
         not being met by the implementation."

    OBJECT		ipIfStatsHCInBcastPkts
    MIN-ACCESS	read-only
    DESCRIPTION
        "(U//FOUO) Implementation of this object can be as low
         as read-only depending on which
         IS Objective or MIB desired requirements are
         not being met by the implementation."

    OBJECT		ipIfStatsHCOutForwDatagrams
    MIN-ACCESS	read-only
    DESCRIPTION
        "(U//FOUO) Implementation of this object can be as low
         as read-only depending on which
         IS Objective or MIB desired requirements are
         not being met by the implementation."

    OBJECT		mgmdRouterSrcListHostAddress
    MIN-ACCESS	not-accessible
    DESCRIPTION
        "(U//FOUO) Implementation of this object can be as low
         as not-accessible depending on which
         IS Objective or MIB desired requirements are
         not being met by the implementation."

    OBJECT		hTPSAesn
    MIN-ACCESS	not-accessible
    DESCRIPTION
        "(U//FOUO) Implementation of this object can be as low
         as not-accessible depending on which
         IS Objective or MIB desired requirements are
         not being met by the implementation."

    OBJECT		hTopologyTableLastChanged
    MIN-ACCESS	read-only
    DESCRIPTION
        "(U//FOUO) Implementation of this object can be as low
         as read-only depending on which
         IS Objective or MIB desired requirements are
         not being met by the implementation."

    OBJECT		usmUserCloneFrom
    MIN-ACCESS	read-write
    DESCRIPTION
        "(U//FOUO) Implementation of this object can be as low
         as read-write depending on which
         IS Objective or MIB desired requirements are
         not being met by the implementation."

    OBJECT		ipSystemStatsReasmOKs
    MIN-ACCESS	not-accessible
    DESCRIPTION
        "(U//FOUO) Implementation of this object can be as low
         as not-accessible depending on which
         IS Objective or MIB desired requirements are
         not being met by the implementation."

--    OBJECT		ipv6InterfaceTable
--    MIN-ACCESS	read-only
--    DESCRIPTION
--        "(U//FOUO) Implementation of this object can be as low
--         as read-only depending on which
--         IS Objective or MIB desired requirements are
--         not being met by the implementation."

    OBJECT		hFirmwareDownloadAdminStatus
    MIN-ACCESS	read-write
    DESCRIPTION
        "(U//FOUO) Implementation of this object can be as low
         as read-write depending on which
         IS Objective or MIB desired requirements are
         not being met by the implementation."

    OBJECT		hPPKChainEffectiveDate
    MIN-ACCESS	read-write
    DESCRIPTION
        "(U//FOUO) Implementation of this object can be as low
         as read-write depending on which
         IS Objective or MIB desired requirements are
         not being met by the implementation."

    OBJECT		hIPhRuleAdminStatus
    MIN-ACCESS	read-write
    DESCRIPTION
        "(U//FOUO) Implementation of this object can be as low
         as read-write depending on which
         IS Objective or MIB desired requirements are
         not being met by the implementation."

--    OBJECT		snmpFrameworkMIBCompliances
--    MIN-ACCESS	read-write
--    DESCRIPTION
--        "(U//FOUO) Implementation of this object can be as low
--         as read-write depending on which
--         IS Objective or MIB desired requirements are
--         not being met by the implementation."

    OBJECT		mgmdHostInterfaceQuerier
    MIN-ACCESS	read-only
    DESCRIPTION
        "(U//FOUO) Implementation of this object can be as low
         as read-only depending on which
         IS Objective or MIB desired requirements are
         not being met by the implementation."

    OBJECT		snmpNotifyFilterProfileStorType
    MIN-ACCESS	read-write
    DESCRIPTION
        "(U//FOUO) Implementation of this object can be as low
         as read-write depending on which
         IS Objective or MIB desired requirements are
         not being met by the implementation."

    OBJECT		hTPSARetryICMPCount
    MIN-ACCESS	read-write
    DESCRIPTION
        "(U//FOUO) Implementation of this object can be as low
         as read-write depending on which
         IS Objective or MIB desired requirements are
         not being met by the implementation."

    OBJECT		hIPhFFSAPHRDRate
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		mgmdHostCacheSourceFilterMode
    MIN-ACCESS	read-only
    DESCRIPTION
        "(U//FOUO) Implementation of this object can be as low
         as read-only depending on which
         IS Objective or MIB desired requirements are
         not being met by the implementation."

--    OBJECT		snmpTargetResponseGroup
--    MIN-ACCESS	read-write
--    DESCRIPTION
--        "(U//FOUO) Implementation of this object can be as low
--         as read-write depending on which
--         IS Objective or MIB desired requirements are
--         not being met by the implementation."

    OBJECT		ipSystemStatsHCOutBcastPkts
    MIN-ACCESS	not-accessible
    DESCRIPTION
        "(U//FOUO) Implementation of this object can be as low
         as not-accessible depending on which
         IS Objective or MIB desired requirements are
         not being met by the implementation."

    OBJECT		nlmLogVariableOpaqueVal
    MIN-ACCESS	read-only
    DESCRIPTION
        "(U//FOUO) Implementation of this object can be as low
         as read-only depending on which
         IS Objective or MIB desired requirements are
         not being met by the implementation."

--    OBJECT		snmpUsmMIB
--    MIN-ACCESS	read-write
--    DESCRIPTION
--        "(U//FOUO) Implementation of this object can be as low
--         as read-write depending on which
--         IS Objective or MIB desired requirements are
--         not being met by the implementation."

    OBJECT		hTPSARemoteCTAddress
    MIN-ACCESS	read-write
    DESCRIPTION
        "(U//FOUO) Implementation of this object can be as low
         as read-write depending on which
         IS Objective or MIB desired requirements are
         not being met by the implementation."

    OBJECT		hTPSAFlowLabelValue
    MIN-ACCESS	read-write
    DESCRIPTION
        "(U//FOUO) Implementation of this object can be as low
         as read-write depending on which
         IS Objective or MIB desired requirements are
         not being met by the implementation."

    OBJECT		hAudThrottleCfgInterval
    MIN-ACCESS	read-only
    DESCRIPTION
        "(U//FOUO) Implementation of this object can be as low
         as read-only depending on which
         IS Objective or MIB desired requirements are
         not being met by the implementation."

    OBJECT		hiaaAddress
    MIN-ACCESS	read-write
    DESCRIPTION
        "(U//FOUO) Implementation of this object can be as low
         as read-write depending on which
         IS Objective or MIB desired requirements are
         not being met by the implementation."

    OBJECT		hTPSASelectorNextHeaderEnd
    MIN-ACCESS	not-accessible
    DESCRIPTION
        "(U//FOUO) Implementation of this object can be as low
         as not-accessible depending on which
         IS Objective or MIB desired requirements are
         not being met by the implementation."

    OBJECT		mgmdRouterInterfaceWrongVersionQueries
    MIN-ACCESS	not-accessible
    DESCRIPTION
        "(U//FOUO) Implementation of this object can be as low
         as not-accessible depending on which
         IS Objective or MIB desired requirements are
         not being met by the implementation."

    OBJECT		nlmStatsLogNotificationsBumped
    MIN-ACCESS	not-accessible
    DESCRIPTION
        "(U//FOUO) Implementation of this object can be as low
         as not-accessible depending on which
         IS Objective or MIB desired requirements are
         not being met by the implementation."

    OBJECT		hTPSATableCount
    MIN-ACCESS	read-only
    DESCRIPTION
        "(U//FOUO) Implementation of this object can be as low
         as read-only depending on which
         IS Objective or MIB desired requirements are
         not being met by the implementation."

    OBJECT		hNotificationLogFullBehavior
    MIN-ACCESS	read-only
    DESCRIPTION
        "(U//FOUO) Implementation of this object can be as low
         as read-only depending on which
         IS Objective or MIB desired requirements are
         not being met by the implementation."

--    OBJECT		usmMIBCompliances
--    MIN-ACCESS	read-write
--    DESCRIPTION
--        "(U//FOUO) Implementation of this object can be as low
--         as read-write depending on which
--         IS Objective or MIB desired requirements are
--         not being met by the implementation."

    OBJECT		hPreplacedKeyTableCount
    MIN-ACCESS	read-only
    DESCRIPTION
        "(U//FOUO) Implementation of this object can be as low
         as read-only depending on which
         IS Objective or MIB desired requirements are
         not being met by the implementation."

    OBJECT		ipDefaultTTL
    MIN-ACCESS	read-only
    DESCRIPTION
        "(U//FOUO) Implementation of this object can be as low
         as read-only depending on which
         IS Objective or MIB desired requirements are
         not being met by the implementation."

    OBJECT		mgmdRouterInterfaceQuerier
    MIN-ACCESS	not-accessible
    DESCRIPTION
        "(U//FOUO) Implementation of this object can be as low
         as not-accessible depending on which
         IS Objective or MIB desired requirements are
         not being met by the implementation."

    OBJECT		tcpInSegs
    MIN-ACCESS	read-only
    DESCRIPTION
        "(U//FOUO) Implementation of this object can be as low
         as read-only depending on which
         IS Objective or MIB desired requirements are
         not being met by the implementation."

    OBJECT		hTPSALocalCredentialID
    MIN-ACCESS	read-only
    DESCRIPTION
        "(U//FOUO) Implementation of this object can be as low
         as read-only depending on which
         IS Objective or MIB desired requirements are
         not being met by the implementation."

--    OBJECT		hFirmwareInstallSucceeded
--    MIN-ACCESS	accessible-for-notify
--    DESCRIPTION
--        "(U//FOUO) Implementation of this object can be as low
--         as accessible-for-notify depending on which
--         IS Objective or MIB desired requirements are
--         not being met by the implementation."

    OBJECT		ifAdminStatus
    MIN-ACCESS	read-write
    DESCRIPTION
        "(U//FOUO) Implementation of this object can be as low
         as read-write depending on which
         IS Objective or MIB desired requirements are
         not being met by the implementation."

    OBJECT		hIPhRuleRowStatus
    MIN-ACCESS	read-write
    DESCRIPTION
        "(U//FOUO) Implementation of this object can be as low
         as read-write depending on which
         IS Objective or MIB desired requirements are
         not being met by the implementation."

    OBJECT		ipSystemStatsOutNoRoutes
    MIN-ACCESS	not-accessible
    DESCRIPTION
        "(U//FOUO) Implementation of this object can be as low
         as not-accessible depending on which
         IS Objective or MIB desired requirements are
         not being met by the implementation."

    OBJECT		mgmdHostInterfaceVersion2QuerierTimer
    MIN-ACCESS	read-only
    DESCRIPTION
        "(U//FOUO) Implementation of this object can be as low
         as read-only depending on which
         IS Objective or MIB desired requirements are
         not being met by the implementation."

--    OBJECT		snmpFrameworkMIBCompliance
--    MIN-ACCESS	read-write
--    DESCRIPTION
--        "(U//FOUO) Implementation of this object can be as low
--         as read-write depending on which
--         IS Objective or MIB desired requirements are
--         not being met by the implementation."

    OBJECT		inetCidrRouteMetric2
    MIN-ACCESS	read-write
    DESCRIPTION
        "(U//FOUO) Implementation of this object can be as low
         as read-write depending on which
         IS Objective or MIB desired requirements are
         not being met by the implementation."

    OBJECT		tcpCurrEstab
    MIN-ACCESS	read-only
    DESCRIPTION
        "(U//FOUO) Implementation of this object can be as low
         as read-only depending on which
         IS Objective or MIB desired requirements are
         not being met by the implementation."

    OBJECT		nlmLogVariableUnsigned32Val
    MIN-ACCESS	read-only
    DESCRIPTION
        "(U//FOUO) Implementation of this object can be as low
         as read-only depending on which
         IS Objective or MIB desired requirements are
         not being met by the implementation."

    OBJECT		tcpActiveOpens
    MIN-ACCESS	read-only
    DESCRIPTION
        "(U//FOUO) Implementation of this object can be as low
         as read-only depending on which
         IS Objective or MIB desired requirements are
         not being met by the implementation."

    OBJECT		hIPhFFSACTOutAddress
    MIN-ACCESS	read-write
    DESCRIPTION
        "(U//FOUO) Implementation of this object can be as low
         as read-write depending on which
         IS Objective or MIB desired requirements are
         not being met by the implementation."

    OBJECT		hIPhFFSAPopulateFromPacket
    MIN-ACCESS	not-accessible
    DESCRIPTION
        "(U//FOUO) Implementation of this object can be as low
         as not-accessible depending on which
         IS Objective or MIB desired requirements are
         not being met by the implementation."

--    OBJECT		snmpTargetGroups
--    MIN-ACCESS	read-write
--    DESCRIPTION
--        "(U//FOUO) Implementation of this object can be as low
--         as read-write depending on which
--         IS Objective or MIB desired requirements are
--         not being met by the implementation."

    OBJECT		ipIfStatsInMcastOctets
    MIN-ACCESS	not-accessible
    DESCRIPTION
        "(U//FOUO) Implementation of this object can be as low
         as not-accessible depending on which
         IS Objective or MIB desired requirements are
         not being met by the implementation."

    OBJECT		hLastChanged
    MIN-ACCESS	read-only
    DESCRIPTION
        "(U//FOUO) Implementation of this object can be as low
         as read-only depending on which
         IS Objective or MIB desired requirements are
         not being met by the implementation."

    OBJECT		ipIfStatsHCOutRequests
    MIN-ACCESS	read-only
    DESCRIPTION
        "(U//FOUO) Implementation of this object can be as low
         as read-only depending on which
         IS Objective or MIB desired requirements are
         not being met by the implementation."

    OBJECT		usmUserStorageType
    MIN-ACCESS	read-write
    DESCRIPTION
        "(U//FOUO) Implementation of this object can be as low
         as read-write depending on which
         IS Objective or MIB desired requirements are
         not being met by the implementation."

--    OBJECT		snmpTargetBasicGroup
--    MIN-ACCESS	read-write
--    DESCRIPTION
--        "(U//FOUO) Implementation of this object can be as low
--         as read-write depending on which
--         IS Objective or MIB desired requirements are
--         not being met by the implementation."

    OBJECT		usmUserOwnPrivKeyChange
    MIN-ACCESS	read-write
    DESCRIPTION
        "(U//FOUO) Implementation of this object can be as low
         as read-write depending on which
         IS Objective or MIB desired requirements are
         not being met by the implementation."

--    OBJECT		snmpVacmMIB
--    MIN-ACCESS	read-write
--    DESCRIPTION
--        "(U//FOUO) Implementation of this object can be as low
--         as read-write depending on which
--         IS Objective or MIB desired requirements are
--         not being met by the implementation."

    OBJECT		hIPhSelectorLastChanged
    MIN-ACCESS	read-only
    DESCRIPTION
        "(U//FOUO) Implementation of this object can be as low
         as read-only depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hTPSAPHRDRate
    MIN-ACCESS	read-write
    DESCRIPTION
        "(U//FOUO) Implementation of this object can be as low
         as read-write depending on which
         IS Objective or MIB desired requirements are
         not being met by the implementation."

    OBJECT		tcpRtoMax
    MIN-ACCESS	read-only
    DESCRIPTION
        "(U//FOUO) Implementation of this object can be as low
         as read-only depending on which
         IS Objective or MIB desired requirements are
         not being met by the implementation."

    OBJECT		ifHighSpeed
    MIN-ACCESS	read-only
    DESCRIPTION
        "(U//FOUO) Implementation of this object can be as low
         as read-only depending on which
         IS Objective or MIB desired requirements are
         not being met by the implementation."

    OBJECT		ipIfStatsInHdrErrors
    MIN-ACCESS	read-only
    DESCRIPTION
        "(U//FOUO) Implementation of this object can be as low
         as read-only depending on which
         IS Objective or MIB desired requirements are
         not being met by the implementation."

    OBJECT		tcpOutRsts
    MIN-ACCESS	read-only
    DESCRIPTION
        "(U//FOUO) Implementation of this object can be as low
         as read-only depending on which
         IS Objective or MIB desired requirements are
         not being met by the implementation."

    OBJECT		udpEndpointProcess
    MIN-ACCESS	read-only
    DESCRIPTION
        "(U//FOUO) Implementation of this object can be as low
         as read-only depending on which
         IS Objective or MIB desired requirements are
         not being met by the implementation."

    OBJECT		usmUserAuthKeyChange
    MIN-ACCESS	read-write
    DESCRIPTION
        "(U//FOUO) Implementation of this object can be as low
         as read-write depending on which
         IS Objective or MIB desired requirements are
         not being met by the implementation."

    OBJECT		snmpEngineBoots
    MIN-ACCESS	read-only
    DESCRIPTION
        "(U//FOUO) Implementation of this object can be as low
         as read-only depending on which
         IS Objective or MIB desired requirements are
         not being met by the implementation."

    OBJECT		vacmSecurityToGroupStatus
    MIN-ACCESS	read-write
    DESCRIPTION
        "(U//FOUO) Implementation of this object can be as low
         as read-write depending on which
         IS Objective or MIB desired requirements are
         not being met by the implementation."

    OBJECT		hIPhSelectorTableCount
    MIN-ACCESS	read-only
    DESCRIPTION
        "(U//FOUO) Implementation of this object can be as low
         as read-only depending on which
         IS Objective or MIB desired requirements are
         not being met by the implementation."

    OBJECT		ipSystemStatsInAddrErrors
    MIN-ACCESS	not-accessible
    DESCRIPTION
        "(U//FOUO) Implementation of this object can be as low
         as not-accessible depending on which
         IS Objective or MIB desired requirements are
         not being met by the implementation."
::= { haipeV030002Conformance 3 }

--
-- Objects referenced by the Reachability IS
--
hReachabilityGroup OBJECT-GROUP
    OBJECTS {
                hDiscoveryEnabled,
--                hDiscoveryMessageConfig,
                hDiscoveryProbeTimeout,
                hDiscoveryProbeRetry,
                hDiscoveryRegistrationTimeout,
                hDiscoveryRegistrationRetry,
                hDiscoverySolicitationTimeout,
                hDiscoverySolicitationRetry,
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hIPhFFSAPDUNEnabled,
                hIPhFFSAPHRDRate,
                hIPhFFSARetryICMPCount,
                hTPSAPDUNEnabled,
                hTPSAPHRDRate,
                hTPSARetryICMPCount
            }
    STATUS    current
    DESCRIPTION
        "(U//FOUO) Objects for the 'Reachability' document"
    ::= { haipeV030002Groups 4 }

--
-- Conformance levels required by the Reachability IS
--
hReachabilityCompliance MODULE-COMPLIANCE
    STATUS    current
    DESCRIPTION
        "(U//FOUO) Compliance levels for objects required by the
          'Reachability' document"
    MODULE -- this module
    MANDATORY-GROUPS { hReachabilityGroup }

    OBJECT		hIPhFFSARetryICMPCount
    MIN-ACCESS	read-write
    DESCRIPTION
        "(U//FOUO) Implementation of this object can be as low
         as read-write depending on which
         IS Objective or MIB desired requirements are
         not being met by the implementation."

    OBJECT		hDiscoverySolicitationRetry
    MIN-ACCESS	read-write
    DESCRIPTION
        "(U//FOUO) Implementation of this object can be as low
         as read-write depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		hDiscSearchStartAddress
    MIN-ACCESS	read-write
    DESCRIPTION
        "(U//FOUO) Implementation of this object can be as low
         as read-write depending on which
         IS Objective or MIB desired requirements are
         not being met by the implementation."

    OBJECT		hDiscoveryRegistrationRetry
    MIN-ACCESS	read-write
    DESCRIPTION
        "(U//FOUO) Implementation of this object can be as low
         as read-write depending on which
         IS Objective or MIB desired requirements are
         not being met by the implementation."

    OBJECT		hDiscDelivPTAddress
    MIN-ACCESS	read-write
    DESCRIPTION
        "(U//FOUO) Implementation of this object can be as low
         as read-write depending on which
         IS Objective or MIB desired requirements are
         not being met by the implementation."

    OBJECT		hDiscoveryProbeRetry
    MIN-ACCESS	read-write
    DESCRIPTION
        "(U//FOUO) Implementation of this object can be as low
         as read-write depending on which
         IS Objective or MIB desired requirements are
         not being met by the implementation."

    OBJECT		hDiscDelivStatus
    MIN-ACCESS	read-write
    DESCRIPTION
        "(U//FOUO) Implementation of this object can be as low
         as read-write depending on which
         IS Objective or MIB desired requirements are
         not being met by the implementation."

    OBJECT		hDiscSearchEndAddress
    MIN-ACCESS	read-write
    DESCRIPTION
        "(U//FOUO) Implementation of this object can be as low
         as read-write depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hDiscDelivType
    MIN-ACCESS	read-write
    DESCRIPTION
        "(U//FOUO) Implementation of this object can be as low
         as read-write depending on which
         IS Objective or MIB desired requirements are
         not being met by the implementation."

    OBJECT		hDiscoveryProbeTimeout
    MIN-ACCESS	read-write
    DESCRIPTION
        "(U//FOUO) Implementation of this object can be as low
         as read-write depending on which
         IS Objective or MIB desired requirements are
         not being met by the implementation."

--    OBJECT		hDiscoveryMessageConfig
--    MIN-ACCESS	read-write
--    DESCRIPTION
--        "(U//FOUO) Implementation of this object can be as low
--         as read-write depending on which
--         IS Objective or MIB desired requirements are
--         not being met by the implementation."

    OBJECT		hDiscoveryRegistrationTimeout
    MIN-ACCESS	read-write
    DESCRIPTION
        "(U//FOUO) Implementation of this object can be as low
         as read-write depending on which
         IS Objective or MIB desired requirements are
         not being met by the implementation."

    OBJECT		hDiscDelivPriority
    MIN-ACCESS	read-write
    DESCRIPTION
        "(U//FOUO) Implementation of this object can be as low
         as read-write depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		hTPSARetryICMPCount
    MIN-ACCESS	read-write
    DESCRIPTION
        "(U//FOUO) Implementation of this object can be as low
         as read-write depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		hIPhFFSAPHRDRate
    MIN-ACCESS	read-write
    DESCRIPTION
        "(U//FOUO) Implementation of this object can be as low
         as read-write depending on which
         IS Objective or MIB desired requirements are
         not being met by the implementation."

    OBJECT		hDiscDelivPTPort
    MIN-ACCESS	read-write
    DESCRIPTION
        "(U//FOUO) Implementation of this object can be as low
         as read-write depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hDiscSearchAddressType
    MIN-ACCESS	read-write
    DESCRIPTION
        "(U//FOUO) Implementation of this object can be as low
         as read-write depending on which
         IS Objective or MIB desired requirements are
         not being met by the implementation."

    OBJECT		hDiscoveryEnabled
    MIN-ACCESS	read-write
    DESCRIPTION
        "(U//FOUO) Implementation of this object can be as low
         as read-write depending on which
         IS Objective or MIB desired requirements are
         not being met by the implementation."

    OBJECT		hIPhFFSAPDUNEnabled
    MIN-ACCESS	read-write
    DESCRIPTION
        "(U//FOUO) Implementation of this object can be as low
         as read-write depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hTPSAPDUNEnabled
    MIN-ACCESS	read-write
    DESCRIPTION
        "(U//FOUO) Implementation of this object can be as low
         as read-write depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hTPSAPHRDRate
    MIN-ACCESS	read-write
    DESCRIPTION
        "(U//FOUO) Implementation of this object can be as low
         as read-write depending on which
         IS Objective or MIB desired requirements are
         not being met by the implementation."

    OBJECT		hDiscDelivPTAddressType
    MIN-ACCESS	read-write
    DESCRIPTION
        "(U//FOUO) Implementation of this object can be as low
         as read-write depending on which
         IS Objective or MIB desired requirements are
         not being met by the implementation."

    OBJECT		hDiscoverySolicitationTimeout
    MIN-ACCESS	read-write
    DESCRIPTION
        "(U//FOUO) Implementation of this object can be as low
         as read-write depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."
::= { haipeV030002Conformance 4 }

--
-- Objects referenced by the PT-RIP Discovery IS
--
hPTRIPDiscoveryGroup OBJECT-GROUP
    OBJECTS {
                hTopologyTableCount,
                hTopologyTableLastChanged,
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hRIPConfTableCount,
                hRIPConfTableLastChanged,
                hrcAddrType,
                hrcAddr,
                hrcAuthType,
                hrcAuthKey,
                hrcSend,
                hrcReceive,
                hrcDefaultMetric,
                hrcAdvertising,
                hrcFilterDefaultRoutes,
                hrcSrcAddress,
                hrcStatus
            }
    STATUS    current
    DESCRIPTION
        "(U//FOUO) Objects for the 'PT-RIP Discovery' document"
    ::= { haipeV030002Groups 5 }

--
-- Conformance levels required by the PT-RIP Discovery IS
--
hPTRIPDiscoveryCompliance MODULE-COMPLIANCE
    STATUS    current
    DESCRIPTION
        "(U//FOUO) Compliance levels for objects required by the
          'PT-RIP Discovery' document"
    MODULE -- this module
    MANDATORY-GROUPS { hPTRIPDiscoveryGroup }

    OBJECT		hrcStatus
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		hTopologyTableCount
    MIN-ACCESS	read-only
    DESCRIPTION
        "(U//FOUO) Implementation of this object can be as low
         as read-only depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		hRIPConfTableLastChanged
    MIN-ACCESS	read-only
    DESCRIPTION
        "(U//FOUO) Implementation of this object can be as low
         as read-only depending on which
         IS Objective or MIB desired requirements are
         not being met by the implementation."

    OBJECT		hrcSrcAddress
    MIN-ACCESS	read-write
    DESCRIPTION
        "(U//FOUO) Implementation of this object can be as low
         as read-write depending on which
         IS Objective or MIB desired requirements are
         not being met by the implementation."

    OBJECT		hrcDefaultMetric
    MIN-ACCESS	read-write
    DESCRIPTION
        "(U//FOUO) Implementation of this object can be as low
         as read-write depending on which
         IS Objective or MIB desired requirements are
         not being met by the implementation."

    OBJECT		hTopologyTableLastChanged
    MIN-ACCESS	read-only
    DESCRIPTION
        "(U//FOUO) Implementation of this object can be as low
         as read-only depending on which
         IS Objective or MIB desired requirements are
         not being met by the implementation."

    OBJECT		hrcAuthKey
    MIN-ACCESS	read-write
    DESCRIPTION
        "(U//FOUO) Implementation of this object can be as low
         as read-write depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hrcFilterDefaultRoutes
    MIN-ACCESS	read-write
    DESCRIPTION
        "(U//FOUO) Implementation of this object can be as low
         as read-write depending on which
         IS Objective or MIB desired requirements are
         not being met by the implementation."

    OBJECT		hrcAdvertising
    MIN-ACCESS	read-write
    DESCRIPTION
        "(U//FOUO) Implementation of this object can be as low
         as read-write depending on which
         IS Objective or MIB desired requirements are
         not being met by the implementation."

    OBJECT		hrcAddrType
    MIN-ACCESS	read-write
    DESCRIPTION
        "(U//FOUO) Implementation of this object can be as low
         as read-write depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hrcAuthType
    MIN-ACCESS	read-write
    DESCRIPTION
        "(U//FOUO) Implementation of this object can be as low
         as read-write depending on which
         IS Objective or MIB desired requirements are
         not being met by the implementation."

    OBJECT		hrcSend
    MIN-ACCESS	read-write
    DESCRIPTION
        "(U//FOUO) Implementation of this object can be as low
         as read-write depending on which
         IS Objective or MIB desired requirements are
         not being met by the implementation."

    OBJECT		hRIPConfTableCount
    MIN-ACCESS	read-only
    DESCRIPTION
        "(U//FOUO) Implementation of this object can be as low
         as read-only depending on which
         IS Objective or MIB desired requirements are
         not being met by the implementation."

    OBJECT		hrcReceive
    MIN-ACCESS	read-write
    DESCRIPTION
        "(U//FOUO) Implementation of this object can be as low
         as read-write depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		hrcAddr
    MIN-ACCESS	read-write
    DESCRIPTION
        "(U//FOUO) Implementation of this object can be as low
         as read-write depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."
::= { haipeV030002Conformance 5 }

--
-- Objects referenced by the ESPv3 Transport Mode IS
--
hESPv3TransportModeGroup OBJECT-GROUP
    OBJECTS {
                hPPKTrafficIntegrityAlgorithm,
                hIPhFFSAConnectionType,
                hIPhFFSATransformIntegrityAlgorithm,
                hTPSAConnectionType,
                hTPSAIntegrityAlgorithm,
                hTPTransportMapTableCount,
                hTPTransportMapTableLastChanged,
                hTPTransMapDestPTAddress,
                hTPTransMapSourcePTAddress,
                hTPTransMapLastChanged,
                hTPTransMapRowStatus
            }
    STATUS    current
    DESCRIPTION
        "(U//FOUO) Objects for the 'ESPv3 Transport Mode' document"
    ::= { haipeV030002Groups 6 }

--
-- Conformance levels required by the ESPv3 Transport Mode IS
--
hESPv3TransportModeCompliance MODULE-COMPLIANCE
    STATUS    current
    DESCRIPTION
        "(U//FOUO) Compliance levels for objects required by the
          'ESPv3 Transport Mode' document"
    MODULE -- this module
    MANDATORY-GROUPS { hESPv3TransportModeGroup }

    OBJECT		hTPTransMapRowStatus
    MIN-ACCESS	read-write
    DESCRIPTION
        "(U//FOUO) Implementation of this object can be as low
         as read-write depending on which
         IS Objective or MIB desired requirements are
         not being met by the implementation."

    OBJECT		hTPTransportMapTableLastChanged
    MIN-ACCESS	read-only
    DESCRIPTION
        "(U//FOUO) Implementation of this object can be as low
         as read-only depending on which
         IS Objective or MIB desired requirements are
         not being met by the implementation."

    OBJECT		hTPTransportMapTableCount
    MIN-ACCESS	read-only
    DESCRIPTION
        "(U//FOUO) Implementation of this object can be as low
         as read-only depending on which
         IS Objective or MIB desired requirements are
         not being met by the implementation."

    OBJECT		hTPSAIntegrityAlgorithm
    MIN-ACCESS	read-write
    DESCRIPTION
        "(U//FOUO) Implementation of this object can be as low
         as read-write depending on which
         IS Objective or MIB desired requirements are
         not being met by the implementation."

    OBJECT		hTPTransMapLastChanged
    MIN-ACCESS	read-only
    DESCRIPTION
        "(U//FOUO) Implementation of this object can be as low
         as read-only depending on which
         IS Objective or MIB desired requirements are
         not being met by the implementation."

    OBJECT		hIPhFFSAConnectionType
    MIN-ACCESS	read-write
    DESCRIPTION
        "(U//FOUO) Implementation of this object can be as low
         as read-write depending on which
         IS Objective or MIB desired requirements are
         not being met by the implementation."

    OBJECT		hTPTransMapSourcePTAddress
    MIN-ACCESS	read-write
    DESCRIPTION
        "(U//FOUO) Implementation of this object can be as low
         as read-write depending on which
         IS Objective or MIB desired requirements are
         not being met by the implementation."

    OBJECT		hIPhFFSATransformIntegrityAlgorithm
    MIN-ACCESS	read-write
    DESCRIPTION
        "(U//FOUO) Implementation of this object can be as low
         as read-write depending on which
         IS Objective or MIB desired requirements are
         not being met by the implementation."

    OBJECT		hPPKTrafficIntegrityAlgorithm
    MIN-ACCESS	read-only
    DESCRIPTION
        "(U//FOUO) Implementation of this object can be as low
         as read-only depending on which
         IS Objective or MIB desired requirements are
         not being met by the implementation."

    OBJECT		hTPSAConnectionType
    MIN-ACCESS	read-write
    DESCRIPTION
        "(U//FOUO) Implementation of this object can be as low
         as read-write depending on which
         IS Objective or MIB desired requirements are
         not being met by the implementation."

    OBJECT		hTPTransMapDestPTAddress
    MIN-ACCESS	read-write
    DESCRIPTION
        "(U//FOUO) Implementation of this object can be as low
         as read-write depending on which
         IS Objective or MIB desired requirements are
         not being met by the implementation."
::= { haipeV030002Conformance 6 }

--
-- Objects referenced by the Generic Discovery Client IS
--
hGenericDiscoveryClientGroup OBJECT-GROUP
    OBJECTS {
                hDiscoveryAdvertiseAdminCost,
                hDiscoveryRegistrationTimeout,
                hDiscoveryRegistrationRetry,
                hDiscoverySolicitationTimeout,
                hDiscoverySolicitationRetry,
                hDiscoveryDeliveryTableCount,
                hDiscoveryDeliveryTableLastChanged,
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hDiscRegistrationTableCount,
                hDiscRegistrationTableLastChanged,
                hDiscRegPriority,
                hDiscRegPTAddressType,
                hDiscRegPTAddress,
                hDiscRegPTPort,
                hDiscRegStatus,
                hDiscRegistrationDefaultLifetime,
                hDiscSolReceptionTableCount,
                hDiscSolReceptionTableLastChanged,
                hDiscSolRcvSide,
                hDiscSolRcvAddressType,
                hDiscSolRcvAddress,
                hDiscSolRcvPort,
                hDiscSolRcvType,
                hDiscSolRcvStatus,
                hTopologyTableCount,
                hTopologyTableLastChanged,
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime
            }
    STATUS    current
    DESCRIPTION
        "(U//FOUO) Objects for the 'Generic Discovery Client' document"
    ::= { haipeV030002Groups 7 }

--
-- Conformance levels required by the Generic Discovery Client IS
--
hGenericDiscoveryClientCompliance MODULE-COMPLIANCE
    STATUS    current
    DESCRIPTION
        "(U//FOUO) Compliance levels for objects required by the
          'Generic Discovery Client' document"
    MODULE -- this module
    MANDATORY-GROUPS { hGenericDiscoveryClientGroup }

    OBJECT		hTopologyTableCount
    MIN-ACCESS	read-only
    DESCRIPTION
        "(U//FOUO) Implementation of this object can be as low
         as read-only depending on which
         IS Objective or MIB desired requirements are
         not being met by the implementation."

    OBJECT		hDiscRegistrationTableLastChanged
    MIN-ACCESS	read-only
    DESCRIPTION
        "(U//FOUO) Implementation of this object can be as low
         as read-only depending on which
         IS Objective or MIB desired requirements are
         not being met by the implementation."

    OBJECT		hDiscoverySolicitationRetry
    MIN-ACCESS	not-accessible
    DESCRIPTION
        "(U//FOUO) Implementation of this object can be as low
         as not-accessible depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hDiscSolRcvSide
    MIN-ACCESS	read-write
    DESCRIPTION
        "(U//FOUO) Implementation of this object can be as low
         as read-write depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		hDiscSearchStartAddress
    MIN-ACCESS	read-write
    DESCRIPTION
        "(U//FOUO) Implementation of this object can be as low
         as read-write depending on which
         IS Objective or MIB desired requirements are
         not being met by the implementation."

    OBJECT		hTopologyTableLastChanged
    MIN-ACCESS	read-only
    DESCRIPTION
        "(U//FOUO) Implementation of this object can be as low
         as read-only depending on which
         IS Objective or MIB desired requirements are
         not being met by the implementation."

    OBJECT		hDiscSolRcvAddressType
    MIN-ACCESS	read-write
    DESCRIPTION
        "(U//FOUO) Implementation of this object can be as low
         as read-write depending on which
         IS Objective or MIB desired requirements are
         not being met by the implementation."

    OBJECT		hDiscSolReceptionTableCount
    MIN-ACCESS	read-only
    DESCRIPTION
        "(U//FOUO) Implementation of this object can be as low
         as read-only depending on which
         IS Objective or MIB desired requirements are
         not being met by the implementation."

    OBJECT		hDiscoveryRegistrationRetry
    MIN-ACCESS	read-write
    DESCRIPTION
        "(U//FOUO) Implementation of this object can be as low
         as read-write depending on which
         IS Objective or MIB desired requirements are
         not being met by the implementation."

    OBJECT		hDiscRegPriority
    MIN-ACCESS	read-write
    DESCRIPTION
        "(U//FOUO) Implementation of this object can be as low
         as read-write depending on which
         IS Objective or MIB desired requirements are
         not being met by the implementation."

    OBJECT		hDiscDelivPTAddress
    MIN-ACCESS	read-write
    DESCRIPTION
        "(U//FOUO) Implementation of this object can be as low
         as read-write depending on which
         IS Objective or MIB desired requirements are
         not being met by the implementation."

    OBJECT		hDiscDelivStatus
    MIN-ACCESS	read-write
    DESCRIPTION
        "(U//FOUO) Implementation of this object can be as low
         as read-write depending on which
         IS Objective or MIB desired requirements are
         not being met by the implementation."

    OBJECT		hDiscSearchEndAddress
    MIN-ACCESS	read-write
    DESCRIPTION
        "(U//FOUO) Implementation of this object can be as low
         as read-write depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hDiscDelivType
    MIN-ACCESS	read-write
    DESCRIPTION
        "(U//FOUO) Implementation of this object can be as low
         as read-write depending on which
         IS Objective or MIB desired requirements are
         not being met by the implementation."

    OBJECT		hDiscRegStatus
    MIN-ACCESS	read-write
    DESCRIPTION
        "(U//FOUO) Implementation of this object can be as low
         as read-write depending on which
         IS Objective or MIB desired requirements are
         not being met by the implementation."

    OBJECT		hDiscoveryAdvertiseAdminCost
    MIN-ACCESS	read-write
    DESCRIPTION
        "(U//FOUO) Implementation of this object can be as low
         as read-write depending on which
         IS Objective or MIB desired requirements are
         not being met by the implementation."

    OBJECT		hDiscoveryRegistrationTimeout
    MIN-ACCESS	read-write
    DESCRIPTION
        "(U//FOUO) Implementation of this object can be as low
         as read-write depending on which
         IS Objective or MIB desired requirements are
         not being met by the implementation."

    OBJECT		hDiscRegPTAddressType
    MIN-ACCESS	read-write
    DESCRIPTION
        "(U//FOUO) Implementation of this object can be as low
         as read-write depending on which
         IS Objective or MIB desired requirements are
         not being met by the implementation."

    OBJECT		hDiscDelivPriority
    MIN-ACCESS	read-write
    DESCRIPTION
        "(U//FOUO) Implementation of this object can be as low
         as read-write depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hDiscDelivPTPort
    MIN-ACCESS	read-write
    DESCRIPTION
        "(U//FOUO) Implementation of this object can be as low
         as read-write depending on which
         IS Objective or MIB desired requirements are
         not being met by the implementation."

    OBJECT		hDiscSolRcvType
    MIN-ACCESS	read-write
    DESCRIPTION
        "(U//FOUO) Implementation of this object can be as low
         as read-write depending on which
         IS Objective or MIB desired requirements are
         not being met by the implementation."

    OBJECT		hDiscRegPTPort
    MIN-ACCESS	read-write
    DESCRIPTION
        "(U//FOUO) Implementation of this object can be as low
         as read-write depending on which
         IS Objective or MIB desired requirements are
         not being met by the implementation."

    OBJECT		hDiscRegistrationDefaultLifetime
    MIN-ACCESS	read-only
    DESCRIPTION
        "(U//FOUO) Implementation of this object can be as low
         as read-only depending on which
         IS Objective or MIB desired requirements are
         not being met by the implementation."

    OBJECT		hDiscSearchAddressType
    MIN-ACCESS	read-write
    DESCRIPTION
        "(U//FOUO) Implementation of this object can be as low
         as read-write depending on which
         IS Objective or MIB desired requirements are
         not being met by the implementation."

    OBJECT		hDiscSolRcvStatus
    MIN-ACCESS	read-write
    DESCRIPTION
        "(U//FOUO) Implementation of this object can be as low
         as read-write depending on which
         IS Objective or MIB desired requirements are
         not being met by the implementation."

    OBJECT		hDiscSolRcvAddress
    MIN-ACCESS	read-write
    DESCRIPTION
        "(U//FOUO) Implementation of this object can be as low
         as read-write depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hDiscSolRcvPort
    MIN-ACCESS	read-write
    DESCRIPTION
        "(U//FOUO) Implementation of this object can be as low
         as read-write depending on which
         IS Objective or MIB desired requirements are
         not being met by the implementation."

    OBJECT		hDiscDelivPTAddressType
    MIN-ACCESS	read-write
    DESCRIPTION
        "(U//FOUO) Implementation of this object can be as low
         as read-write depending on which
         IS Objective or MIB desired requirements are
         not being met by the implementation."

    OBJECT		hDiscoveryDeliveryTableLastChanged
    MIN-ACCESS	read-only
    DESCRIPTION
        "(U//FOUO) Implementation of this object can be as low
         as read-only depending on which
         IS Objective or MIB desired requirements are
         not being met by the implementation."

    OBJECT		hDiscSolReceptionTableLastChanged
    MIN-ACCESS	read-only
    DESCRIPTION
        "(U//FOUO) Implementation of this object can be as low
         as read-only depending on which
         IS Objective or MIB desired requirements are
         not being met by the implementation."

    OBJECT		hDiscoveryDeliveryTableCount
    MIN-ACCESS	read-only
    DESCRIPTION
        "(U//FOUO) Implementation of this object can be as low
         as read-only depending on which
         IS Objective or MIB desired requirements are
         not being met by the implementation."

    OBJECT		hDiscoverySolicitationTimeout
    MIN-ACCESS	read-write
    DESCRIPTION
        "(U//FOUO) Implementation of this object can be as low
         as read-write depending on which
         IS Objective or MIB desired requirements are
         not being met by the implementation."

    OBJECT		hDiscRegistrationTableCount
    MIN-ACCESS	read-only
    DESCRIPTION
        "(U//FOUO) Implementation of this object can be as low
         as read-only depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hDiscRegPTAddress
    MIN-ACCESS	read-write
    DESCRIPTION
        "(U//FOUO) Implementation of this object can be as low
         as read-write depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."
::= { haipeV030002Conformance 7 }

--
-- Objects referenced by the Legacy Discovery IS
--
hLegacyDiscoveryGroup OBJECT-GROUP
    OBJECTS {
                hDiscoveryEnabled,
                hDiscoveryProbeTimeout,
                hDiscoveryProbeRetry,
                hDiscoveryDeliveryTableCount,
                hDiscoveryDeliveryTableLastChanged,
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hTopologyTableCount,
                hTopologyTableLastChanged,
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hPreplacedKeyTableCount,
                hPreplacedKeyTableCapacity,
                hPreplacedKeyTableLastChanged,
                hPPKUsageType,
                hPPKEffectiveDate,
                hPPKSecurityLevel,
                hPPKZeroizeKey,
                hPPKRegister,
                hPPKAuthority,
                hPPKLastChanged,
--                hPPKTrafficTable,
--                hPPKTrafficTable,
                hPPKTrafficIntegrityAlgorithm,
                hPPKTrafficEncryptAlgorithm,
                hTPSATableCount,
                hTPSATableLastChanged,
                hTPSAspi,
                hTPSAAddressType,
                hTPSALocalCTAddress,
                hTPSARemoteCTAddress,
                hTPSAPTAddressType,
                hTPSALocalPTAddress,
                hTPSARemotePTAddress,
                hTPSADirection,
                hTPSASelectorNextHeaderStart,
                hTPSASelectorNextHeaderEnd,
                hTPSASelectorNextHeaderOpt1Start,
                hTPSASelectorNextHeaderOpt1End,
                hTPSASelectorNextHeaderOpt2Start,
                hTPSASelectorNextHeaderOpt2End,
                hTPSAConnectionType,
                hTPSASecurityPayloadType,
                hTPSAStartTime,
                hTPSAEndTime,
                hTPSAPPK,
                hTPSACreationReason,
                hTPSAEncryptAlgorithm,
                hTPSAIntegrityAlgorithm,
                hTPSAICV,
                hTPSACryptoBlockSize,
                hTPSADSCP,
                hTPSADSCPValue,
                hTPSAPMTU,
                hTPSAECN,
                hTPSAFlowLabel,
                hTPSAFlowLabelValue,
                hTPSADecrementTTL,
                hTPSADIndexType,
                hTPSAPDUNEnabled,
                hTPSAPHRDRate,
                hTPSADFBit,
                hTPSAProcessFlowlabel,
                hTPSARetryICMPCount,
                hTPSAesn,
                hTPSAHCOctets,
                hTPSAHCUcastPkts,
                hTPSAHCMcastPkts,
                hTPSAHCBrdcastPkts,
                hTPSARowStatus,
                hTPSALocalCredentialID,
                hTPSALocalCredentialType,
                hTPSALocalCAName,
                hTPSARemoteCredentialID,
                hTPSARemoteCredentialType,
                hTPSARemoteCAName
            }
    STATUS    current
    DESCRIPTION
        "(U//FOUO) Objects for the 'Legacy Discovery' document"
    ::= { haipeV030002Groups 8 }

--
-- Conformance levels required by the Legacy Discovery IS
--
hLegacyDiscoveryCompliance MODULE-COMPLIANCE
    STATUS    current
    DESCRIPTION
        "(U//FOUO) Compliance levels for objects required by the
          'Legacy Discovery' document"
    MODULE -- this module
    MANDATORY-GROUPS { hLegacyDiscoveryGroup }

    OBJECT		hTopologyTableCount
    MIN-ACCESS	read-only
    DESCRIPTION
        "(U//FOUO) Implementation of this object can be as low
         as read-only depending on which
         IS Objective or MIB desired requirements are
         not being met by the implementation."

    OBJECT		hTPSADecrementTTL
    MIN-ACCESS	read-only
    DESCRIPTION
        "(U//FOUO) Implementation of this object can be as low
         as read-only depending on which
         IS Objective or MIB desired requirements are
         not being met by the implementation."

    OBJECT		hTPSARemoteCredentialType
    MIN-ACCESS	not-accessible
    DESCRIPTION
        "(U//FOUO) Implementation of this object can be as low
         as not-accessible depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		hTPSAesn
    MIN-ACCESS	not-accessible
    DESCRIPTION
        "(U//FOUO) Implementation of this object can be as low
         as not-accessible depending on which
         IS Objective or MIB desired requirements are
         not being met by the implementation."

    OBJECT		hTPSAIntegrityAlgorithm
    MIN-ACCESS	read-write
    DESCRIPTION
        "(U//FOUO) Implementation of this object can be as low
         as read-write depending on which
         IS Objective or MIB desired requirements are
         not being met by the implementation."

    OBJECT		hDiscSearchStartAddress
    MIN-ACCESS	read-write
    DESCRIPTION
        "(U//FOUO) Implementation of this object can be as low
         as read-write depending on which
         IS Objective or MIB desired requirements are
         not being met by the implementation."

    OBJECT		hTopologyTableLastChanged
    MIN-ACCESS	read-only
    DESCRIPTION
        "(U//FOUO) Implementation of this object can be as low
         as read-only depending on which
         IS Objective or MIB desired requirements are
         not being met by the implementation."

    OBJECT		hPPKEffectiveDate
    MIN-ACCESS	read-only
    DESCRIPTION
        "(U//FOUO) Implementation of this object can be as low
         as read-only depending on which
         IS Objective or MIB desired requirements are
         not being met by the implementation."

    OBJECT		hTPSAEndTime
    MIN-ACCESS	read-write
    DESCRIPTION
        "(U//FOUO) Implementation of this object can be as low
         as read-write depending on which
         IS Objective or MIB desired requirements are
         not being met by the implementation."

    OBJECT		hTPSAHCMcastPkts
    MIN-ACCESS	not-accessible
    DESCRIPTION
        "(U//FOUO) Implementation of this object can be as low
         as not-accessible depending on which
         IS Objective or MIB desired requirements are
         not being met by the implementation."

    OBJECT		hTPSADSCP
    MIN-ACCESS	read-write
    DESCRIPTION
        "(U//FOUO) Implementation of this object can be as low
         as read-write depending on which
         IS Objective or MIB desired requirements are
         not being met by the implementation."

    OBJECT		hTPSAspi
    MIN-ACCESS	read-write
    DESCRIPTION
        "(U//FOUO) Implementation of this object can be as low
         as read-write depending on which
         IS Objective or MIB desired requirements are
         not being met by the implementation."

    OBJECT		hPPKTrafficIntegrityAlgorithm
    MIN-ACCESS	read-only
    DESCRIPTION
        "(U//FOUO) Implementation of this object can be as low
         as read-only depending on which
         IS Objective or MIB desired requirements are
         not being met by the implementation."

    OBJECT		hTPSARemoteCAName
    MIN-ACCESS	not-accessible
    DESCRIPTION
        "(U//FOUO) Implementation of this object can be as low
         as not-accessible depending on which
         IS Objective or MIB desired requirements are
         not being met by the implementation."

    OBJECT		hTPSALocalCAName
    MIN-ACCESS	not-accessible
    DESCRIPTION
        "(U//FOUO) Implementation of this object can be as low
         as not-accessible depending on which
         IS Objective or MIB desired requirements are
         not being met by the implementation."

    OBJECT		hTPSASelectorNextHeaderOpt2Start
    MIN-ACCESS	not-accessible
    DESCRIPTION
        "(U//FOUO) Implementation of this object can be as low
         as not-accessible depending on which
         IS Objective or MIB desired requirements are
         not being met by the implementation."

    OBJECT		hTPSALocalPTAddress
    MIN-ACCESS	read-write
    DESCRIPTION
        "(U//FOUO) Implementation of this object can be as low
         as read-write depending on which
         IS Objective or MIB desired requirements are
         not being met by the implementation."

    OBJECT		hDiscDelivType
    MIN-ACCESS	read-write
    DESCRIPTION
        "(U//FOUO) Implementation of this object can be as low
         as read-write depending on which
         IS Objective or MIB desired requirements are
         not being met by the implementation."

    OBJECT		hTPSAPTAddressType
    MIN-ACCESS	read-write
    DESCRIPTION
        "(U//FOUO) Implementation of this object can be as low
         as read-write depending on which
         IS Objective or MIB desired requirements are
         not being met by the implementation."

    OBJECT		hTPSAECN
    MIN-ACCESS	read-write
    DESCRIPTION
        "(U//FOUO) Implementation of this object can be as low
         as read-write depending on which
         IS Objective or MIB desired requirements are
         not being met by the implementation."

    OBJECT		hTPSADFBit
    MIN-ACCESS	read-write
    DESCRIPTION
        "(U//FOUO) Implementation of this object can be as low
         as read-write depending on which
         IS Objective or MIB desired requirements are
         not being met by the implementation."

    OBJECT		hDiscDelivPriority
    MIN-ACCESS	read-write
    DESCRIPTION
        "(U//FOUO) Implementation of this object can be as low
         as read-write depending on which
         IS Objective or MIB desired requirements are
         not being met by the implementation."

    OBJECT		hTPSARetryICMPCount
    MIN-ACCESS	read-write
    DESCRIPTION
        "(U//FOUO) Implementation of this object can be as low
         as read-write depending on which
         IS Objective or MIB desired requirements are
         not being met by the implementation."

    OBJECT		hTPSAConnectionType
    MIN-ACCESS	read-write
    DESCRIPTION
        "(U//FOUO) Implementation of this object can be as low
         as read-write depending on which
         IS Objective or MIB desired requirements are
         not being met by the implementation."

    OBJECT		hTPSASelectorNextHeaderOpt2End
    MIN-ACCESS	not-accessible
    DESCRIPTION
        "(U//FOUO) Implementation of this object can be as low
         as not-accessible depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		hTPSADSCPValue
    MIN-ACCESS	read-write
    DESCRIPTION
        "(U//FOUO) Implementation of this object can be as low
         as read-write depending on which
         IS Objective or MIB desired requirements are
         not being met by the implementation."

    OBJECT		hPreplacedKeyTableCapacity
    MIN-ACCESS	read-only
    DESCRIPTION
        "(U//FOUO) Implementation of this object can be as low
         as read-only depending on which
         IS Objective or MIB desired requirements are
         not being met by the implementation."

    OBJECT		hTPSARemoteCTAddress
    MIN-ACCESS	read-write
    DESCRIPTION
        "(U//FOUO) Implementation of this object can be as low
         as read-write depending on which
         IS Objective or MIB desired requirements are
         not being met by the implementation."

    OBJECT		hPPKRegister
    MIN-ACCESS	not-accessible
    DESCRIPTION
        "(U//FOUO) Implementation of this object can be as low
         as not-accessible depending on which
         IS Objective or MIB desired requirements are
         not being met by the implementation."

    OBJECT		hTPSALocalCredentialType
    MIN-ACCESS	not-accessible
    DESCRIPTION
        "(U//FOUO) Implementation of this object can be as low
         as not-accessible depending on which
         IS Objective or MIB desired requirements are
         not being met by the implementation."

    OBJECT		hTPSAProcessFlowlabel
    MIN-ACCESS	not-accessible
    DESCRIPTION
        "(U//FOUO) Implementation of this object can be as low
         as not-accessible depending on which
         IS Objective or MIB desired requirements are
         not being met by the implementation."

    OBJECT		hTPSAFlowLabelValue
    MIN-ACCESS	read-write
    DESCRIPTION
        "(U//FOUO) Implementation of this object can be as low
         as read-write depending on which
         IS Objective or MIB desired requirements are
         not being met by the implementation."

    OBJECT		hTPSAEncryptAlgorithm
    MIN-ACCESS	read-only
    DESCRIPTION
        "(U//FOUO) Implementation of this object can be as low
         as read-only depending on which
         IS Objective or MIB desired requirements are
         not being met by the implementation."

    OBJECT		hPPKAuthority
    MIN-ACCESS	not-accessible
    DESCRIPTION
        "(U//FOUO) Implementation of this object can be as low
         as not-accessible depending on which
         IS Objective or MIB desired requirements are
         not being met by the implementation."

    OBJECT		hTPSARemotePTAddress
    MIN-ACCESS	read-write
    DESCRIPTION
        "(U//FOUO) Implementation of this object can be as low
         as read-write depending on which
         IS Objective or MIB desired requirements are
         not being met by the implementation."

    OBJECT		hDiscoveryEnabled
    MIN-ACCESS	read-write
    DESCRIPTION
        "(U//FOUO) Implementation of this object can be as low
         as read-write depending on which
         IS Objective or MIB desired requirements are
         not being met by the implementation."

    OBJECT		hTPSALocalCTAddress
    MIN-ACCESS	read-write
    DESCRIPTION
        "(U//FOUO) Implementation of this object can be as low
         as read-write depending on which
         IS Objective or MIB desired requirements are
         not being met by the implementation."

    OBJECT		hTPSAPDUNEnabled
    MIN-ACCESS	read-write
    DESCRIPTION
        "(U//FOUO) Implementation of this object can be as low
         as read-write depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hTPSASelectorNextHeaderEnd
    MIN-ACCESS	not-accessible
    DESCRIPTION
        "(U//FOUO) Implementation of this object can be as low
         as not-accessible depending on which
         IS Objective or MIB desired requirements are
         not being met by the implementation."

    OBJECT		hDiscoveryDeliveryTableLastChanged
    MIN-ACCESS	read-only
    DESCRIPTION
        "(U//FOUO) Implementation of this object can be as low
         as read-only depending on which
         IS Objective or MIB desired requirements are
         not being met by the implementation."

    OBJECT		hPreplacedKeyTableLastChanged
    MIN-ACCESS	read-only
    DESCRIPTION
        "(U//FOUO) Implementation of this object can be as low
         as read-only depending on which
         IS Objective or MIB desired requirements are
         not being met by the implementation."

    OBJECT		hPPKSecurityLevel
    MIN-ACCESS	read-only
    DESCRIPTION
        "(U//FOUO) Implementation of this object can be as low
         as read-only depending on which
         IS Objective or MIB desired requirements are
         not being met by the implementation."

    OBJECT		hTPSATableCount
    MIN-ACCESS	read-only
    DESCRIPTION
        "(U//FOUO) Implementation of this object can be as low
         as read-only depending on which
         IS Objective or MIB desired requirements are
         not being met by the implementation."

    OBJECT		hPreplacedKeyTableCount
    MIN-ACCESS	read-only
    DESCRIPTION
        "(U//FOUO) Implementation of this object can be as low
         as read-only depending on which
         IS Objective or MIB desired requirements are
         not being met by the implementation."

    OBJECT		hTPSACryptoBlockSize
    MIN-ACCESS	read-write
    DESCRIPTION
        "(U//FOUO) Implementation of this object can be as low
         as read-write depending on which
         IS Objective or MIB desired requirements are
         not being met by the implementation."

    OBJECT		hTPSACreationReason
    MIN-ACCESS	read-only
    DESCRIPTION
        "(U//FOUO) Implementation of this object can be as low
         as read-only depending on which
         IS Objective or MIB desired requirements are
         not being met by the implementation."

    OBJECT		hTPSADirection
    MIN-ACCESS	read-write
    DESCRIPTION
        "(U//FOUO) Implementation of this object can be as low
         as read-write depending on which
         IS Objective or MIB desired requirements are
         not being met by the implementation."

    OBJECT		hTPSAFlowLabel
    MIN-ACCESS	read-write
    DESCRIPTION
        "(U//FOUO) Implementation of this object can be as low
         as read-write depending on which
         IS Objective or MIB desired requirements are
         not being met by the implementation."

    OBJECT		hTPSALocalCredentialID
    MIN-ACCESS	read-only
    DESCRIPTION
        "(U//FOUO) Implementation of this object can be as low
         as read-only depending on which
         IS Objective or MIB desired requirements are
         not being met by the implementation."

    OBJECT		hTPSAHCOctets
    MIN-ACCESS	not-accessible
    DESCRIPTION
        "(U//FOUO) Implementation of this object can be as low
         as not-accessible depending on which
         IS Objective or MIB desired requirements are
         not being met by the implementation."

    OBJECT		hTPSAPMTU
    MIN-ACCESS	read-only
    DESCRIPTION
        "(U//FOUO) Implementation of this object can be as low
         as read-only depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hTPSAStartTime
    MIN-ACCESS	read-write
    DESCRIPTION
        "(U//FOUO) Implementation of this object can be as low
         as read-write depending on which
         IS Objective or MIB desired requirements are
         not being met by the implementation."

    OBJECT		hPPKZeroizeKey
    MIN-ACCESS	read-write
    DESCRIPTION
        "(U//FOUO) Implementation of this object can be as low
         as read-write depending on which
         IS Objective or MIB desired requirements are
         not being met by the implementation."

    OBJECT		hTPSAHCUcastPkts
    MIN-ACCESS	not-accessible
    DESCRIPTION
        "(U//FOUO) Implementation of this object can be as low
         as not-accessible depending on which
         IS Objective or MIB desired requirements are
         not being met by the implementation."

    OBJECT		hTPSADIndexType
    MIN-ACCESS	read-write
    DESCRIPTION
        "(U//FOUO) Implementation of this object can be as low
         as read-write depending on which
         IS Objective or MIB desired requirements are
         not being met by the implementation."

    OBJECT		hTPSASelectorNextHeaderOpt1End
    MIN-ACCESS	not-accessible
    DESCRIPTION
        "(U//FOUO) Implementation of this object can be as low
         as not-accessible depending on which
         IS Objective or MIB desired requirements are
         not being met by the implementation."

    OBJECT		hTPSASelectorNextHeaderOpt1Start
    MIN-ACCESS	not-accessible
    DESCRIPTION
        "(U//FOUO) Implementation of this object can be as low
         as not-accessible depending on which
         IS Objective or MIB desired requirements are
         not being met by the implementation."

    OBJECT		hTPSATableLastChanged
    MIN-ACCESS	read-only
    DESCRIPTION
        "(U//FOUO) Implementation of this object can be as low
         as read-only depending on which
         IS Objective or MIB desired requirements are
         not being met by the implementation."

    OBJECT		hDiscDelivPTAddress
    MIN-ACCESS	read-write
    DESCRIPTION
        "(U//FOUO) Implementation of this object can be as low
         as read-write depending on which
         IS Objective or MIB desired requirements are
         not being met by the implementation."

    OBJECT		hDiscDelivStatus
    MIN-ACCESS	read-write
    DESCRIPTION
        "(U//FOUO) Implementation of this object can be as low
         as read-write depending on which
         IS Objective or MIB desired requirements are
         not being met by the implementation."

    OBJECT		hDiscoveryProbeRetry
    MIN-ACCESS	read-only
    DESCRIPTION
        "(U//FOUO) Implementation of this object can be as low
         as read-only depending on which
         IS Objective or MIB desired requirements are
         not being met by the implementation."

    OBJECT		hDiscSearchEndAddress
    MIN-ACCESS	read-write
    DESCRIPTION
        "(U//FOUO) Implementation of this object can be as low
         as read-write depending on which
         IS Objective or MIB desired requirements are
         not being met by the implementation."

    OBJECT		hPPKTrafficEncryptAlgorithm
    MIN-ACCESS	read-only
    DESCRIPTION
        "(U//FOUO) Implementation of this object can be as low
         as read-only depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hTPSARemoteCredentialID
    MIN-ACCESS	not-accessible
    DESCRIPTION
        "(U//FOUO) Implementation of this object can be as low
         as not-accessible depending on which
         IS Objective or MIB desired requirements are
         not being met by the implementation."

    OBJECT		hDiscoveryProbeTimeout
    MIN-ACCESS	read-only
    DESCRIPTION
        "(U//FOUO) Implementation of this object can be as low
         as read-only depending on which
         IS Objective or MIB desired requirements are
         not being met by the implementation."

--    OBJECT		hPPKTrafficTable
--    MIN-ACCESS	read-only
--    DESCRIPTION
--        "(U//FOUO) Implementation of this object can be as low
--         as read-only depending on which
--         IS Objective or MIB desired requirements are
--         not being met by the implementation."

    OBJECT		hPPKLastChanged
    MIN-ACCESS	read-only
    DESCRIPTION
        "(U//FOUO) Implementation of this object can be as low
         as read-only depending on which
         IS Objective or MIB desired requirements are
         not being met by the implementation."

    OBJECT		hTPSAPPK
    MIN-ACCESS	read-write
    DESCRIPTION
        "(U//FOUO) Implementation of this object can be as low
         as read-write depending on which
         IS Objective or MIB desired requirements are
         not being met by the implementation."

    OBJECT		hTPSAHCBrdcastPkts
    MIN-ACCESS	not-accessible
    DESCRIPTION
        "(U//FOUO) Implementation of this object can be as low
         as not-accessible depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hDiscDelivPTPort
    MIN-ACCESS	read-write
    DESCRIPTION
        "(U//FOUO) Implementation of this object can be as low
         as read-write depending on which
         IS Objective or MIB desired requirements are
         not being met by the implementation."

    OBJECT		hTPSARowStatus
    MIN-ACCESS	read-write
    DESCRIPTION
        "(U//FOUO) Implementation of this object can be as low
         as read-write depending on which
         IS Objective or MIB desired requirements are
         not being met by the implementation."

    OBJECT		hTPSASecurityPayloadType
    MIN-ACCESS	read-only
    DESCRIPTION
        "(U//FOUO) Implementation of this object can be as low
         as read-only depending on which
         IS Objective or MIB desired requirements are
         not being met by the implementation."

    OBJECT		hDiscSearchAddressType
    MIN-ACCESS	read-write
    DESCRIPTION
        "(U//FOUO) Implementation of this object can be as low
         as read-write depending on which
         IS Objective or MIB desired requirements are
         not being met by the implementation."

    OBJECT		hTPSAAddressType
    MIN-ACCESS	read-write
    DESCRIPTION
        "(U//FOUO) Implementation of this object can be as low
         as read-write depending on which
         IS Objective or MIB desired requirements are
         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hTPSAPHRDRate
    MIN-ACCESS	read-write
    DESCRIPTION
        "(U//FOUO) Implementation of this object can be as low
         as read-write depending on which
         IS Objective or MIB desired requirements are
         not being met by the implementation."

    OBJECT		hTPSASelectorNextHeaderStart
    MIN-ACCESS	not-accessible
    DESCRIPTION
        "(U//FOUO) Implementation of this object can be as low
         as not-accessible depending on which
         IS Objective or MIB desired requirements are
         not being met by the implementation."

    OBJECT		hDiscDelivPTAddressType
    MIN-ACCESS	read-write
    DESCRIPTION
        "(U//FOUO) Implementation of this object can be as low
         as read-write depending on which
         IS Objective or MIB desired requirements are
         not being met by the implementation."

    OBJECT		hDiscoveryDeliveryTableCount
    MIN-ACCESS	read-only
    DESCRIPTION
        "(U//FOUO) Implementation of this object can be as low
         as read-only depending on which
         IS Objective or MIB desired requirements are
         not being met by the implementation."

    OBJECT		hTPSAICV
    MIN-ACCESS	not-accessible
    DESCRIPTION
        "(U//FOUO) Implementation of this object can be as low
         as not-accessible depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hPPKUsageType
    MIN-ACCESS	read-write
    DESCRIPTION
        "(U//FOUO) Implementation of this object can be as low
         as read-write depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."
::= { haipeV030002Conformance 8 }

--
-- Objects referenced by the Traffic Protection IS
--
hTrafficProtectionGroup OBJECT-GROUP
    OBJECTS {
                hTopologyDestHostAddrType,
                hTopologyDestHost,
                hTopologyDestHostPTPfxLen,
                hTopologyDestHaipeCTAddrType,
                hTopologyDestHaipeCTAddr,
                hTopologyDestHaipePTAddrType,
                hTopologyDestHaipePTAddr,
                hTopologyRowStatus,
                hTopologyDestAdminCost,
                hTopologyMethod,
                hTopologyLifetime,
                hIfv4TTL,
                hIfv4OutputPacketPadding,
                hIfv4OutputPacketFixedSize,
                hIfv6HopLimit,
                hIfv6OutputPacketPadding,
                hIfv6OutputPacketFixedSize,
--                hIfAddrAssignmentTable,
--                hIfAddrAssignmentTable,
                hiaaInterface,
                hiaaType,
                hiaaAddress,
                hiaaPrefixLen,
                hiaaRowStatus,
                hFireflyTableCount,
                hFireflyTableLastChanged,
                hFFKMID,
                hFFUniversalID,
                hFFUniversalEdition,
                hFFAlgorithmPrivilege,
                hFFSecurityLevels,
                hFFMaterialType,
                hFFExpiration,
                hFFNextVector,
                hFFPartitionCode,
                hFFLastChanged,
                hFFZeroizeKey,
                hFFAuthority,
                hFFASCIIID,
                hFFIsTestKey,
                hFFEnhancedFFTag,
                hPreplacedKeyTableCount,
                hPreplacedKeyTableCapacity,
                hPreplacedKeyTableLastChanged,
                hPPKUsageType,
                hPPKEffectiveDate,
                hPPKSecurityLevel,
                hPPKZeroizeKey,
                hPPKRegister,
                hPPKAuthority,
                hPPKLastChanged,
--                hPPKTrafficTable,
                hPPKTrafficTableMaxCount,
--                hPPKTrafficTable,
                hPPKTrafficIntegrityAlgorithm,
                hPPKTrafficEncryptAlgorithm,
--                hPPKEKTable,
                hPPKEKTableMaxCount,
--                hPPKEKTable,
                hPPKEKKeyType,
                hPPKEKUniversalID,
                hPPKChainTableCount,
                hPPKChainTableLastChanged,
                hPPKChainID,
                hPPKChainOrder,
                hPPKChainPPK,
                hPPKChainEffectiveDate,
                hPPKChainIntegrityAlgorithm,
                hPPKChainEncryptionAlgorithm,
                hPPKChainRowStatus,
--                hUniversalTable,
--                hUniversalTable,
                hUniversalID,
                hUniversalCKLDate,
                hUniversalCKLVersion,
--                hFFKeyExpirationWarning,
--                hPPKKeyExpirationWarning,
                hPPKKeyExpirationWarningCount,
                hIPhRuleTableCount,
                hIPhRuleTableLastChanged,
                hIPhRuleName,
                hIPhRuleSelectorName,
                hIPhRuleAction,
                hIPhRuleActionIndex,
                hIPhRuleAdminStatus,
                hIPhRuleLastChanged,
                hIPhRuleRowStatus,
                hIPhSelectorTableCount,
                hIPhSelectorTableLastChanged,
                hIPhSelectorType,
                hIPhSelectorIPVersion,
                hIPhSelectorSrcAddressBegin,
                hIPhSelectorSrcAddressEnd,
                hIPhSelectorDstAddressBegin,
                hIPhSelectorDstAddressEnd,
                hIPhSelectorLastChanged,
                hIPhSelectorRowStatus,
--                hTPiphSATransforms,
--                hTPiphFFSA,
--                hTPiphFFSAKey,
                hIPhFFSATableCount,
                hIPhFFSATableLastChanged,
                hIPhFFSAFF,
                hIPhFFSATransformsName,
                hIPhFFSADSCP,
                hIPhFFSADSCPValue,
                hIPhFFSAECN,
                hIPhFFSAFlowLabel,
                hIPhFFSAFlowLabelValue,
                hIPhFFSADecrementTTL,
                hIPhFFSADIndexType,
                hIPhFFSALastChanged,
                hIPhFFSARowStatus,
                hIPhFFSAPDUNEnabled,
                hIPhFFSAPHRDRate,
                hIPhFFSADFBit,
                hIPhFFSAProcessFlowlabel,
                hIPhFFSARetryICMPCount,
                hIPhFFSAConnectionType,
                hIPhFFSACTOutAddressType,
                hIPhFFSACTOutAddress,
                hIPhFFSAPopulateFromPacket,
                hIPhFFSAFFUniversal,
                hIPhFFSAFFUniversalEdition,
--                hTPiphFFSATransforms,
                hIPhFFSATransformsTableCount,
                hIPhFFSATransformsTableLastChanged,
                hIPhFFSATransformEncryptAlgorithm,
                hIPhFFSATransformKeyUpdateMethod,
                hIPhFFSATransformKeyUpdateFrequency,
                hIPhFFSATransformCryptoBlockSize,
                hIPhFFSATransformLastChanged,
                hIPhFFSATransformRowStatus,
                hIPhFFSATransformESN,
                hIPhFFSATransformIntegrityAlgorithm,
                hIPhFFSATransformHashAlgorithm,
                hIPhFFSATransformAuthenticationAlgorithm,
                hIPhFFSATransformICV,
                hTPSATableCount,
                hTPSATableLastChanged,
                hTPSAspi,
                hTPSAAddressType,
                hTPSALocalCTAddress,
                hTPSARemoteCTAddress,
                hTPSAPTAddressType,
                hTPSALocalPTAddress,
                hTPSARemotePTAddress,
                hTPSADirection,
                hTPSASelectorNextHeaderStart,
                hTPSASelectorNextHeaderEnd,
                hTPSASelectorNextHeaderOpt1Start,
                hTPSASelectorNextHeaderOpt1End,
                hTPSASelectorNextHeaderOpt2Start,
                hTPSASelectorNextHeaderOpt2End,
                hTPSAConnectionType,
                hTPSASecurityPayloadType,
                hTPSAStartTime,
                hTPSAEndTime,
                hTPSAPPK,
                hTPSACreationReason,
                hTPSAEncryptAlgorithm,
                hTPSAIntegrityAlgorithm,
                hTPSAICV,
                hTPSACryptoBlockSize,
                hTPSADSCP,
                hTPSADSCPValue,
                hTPSAPMTU,
                hTPSAECN,
                hTPSAFlowLabel,
                hTPSAFlowLabelValue,
                hTPSADecrementTTL,
                hTPSADIndexType,
                hTPSAPDUNEnabled,
                hTPSAPHRDRate,
                hTPSADFBit,
                hTPSAProcessFlowlabel,
                hTPSARetryICMPCount,
                hTPSAesn,
                hTPSAHCOctets,
                hTPSAHCUcastPkts,
                hTPSAHCMcastPkts,
                hTPSAHCBrdcastPkts,
                hTPSARowStatus,
                hTPSALocalCredentialID,
                hTPSALocalCredentialType,
                hTPSALocalCAName,
                hTPSARemoteCredentialID,
                hTPSARemoteCredentialType,
                hTPSARemoteCAName,
--                hTPSAAddressSelectorTable,
--                hTPSAAddressSelectorTable,
                hTPSAAddressSrcOrDest,
                hTPSAAddressStart,
                hTPSAAddressEnd,
                hTPSAAddressRowStatus
            }
    STATUS    current
    DESCRIPTION
        "(U//FOUO) Objects for the 'Traffic Protection' document"
    ::= { haipeV030002Groups 9 }

--
-- Conformance levels required by the Traffic Protection IS
--
hTrafficProtectionCompliance MODULE-COMPLIANCE
    STATUS    current
    DESCRIPTION
        "(U//FOUO) Compliance levels for objects required by the
          'Traffic Protection' document"
    MODULE -- this module
    MANDATORY-GROUPS { hTrafficProtectionGroup }

    OBJECT		hPPKEKTableMaxCount
    MIN-ACCESS	read-only
    DESCRIPTION
        "(U//FOUO) Implementation of this object can be as low
         as read-only depending on which
         IS Objective or MIB desired requirements are
         not being met by the implementation."

    OBJECT		hIPhFFSATransformLastChanged
    MIN-ACCESS	read-only
    DESCRIPTION
        "(U//FOUO) Implementation of this object can be as low
         as read-only depending on which
         IS Objective or MIB desired requirements are
         not being met by the implementation."

    OBJECT		hUniversalCKLVersion
    MIN-ACCESS	read-only
    DESCRIPTION
        "(U//FOUO) Implementation of this object can be as low
         as read-only depending on which
         IS Objective or MIB desired requirements are
         not being met by the implementation."

    OBJECT		hTopologyMethod
    MIN-ACCESS	read-only
    DESCRIPTION
        "(U//FOUO) Implementation of this object can be as low
         as read-only depending on which
         IS Objective or MIB desired requirements are
         not being met by the implementation."

    OBJECT		hTPSAIntegrityAlgorithm
    MIN-ACCESS	read-write
    DESCRIPTION
        "(U//FOUO) Implementation of this object can be as low
         as read-write depending on which
         IS Objective or MIB desired requirements are
         not being met by the implementation."

    OBJECT		hPPKEffectiveDate
    MIN-ACCESS	read-only
    DESCRIPTION
        "(U//FOUO) Implementation of this object can be as low
         as read-only depending on which
         IS Objective or MIB desired requirements are
         not being met by the implementation."

    OBJECT		hIfv4OutputPacketPadding
    MIN-ACCESS	not-accessible
    DESCRIPTION
        "(U//FOUO) Implementation of this object can be as low
         as not-accessible depending on which
         IS Objective or MIB desired requirements are
         not being met by the implementation."

    OBJECT		hTPSAEndTime
    MIN-ACCESS	read-write
    DESCRIPTION
        "(U//FOUO) Implementation of this object can be as low
         as read-write depending on which
         IS Objective or MIB desired requirements are
         not being met by the implementation."

    OBJECT		hTPSARemoteCAName
    MIN-ACCESS	not-accessible
    DESCRIPTION
        "(U//FOUO) Implementation of this object can be as low
         as not-accessible depending on which
         IS Objective or MIB desired requirements are
         not being met by the implementation."

    OBJECT		hTPSALocalCAName
    MIN-ACCESS	not-accessible
    DESCRIPTION
        "(U//FOUO) Implementation of this object can be as low
         as not-accessible depending on which
         IS Objective or MIB desired requirements are
         not being met by the implementation."

    OBJECT		hFFExpiration
    MIN-ACCESS	read-only
    DESCRIPTION
        "(U//FOUO) Implementation of this object can be as low
         as read-only depending on which
         IS Objective or MIB desired requirements are
         not being met by the implementation."

    OBJECT		hIPhFFSATransformKeyUpdateMethod
    MIN-ACCESS	read-write
    DESCRIPTION
        "(U//FOUO) Implementation of this object can be as low
         as read-write depending on which
         IS Objective or MIB desired requirements are
         not being met by the implementation."

    OBJECT		hPPKChainRowStatus
    MIN-ACCESS	read-write
    DESCRIPTION
        "(U//FOUO) Implementation of this object can be as low
         as read-write depending on which
         IS Objective or MIB desired requirements are
         not being met by the implementation."

    OBJECT		hTPSAPTAddressType
    MIN-ACCESS	read-write
    DESCRIPTION
        "(U//FOUO) Implementation of this object can be as low
         as read-write depending on which
         IS Objective or MIB desired requirements are
         not being met by the implementation."

    OBJECT		hIfv4TTL
    MIN-ACCESS	read-only
    DESCRIPTION
        "(U//FOUO) Implementation of this object can be as low
         as read-only depending on which
         IS Objective or MIB desired requirements are
         not being met by the implementation."

--    OBJECT		hTPiphFFSAKey
--    MIN-ACCESS	read-write
--    DESCRIPTION
--        "(U//FOUO) Implementation of this object can be as low
--         as read-write depending on which
--         IS Objective or MIB desired requirements are
--         not being met by the implementation."

    OBJECT		hIPhSelectorTableLastChanged
    MIN-ACCESS	read-only
    DESCRIPTION
        "(U//FOUO) Implementation of this object can be as low
         as read-only depending on which
         IS Objective or MIB desired requirements are
         not being met by the implementation."

    OBJECT		hIPhFFSATransformAuthenticationAlgorithm
    MIN-ACCESS	read-write
    DESCRIPTION
        "(U//FOUO) Implementation of this object can be as low
         as read-write depending on which
         IS Objective or MIB desired requirements are
         not being met by the implementation."

    OBJECT		hIPhFFSATransformsTableCount
    MIN-ACCESS	read-only
    DESCRIPTION
        "(U//FOUO) Implementation of this object can be as low
         as read-only depending on which
         IS Objective or MIB desired requirements are
         not being met by the implementation."

    OBJECT		hPPKKeyExpirationWarningCount
    MIN-ACCESS	accessible-for-notify
    DESCRIPTION
        "(U//FOUO) Implementation of this object can be as low
         as accessible-for-notify depending on which
         IS Objective or MIB desired requirements are
         not being met by the implementation."

    OBJECT		hIPhSelectorSrcAddressEnd
    MIN-ACCESS	read-write
    DESCRIPTION
        "(U//FOUO) Implementation of this object can be as low
         as read-write depending on which
         IS Objective or MIB desired requirements are
         not being met by the implementation."

    OBJECT		hTPSAConnectionType
    MIN-ACCESS	read-write
    DESCRIPTION
        "(U//FOUO) Implementation of this object can be as low
         as read-write depending on which
         IS Objective or MIB desired requirements are
         not being met by the implementation."

    OBJECT		hTPSASelectorNextHeaderOpt2End
    MIN-ACCESS	not-accessible
    DESCRIPTION
        "(U//FOUO) Implementation of this object can be as low
         as not-accessible depending on which
         IS Objective or MIB desired requirements are
         not being met by the implementation."

    OBJECT		hIPhFFSADFBit
    MIN-ACCESS	read-write
    DESCRIPTION
        "(U//FOUO) Implementation of this object can be as low
         as read-write depending on which
         IS Objective or MIB desired requirements are
         not being met by the implementation."

    OBJECT		hIPhFFSATransformHashAlgorithm
    MIN-ACCESS	read-write
    DESCRIPTION
        "(U//FOUO) Implementation of this object can be as low
         as read-write depending on which
         IS Objective or MIB desired requirements are
         not being met by the implementation."

    OBJECT		hPPKChainPPK
    MIN-ACCESS	read-write
    DESCRIPTION
        "(U//FOUO) Implementation of this object can be as low
         as read-write depending on which
         IS Objective or MIB desired requirements are
         not being met by the implementation."

    OBJECT		hTPSADSCPValue
    MIN-ACCESS	read-write
    DESCRIPTION
        "(U//FOUO) Implementation of this object can be as low
         as read-write depending on which
         IS Objective or MIB desired requirements are
         not being met by the implementation."

    OBJECT		hPPKRegister
    MIN-ACCESS	not-accessible
    DESCRIPTION
        "(U//FOUO) Implementation of this object can be as low
         as not-accessible depending on which
         IS Objective or MIB desired requirements are
         not being met by the implementation."

    OBJECT		hFFMaterialType
    MIN-ACCESS	read-only
    DESCRIPTION
        "(U//FOUO) Implementation of this object can be as low
         as read-only depending on which
         IS Objective or MIB desired requirements are
         not being met by the implementation."

    OBJECT		hTPSAProcessFlowlabel
    MIN-ACCESS	read-write
    DESCRIPTION
        "(U//FOUO) Implementation of this object can be as low
         as read-write depending on which
         IS Objective or MIB desired requirements are
         not being met by the implementation."

    OBJECT		hPPKAuthority
    MIN-ACCESS	not-accessible
    DESCRIPTION
        "(U//FOUO) Implementation of this object can be as low
         as not-accessible depending on which
         IS Objective or MIB desired requirements are
         not being met by the implementation."

    OBJECT		hFFKMID
    MIN-ACCESS	read-only
    DESCRIPTION
        "(U//FOUO) Implementation of this object can be as low
         as read-only depending on which
         IS Objective or MIB desired requirements are
         not being met by the implementation."

    OBJECT		hTPSARemotePTAddress
    MIN-ACCESS	read-write
    DESCRIPTION
        "(U//FOUO) Implementation of this object can be as low
         as read-write depending on which
         IS Objective or MIB desired requirements are
         not being met by the implementation."

    OBJECT		hIPhSelectorSrcAddressBegin
    MIN-ACCESS	read-write
    DESCRIPTION
        "(U//FOUO) Implementation of this object can be as low
         as read-write depending on which
         IS Objective or MIB desired requirements are
         not being met by the implementation."

    OBJECT		hIPhFFSATransformKeyUpdateFrequency
    MIN-ACCESS	read-write
    DESCRIPTION
        "(U//FOUO) Implementation of this object can be as low
         as read-write depending on which
         IS Objective or MIB desired requirements are
         not being met by the implementation."

    OBJECT		hFFZeroizeKey
    MIN-ACCESS	read-write
    DESCRIPTION
        "(U//FOUO) Implementation of this object can be as low
         as read-write depending on which
         IS Objective or MIB desired requirements are
         not being met by the implementation."

    OBJECT		hTopologyDestHost
    MIN-ACCESS	read-write
    DESCRIPTION
        "(U//FOUO) Implementation of this object can be as low
         as read-write depending on which
         IS Objective or MIB desired requirements are
         not being met by the implementation."

    OBJECT		hFFNextVector
    MIN-ACCESS	read-only
    DESCRIPTION
        "(U//FOUO) Implementation of this object can be as low
         as read-only depending on which
         IS Objective or MIB desired requirements are
         not being met by the implementation."

    OBJECT		hPPKEKKeyType
    MIN-ACCESS	read-write
    DESCRIPTION
        "(U//FOUO) Implementation of this object can be as low
         as read-write depending on which
         IS Objective or MIB desired requirements are
         not being met by the implementation."

    OBJECT		hPreplacedKeyTableLastChanged
    MIN-ACCESS	read-only
    DESCRIPTION
        "(U//FOUO) Implementation of this object can be as low
         as read-only depending on which
         IS Objective or MIB desired requirements are
         not being met by the implementation."

    OBJECT		hIPhRuleLastChanged
    MIN-ACCESS	read-only
    DESCRIPTION
        "(U//FOUO) Implementation of this object can be as low
         as read-only depending on which
         IS Objective or MIB desired requirements are
         not being met by the implementation."

    OBJECT		hIPhFFSATransformCryptoBlockSize
    MIN-ACCESS	read-write
    DESCRIPTION
        "(U//FOUO) Implementation of this object can be as low
         as read-write depending on which
         IS Objective or MIB desired requirements are
         not being met by the implementation."

    OBJECT		hPPKSecurityLevel
    MIN-ACCESS	read-only
    DESCRIPTION
        "(U//FOUO) Implementation of this object can be as low
         as read-only depending on which
         IS Objective or MIB desired requirements are
         not being met by the implementation."

    OBJECT		hTPSACryptoBlockSize
    MIN-ACCESS	read-write
    DESCRIPTION
        "(U//FOUO) Implementation of this object can be as low
         as read-write depending on which
         IS Objective or MIB desired requirements are
         not being met by the implementation."

    OBJECT		hTPSACreationReason
    MIN-ACCESS	read-only
    DESCRIPTION
        "(U//FOUO) Implementation of this object can be as low
         as read-only depending on which
         IS Objective or MIB desired requirements are
         not being met by the implementation."

    OBJECT		hTPSADirection
    MIN-ACCESS	read-write
    DESCRIPTION
        "(U//FOUO) Implementation of this object can be as low
         as read-write depending on which
         IS Objective or MIB desired requirements are
         not being met by the implementation."

    OBJECT		hIPhSelectorIPVersion
    MIN-ACCESS	read-write
    DESCRIPTION
        "(U//FOUO) Implementation of this object can be as low
         as read-write depending on which
         IS Objective or MIB desired requirements are
         not being met by the implementation."

    OBJECT		hTPSAFlowLabel
    MIN-ACCESS	read-write
    DESCRIPTION
        "(U//FOUO) Implementation of this object can be as low
         as read-write depending on which
         IS Objective or MIB desired requirements are
         not being met by the implementation."

    OBJECT		hFireflyTableLastChanged
    MIN-ACCESS	read-only
    DESCRIPTION
        "(U//FOUO) Implementation of this object can be as low
         as read-only depending on which
         IS Objective or MIB desired requirements are
         not being met by the implementation."

--    OBJECT		hTPiphFFSA
--    MIN-ACCESS	read-write
--    DESCRIPTION
--        "(U//FOUO) Implementation of this object can be as low
--         as read-write depending on which
--         IS Objective or MIB desired requirements are
--         not being met by the implementation."

    OBJECT		hIPhFFSATableCount
    MIN-ACCESS	read-only
    DESCRIPTION
        "(U//FOUO) Implementation of this object can be as low
         as read-only depending on which
         IS Objective or MIB desired requirements are
         not being met by the implementation."

    OBJECT		hTPSAHCOctets
    MIN-ACCESS	not-accessible
    DESCRIPTION
        "(U//FOUO) Implementation of this object can be as low
         as not-accessible depending on which
         IS Objective or MIB desired requirements are
         not being met by the implementation."

    OBJECT		hTPSAPMTU
    MIN-ACCESS	read-only
    DESCRIPTION
        "(U//FOUO) Implementation of this object can be as low
         as read-only depending on which
         IS Objective or MIB desired requirements are
         not being met by the implementation."

    OBJECT		hIPhFFSAFFUniversal
    MIN-ACCESS	read-write
    DESCRIPTION
        "(U//FOUO) Implementation of this object can be as low
         as read-write depending on which
         IS Objective or MIB desired requirements are
         not being met by the implementation."

    OBJECT		hTopologyDestHaipePTAddr
    MIN-ACCESS	read-write
    DESCRIPTION
        "(U//FOUO) Implementation of this object can be as low
         as read-write depending on which
         IS Objective or MIB desired requirements are
         not being met by the implementation."

    OBJECT		hiaaType
    MIN-ACCESS	not-accessible
    DESCRIPTION
        "(U//FOUO) Implementation of this object can be as low
         as not-accessible depending on which
         IS Objective or MIB desired requirements are
         not being met by the implementation."

    OBJECT		hPPKZeroizeKey
    MIN-ACCESS	read-write
    DESCRIPTION
        "(U//FOUO) Implementation of this object can be as low
         as read-write depending on which
         IS Objective or MIB desired requirements are
         not being met by the implementation."

    OBJECT		hPPKChainID
    MIN-ACCESS	read-write
    DESCRIPTION
        "(U//FOUO) Implementation of this object can be as low
         as read-write depending on which
         IS Objective or MIB desired requirements are
         not being met by the implementation."

    OBJECT		hPPKChainOrder
    MIN-ACCESS	read-write
    DESCRIPTION
        "(U//FOUO) Implementation of this object can be as low
         as read-write depending on which
         IS Objective or MIB desired requirements are
         not being met by the implementation."

    OBJECT		hTPSAHCUcastPkts
    MIN-ACCESS	not-accessible
    DESCRIPTION
        "(U//FOUO) Implementation of this object can be as low
         as not-accessible depending on which
         IS Objective or MIB desired requirements are
         not being met by the implementation."

    OBJECT		hFFPartitionCode
    MIN-ACCESS	read-only
    DESCRIPTION
        "(U//FOUO) Implementation of this object can be as low
         as read-only depending on which
         IS Objective or MIB desired requirements are
         not being met by the implementation."

    OBJECT		hTPSASelectorNextHeaderOpt1Start
    MIN-ACCESS	not-accessible
    DESCRIPTION
        "(U//FOUO) Implementation of this object can be as low
         as not-accessible depending on which
         IS Objective or MIB desired requirements are
         not being met by the implementation."

    OBJECT		hIPhFFSATransformsTableLastChanged
    MIN-ACCESS	read-only
    DESCRIPTION
        "(U//FOUO) Implementation of this object can be as low
         as read-only depending on which
         IS Objective or MIB desired requirements are
         not being met by the implementation."

    OBJECT		hUniversalCKLDate
    MIN-ACCESS	read-only
    DESCRIPTION
        "(U//FOUO) Implementation of this object can be as low
         as read-only depending on which
         IS Objective or MIB desired requirements are
         not being met by the implementation."

    OBJECT		hIPhFFSATransformEncryptAlgorithm
    MIN-ACCESS	read-write
    DESCRIPTION
        "(U//FOUO) Implementation of this object can be as low
         as read-write depending on which
         IS Objective or MIB desired requirements are
         not being met by the implementation."

    OBJECT		hIPhFFSAProcessFlowlabel
    MIN-ACCESS	read-write
    DESCRIPTION
        "(U//FOUO) Implementation of this object can be as low
         as read-write depending on which
         IS Objective or MIB desired requirements are
         not being met by the implementation."

    OBJECT		hIPhRuleActionIndex
    MIN-ACCESS	read-write
    DESCRIPTION
        "(U//FOUO) Implementation of this object can be as low
         as read-write depending on which
         IS Objective or MIB desired requirements are
         not being met by the implementation."

--    OBJECT		hPPKTrafficTable
--    MIN-ACCESS	read-only
--    DESCRIPTION
--        "(U//FOUO) Implementation of this object can be as low
--         as read-only depending on which
--         IS Objective or MIB desired requirements are
--         not being met by the implementation."

    OBJECT		hPPKLastChanged
    MIN-ACCESS	read-only
    DESCRIPTION
        "(U//FOUO) Implementation of this object can be as low
         as read-only depending on which
         IS Objective or MIB desired requirements are
         not being met by the implementation."

    OBJECT		hIPhFFSAConnectionType
    MIN-ACCESS	read-write
    DESCRIPTION
        "(U//FOUO) Implementation of this object can be as low
         as read-write depending on which
         IS Objective or MIB desired requirements are
         not being met by the implementation."

    OBJECT		hFFASCIIID
    MIN-ACCESS	not-accessible
    DESCRIPTION
        "(U//FOUO) Implementation of this object can be as low
         as not-accessible depending on which
         IS Objective or MIB desired requirements are
         not being met by the implementation."

    OBJECT		hIfv6OutputPacketFixedSize
    MIN-ACCESS	not-accessible
    DESCRIPTION
        "(U//FOUO) Implementation of this object can be as low
         as not-accessible depending on which
         IS Objective or MIB desired requirements are
         not being met by the implementation."

    OBJECT		hiaaPrefixLen
    MIN-ACCESS	not-accessible
    DESCRIPTION
        "(U//FOUO) Implementation of this object can be as low
         as not-accessible depending on which
         IS Objective or MIB desired requirements are
         not being met by the implementation."

    OBJECT		hTPSAHCBrdcastPkts
    MIN-ACCESS	not-accessible
    DESCRIPTION
        "(U//FOUO) Implementation of this object can be as low
         as not-accessible depending on which
         IS Objective or MIB desired requirements are
         not being met by the implementation."

    OBJECT		hFFAlgorithmPrivilege
    MIN-ACCESS	not-accessible
    DESCRIPTION
        "(U//FOUO) Implementation of this object can be as low
         as not-accessible depending on which
         IS Objective or MIB desired requirements are
         not being met by the implementation."

    OBJECT		hTopologyDestHaipePTAddrType
    MIN-ACCESS	read-write
    DESCRIPTION
        "(U//FOUO) Implementation of this object can be as low
         as read-write depending on which
         IS Objective or MIB desired requirements are
         not being met by the implementation."

    OBJECT		hTPSAAddressSrcOrDest
    MIN-ACCESS	read-write
    DESCRIPTION
        "(U//FOUO) Implementation of this object can be as low
         as read-write depending on which
         IS Objective or MIB desired requirements are
         not being met by the implementation."

    OBJECT		hTPSARowStatus
    MIN-ACCESS	read-write
    DESCRIPTION
        "(U//FOUO) Implementation of this object can be as low
         as read-write depending on which
         IS Objective or MIB desired requirements are
         not being met by the implementation."

    OBJECT		hIPhFFSAFFUniversalEdition
    MIN-ACCESS	read-write
    DESCRIPTION
        "(U//FOUO) Implementation of this object can be as low
         as read-write depending on which
         IS Objective or MIB desired requirements are
         not being met by the implementation."

    OBJECT		hIPhFFSADSCP
    MIN-ACCESS	read-write
    DESCRIPTION
        "(U//FOUO) Implementation of this object can be as low
         as read-write depending on which
         IS Objective or MIB desired requirements are
         not being met by the implementation."

    OBJECT		hIPhFFSAECN
    MIN-ACCESS	read-write
    DESCRIPTION
        "(U//FOUO) Implementation of this object can be as low
         as read-write depending on which
         IS Objective or MIB desired requirements are
         not being met by the implementation."

--    OBJECT		hFFKeyExpirationWarning
--    MIN-ACCESS	accessible-for-notify
--    DESCRIPTION
--        "(U//FOUO) Implementation of this object can be as low
--         as accessible-for-notify depending on which
--         IS Objective or MIB desired requirements are
--         not being met by the implementation."

    OBJECT		hFFAuthority
    MIN-ACCESS	not-accessible
    DESCRIPTION
        "(U//FOUO) Implementation of this object can be as low
         as not-accessible depending on which
         IS Objective or MIB desired requirements are
         not being met by the implementation."

    OBJECT		hTPSASelectorNextHeaderStart
    MIN-ACCESS	not-accessible
    DESCRIPTION
        "(U//FOUO) Implementation of this object can be as low
         as not-accessible depending on which
         IS Objective or MIB desired requirements are
         not being met by the implementation."

--    OBJECT		hUniversalTable
--    MIN-ACCESS	read-only
--    DESCRIPTION
--        "(U//FOUO) Implementation of this object can be as low
--         as read-only depending on which
--         IS Objective or MIB desired requirements are
--         not being met by the implementation."

    OBJECT		hIPhFFSATransformESN
    MIN-ACCESS	not-accessible
    DESCRIPTION
        "(U//FOUO) Implementation of this object can be as low
         as not-accessible depending on which
         IS Objective or MIB desired requirements are
         not being met by the implementation."

    OBJECT		hIPhFFSAFlowLabelValue
    MIN-ACCESS	read-write
    DESCRIPTION
        "(U//FOUO) Implementation of this object can be as low
         as read-write depending on which
         IS Objective or MIB desired requirements are
         not being met by the implementation."

    OBJECT		hPPKUsageType
    MIN-ACCESS	read-write
    DESCRIPTION
        "(U//FOUO) Implementation of this object can be as low
         as read-write depending on which
         IS Objective or MIB desired requirements are
         not being met by the implementation."

    OBJECT		hIPhFFSADSCPValue
    MIN-ACCESS	read-write
    DESCRIPTION
        "(U//FOUO) Implementation of this object can be as low
         as read-write depending on which
         IS Objective or MIB desired requirements are
         not being met by the implementation."

    OBJECT		hTPSADecrementTTL
    MIN-ACCESS	read-only
    DESCRIPTION
        "(U//FOUO) Implementation of this object can be as low
         as read-only depending on which
         IS Objective or MIB desired requirements are
         not being met by the implementation."

    OBJECT		hIfv4OutputPacketFixedSize
    MIN-ACCESS	not-accessible
    DESCRIPTION
        "(U//FOUO) Implementation of this object can be as low
         as not-accessible depending on which
         IS Objective or MIB desired requirements are
         not being met by the implementation."

    OBJECT		hIPhFFSARetryICMPCount
    MIN-ACCESS	read-write
    DESCRIPTION
        "(U//FOUO) Implementation of this object can be as low
         as read-write depending on which
         IS Objective or MIB desired requirements are
         not being met by the implementation."

    OBJECT		hTPSAAddressRowStatus
    MIN-ACCESS	read-write
    DESCRIPTION
        "(U//FOUO) Implementation of this object can be as low
         as read-write depending on which
         IS Objective or MIB desired requirements are
         not being met by the implementation."

    OBJECT		hTPSARemoteCredentialType
    MIN-ACCESS	not-accessible
    DESCRIPTION
        "(U//FOUO) Implementation of this object can be as low
         as not-accessible depending on which
         IS Objective or MIB desired requirements are
         not being met by the implementation."

--    OBJECT		hIfAddrAssignmentTable
--    MIN-ACCESS	not-accessible
--    DESCRIPTION
--        "(U//FOUO) Implementation of this object can be as low
--         as not-accessible depending on which
--         IS Objective or MIB desired requirements are
--         not being met by the implementation."

    OBJECT		hIPhFFSACTOutAddressType
    MIN-ACCESS	read-write
    DESCRIPTION
        "(U//FOUO) Implementation of this object can be as low
         as read-write depending on which
         IS Objective or MIB desired requirements are
         not being met by the implementation."

    OBJECT		hIPhFFSATransformICV
    MIN-ACCESS	not-accessible
    DESCRIPTION
        "(U//FOUO) Implementation of this object can be as low
         as not-accessible depending on which
         IS Objective or MIB desired requirements are
         not being met by the implementation."

    OBJECT		hTPSAesn
    MIN-ACCESS	not-accessible
    DESCRIPTION
        "(U//FOUO) Implementation of this object can be as low
         as not-accessible depending on which
         IS Objective or MIB desired requirements are
         not being met by the implementation."

    OBJECT		hIPhFFSATransformsName
    MIN-ACCESS	read-write
    DESCRIPTION
        "(U//FOUO) Implementation of this object can be as low
         as read-write depending on which
         IS Objective or MIB desired requirements are
         not being met by the implementation."

    OBJECT		hTPSAHCMcastPkts
    MIN-ACCESS	not-accessible
    DESCRIPTION
        "(U//FOUO) Implementation of this object can be as low
         as not-accessible depending on which
         IS Objective or MIB desired requirements are
         not being met by the implementation."

    OBJECT		hTPSADSCP
    MIN-ACCESS	read-write
    DESCRIPTION
        "(U//FOUO) Implementation of this object can be as low
         as read-write depending on which
         IS Objective or MIB desired requirements are
         not being met by the implementation."

    OBJECT		hTPSAspi
    MIN-ACCESS	read-write
    DESCRIPTION
        "(U//FOUO) Implementation of this object can be as low
         as read-write depending on which
         IS Objective or MIB desired requirements are
         not being met by the implementation."

    OBJECT		hPPKTrafficIntegrityAlgorithm
    MIN-ACCESS	read-only
    DESCRIPTION
        "(U//FOUO) Implementation of this object can be as low
         as read-only depending on which
         IS Objective or MIB desired requirements are
         not being met by the implementation."

    OBJECT		hFFUniversalEdition
    MIN-ACCESS	read-only
    DESCRIPTION
        "(U//FOUO) Implementation of this object can be as low
         as read-only depending on which
         IS Objective or MIB desired requirements are
         not being met by the implementation."

    OBJECT		hIPhRuleTableLastChanged
    MIN-ACCESS	read-only
    DESCRIPTION
        "(U//FOUO) Implementation of this object can be as low
         as read-only depending on which
         IS Objective or MIB desired requirements are
         not being met by the implementation."

    OBJECT		hIPhFFSALastChanged
    MIN-ACCESS	read-only
    DESCRIPTION
        "(U//FOUO) Implementation of this object can be as low
         as read-only depending on which
         IS Objective or MIB desired requirements are
         not being met by the implementation."

    OBJECT		hTPSASelectorNextHeaderOpt2Start
    MIN-ACCESS	not-accessible
    DESCRIPTION
        "(U//FOUO) Implementation of this object can be as low
         as not-accessible depending on which
         IS Objective or MIB desired requirements are
         not being met by the implementation."

    OBJECT		hPPKChainEffectiveDate
    MIN-ACCESS	read-write
    DESCRIPTION
        "(U//FOUO) Implementation of this object can be as low
         as read-write depending on which
         IS Objective or MIB desired requirements are
         not being met by the implementation."

    OBJECT		hTPSALocalPTAddress
    MIN-ACCESS	read-write
    DESCRIPTION
        "(U//FOUO) Implementation of this object can be as low
         as read-write depending on which
         IS Objective or MIB desired requirements are
         not being met by the implementation."

--    OBJECT		hTPiphFFSATransforms
--    MIN-ACCESS	read-write
--    DESCRIPTION
--        "(U//FOUO) Implementation of this object can be as low
--         as read-write depending on which
--         IS Objective or MIB desired requirements are
--         not being met by the implementation."

    OBJECT		hIPhRuleAdminStatus
    MIN-ACCESS	read-write
    DESCRIPTION
        "(U//FOUO) Implementation of this object can be as low
         as read-write depending on which
         IS Objective or MIB desired requirements are
         not being met by the implementation."

    OBJECT		hTPSAECN
    MIN-ACCESS	read-write
    DESCRIPTION
        "(U//FOUO) Implementation of this object can be as low
         as read-write depending on which
         IS Objective or MIB desired requirements are
         not being met by the implementation."

    OBJECT		hPPKChainIntegrityAlgorithm
    MIN-ACCESS	not-accessible
    DESCRIPTION
        "(U//FOUO) Implementation of this object can be as low
         as not-accessible depending on which
         IS Objective or MIB desired requirements are
         not being met by the implementation."

--    OBJECT		hTPSAAddressSelectorTable
--    MIN-ACCESS	read-only
--    DESCRIPTION
--        "(U//FOUO) Implementation of this object can be as low
--         as read-only depending on which
--         IS Objective or MIB desired requirements are
--         not being met by the implementation."

    OBJECT		hIPhFFSADecrementTTL
    MIN-ACCESS	read-only
    DESCRIPTION
        "(U//FOUO) Implementation of this object can be as low
         as read-only depending on which
         IS Objective or MIB desired requirements are
         not being met by the implementation."

    OBJECT		hTPSADFBit
    MIN-ACCESS	read-write
    DESCRIPTION
        "(U//FOUO) Implementation of this object can be as low
         as read-write depending on which
         IS Objective or MIB desired requirements are
         not being met by the implementation."

    OBJECT		hTPSARetryICMPCount
    MIN-ACCESS	read-write
    DESCRIPTION
        "(U//FOUO) Implementation of this object can be as low
         as read-write depending on which
         IS Objective or MIB desired requirements are
         not being met by the implementation."

    OBJECT		hTopologyDestHostAddrType
    MIN-ACCESS	read-write
    DESCRIPTION
        "(U//FOUO) Implementation of this object can be as low
         as read-write depending on which
         IS Objective or MIB desired requirements are
         not being met by the implementation."

    OBJECT		hTopologyLifetime
    MIN-ACCESS	read-write
    DESCRIPTION
        "(U//FOUO) Implementation of this object can be as low
         as read-write depending on which
         IS Objective or MIB desired requirements are
         not being met by the implementation."

    OBJECT		hIPhFFSAPHRDRate
    MIN-ACCESS	read-write
    DESCRIPTION
        "(U//FOUO) Implementation of this object can be as low
         as read-write depending on which
         IS Objective or MIB desired requirements are
         not being met by the implementation."

    OBJECT		hIPhFFSARowStatus
    MIN-ACCESS	read-write
    DESCRIPTION
        "(U//FOUO) Implementation of this object can be as low
         as read-write depending on which
         IS Objective or MIB desired requirements are
         not being met by the implementation."

    OBJECT		hPreplacedKeyTableCapacity
    MIN-ACCESS	read-only
    DESCRIPTION
        "(U//FOUO) Implementation of this object can be as low
         as read-only depending on which
         IS Objective or MIB desired requirements are
         not being met by the implementation."

    OBJECT		hFFUniversalID
    MIN-ACCESS	read-only
    DESCRIPTION
        "(U//FOUO) Implementation of this object can be as low
         as read-only depending on which
         IS Objective or MIB desired requirements are
         not being met by the implementation."

    OBJECT		hIPhFFSATransformRowStatus
    MIN-ACCESS	read-write
    DESCRIPTION
        "(U//FOUO) Implementation of this object can be as low
         as read-write depending on which
         IS Objective or MIB desired requirements are
         not being met by the implementation."

    OBJECT		hTPSARemoteCTAddress
    MIN-ACCESS	read-write
    DESCRIPTION
        "(U//FOUO) Implementation of this object can be as low
         as read-write depending on which
         IS Objective or MIB desired requirements are
         not being met by the implementation."

    OBJECT		hFFSecurityLevels
    MIN-ACCESS	read-only
    DESCRIPTION
        "(U//FOUO) Implementation of this object can be as low
         as read-only depending on which
         IS Objective or MIB desired requirements are
         not being met by the implementation."

    OBJECT		hTPSALocalCredentialType
    MIN-ACCESS	not-accessible
    DESCRIPTION
        "(U//FOUO) Implementation of this object can be as low
         as not-accessible depending on which
         IS Objective or MIB desired requirements are
         not being met by the implementation."

    OBJECT		hTPSAFlowLabelValue
    MIN-ACCESS	read-write
    DESCRIPTION
        "(U//FOUO) Implementation of this object can be as low
         as read-write depending on which
         IS Objective or MIB desired requirements are
         not being met by the implementation."

    OBJECT		hTPSAEncryptAlgorithm
    MIN-ACCESS	read-only
    DESCRIPTION
        "(U//FOUO) Implementation of this object can be as low
         as read-only depending on which
         IS Objective or MIB desired requirements are
         not being met by the implementation."

    OBJECT		hIPhSelectorRowStatus
    MIN-ACCESS	read-write
    DESCRIPTION
        "(U//FOUO) Implementation of this object can be as low
         as read-write depending on which
         IS Objective or MIB desired requirements are
         not being met by the implementation."

    OBJECT		hiaaAddress
    MIN-ACCESS	not-accessible
    DESCRIPTION
        "(U//FOUO) Implementation of this object can be as low
         as not-accessible depending on which
         IS Objective or MIB desired requirements are
         not being met by the implementation."

    OBJECT		hIPhFFSAPDUNEnabled
    MIN-ACCESS	read-write
    DESCRIPTION
        "(U//FOUO) Implementation of this object can be as low
         as read-write depending on which
         IS Objective or MIB desired requirements are
         not being met by the implementation."

    OBJECT		hTPSALocalCTAddress
    MIN-ACCESS	read-write
    DESCRIPTION
        "(U//FOUO) Implementation of this object can be as low
         as read-write depending on which
         IS Objective or MIB desired requirements are
         not being met by the implementation."

    OBJECT		hIPhFFSATransformIntegrityAlgorithm
    MIN-ACCESS	read-write
    DESCRIPTION
        "(U//FOUO) Implementation of this object can be as low
         as read-write depending on which
         IS Objective or MIB desired requirements are
         not being met by the implementation."

    OBJECT		hTPSAPDUNEnabled
    MIN-ACCESS	read-write
    DESCRIPTION
        "(U//FOUO) Implementation of this object can be as low
         as read-write depending on which
         IS Objective or MIB desired requirements are
         not being met by the implementation."

    OBJECT		hIPhFFSADIndexType
    MIN-ACCESS	read-write
    DESCRIPTION
        "(U//FOUO) Implementation of this object can be as low
         as read-write depending on which
         IS Objective or MIB desired requirements are
         not being met by the implementation."

    OBJECT		hFFEnhancedFFTag
    MIN-ACCESS	read-only
    DESCRIPTION
        "(U//FOUO) Implementation of this object can be as low
         as read-only depending on which
         IS Objective or MIB desired requirements are
         not being met by the implementation."

    OBJECT		hTPSASelectorNextHeaderEnd
    MIN-ACCESS	not-accessible
    DESCRIPTION
        "(U//FOUO) Implementation of this object can be as low
         as not-accessible depending on which
         IS Objective or MIB desired requirements are
         not being met by the implementation."

    OBJECT		hPPKTrafficTableMaxCount
    MIN-ACCESS	read-only
    DESCRIPTION
        "(U//FOUO) Implementation of this object can be as low
         as read-only depending on which
         IS Objective or MIB desired requirements are
         not being met by the implementation."

    OBJECT		hTPSATableCount
    MIN-ACCESS	read-only
    DESCRIPTION
        "(U//FOUO) Implementation of this object can be as low
         as read-only depending on which
         IS Objective or MIB desired requirements are
         not being met by the implementation."

    OBJECT		hIPhFFSATableLastChanged
    MIN-ACCESS	read-only
    DESCRIPTION
        "(U//FOUO) Implementation of this object can be as low
         as read-only depending on which
         IS Objective or MIB desired requirements are
         not being met by the implementation."

    OBJECT		hPreplacedKeyTableCount
    MIN-ACCESS	read-only
    DESCRIPTION
        "(U//FOUO) Implementation of this object can be as low
         as read-only depending on which
         IS Objective or MIB desired requirements are
         not being met by the implementation."

    OBJECT		hIPhSelectorDstAddressEnd
    MIN-ACCESS	read-write
    DESCRIPTION
        "(U//FOUO) Implementation of this object can be as low
         as read-write depending on which
         IS Objective or MIB desired requirements are
         not being met by the implementation."

    OBJECT		hPPKEKUniversalID
    MIN-ACCESS	read-write
    DESCRIPTION
        "(U//FOUO) Implementation of this object can be as low
         as read-write depending on which
         IS Objective or MIB desired requirements are
         not being met by the implementation."

    OBJECT		hIPhRuleAction
    MIN-ACCESS	read-write
    DESCRIPTION
        "(U//FOUO) Implementation of this object can be as low
         as read-write depending on which
         IS Objective or MIB desired requirements are
         not being met by the implementation."

    OBJECT		hTPSALocalCredentialID
    MIN-ACCESS	read-only
    DESCRIPTION
        "(U//FOUO) Implementation of this object can be as low
         as read-only depending on which
         IS Objective or MIB desired requirements are
         not being met by the implementation."

    OBJECT		hIPhRuleRowStatus
    MIN-ACCESS	read-write
    DESCRIPTION
        "(U//FOUO) Implementation of this object can be as low
         as read-write depending on which
         IS Objective or MIB desired requirements are
         not being met by the implementation."

    OBJECT		hTPSAStartTime
    MIN-ACCESS	read-write
    DESCRIPTION
        "(U//FOUO) Implementation of this object can be as low
         as read-write depending on which
         IS Objective or MIB desired requirements are
         not being met by the implementation."

    OBJECT		hFFLastChanged
    MIN-ACCESS	read-only
    DESCRIPTION
        "(U//FOUO) Implementation of this object can be as low
         as read-only depending on which
         IS Objective or MIB desired requirements are
         not being met by the implementation."

    OBJECT		hIPhSelectorDstAddressBegin
    MIN-ACCESS	read-write
    DESCRIPTION
        "(U//FOUO) Implementation of this object can be as low
         as read-write depending on which
         IS Objective or MIB desired requirements are
         not being met by the implementation."

    OBJECT		hFFIsTestKey
    MIN-ACCESS	read-only
    DESCRIPTION
        "(U//FOUO) Implementation of this object can be as low
         as read-only depending on which
         IS Objective or MIB desired requirements are
         not being met by the implementation."

    OBJECT		hTPSADIndexType
    MIN-ACCESS	read-write
    DESCRIPTION
        "(U//FOUO) Implementation of this object can be as low
         as read-write depending on which
         IS Objective or MIB desired requirements are
         not being met by the implementation."

    OBJECT		hTPSASelectorNextHeaderOpt1End
    MIN-ACCESS	not-accessible
    DESCRIPTION
        "(U//FOUO) Implementation of this object can be as low
         as not-accessible depending on which
         IS Objective or MIB desired requirements are
         not being met by the implementation."

    OBJECT		hTPSATableLastChanged
    MIN-ACCESS	read-only
    DESCRIPTION
        "(U//FOUO) Implementation of this object can be as low
         as read-only depending on which
         IS Objective or MIB desired requirements are
         not being met by the implementation."

    OBJECT		hIfv6OutputPacketPadding
    MIN-ACCESS	not-accessible
    DESCRIPTION
        "(U//FOUO) Implementation of this object can be as low
         as not-accessible depending on which
         IS Objective or MIB desired requirements are
         not being met by the implementation."

    OBJECT		hIPhFFSAFF
    MIN-ACCESS	read-write
    DESCRIPTION
        "(U//FOUO) Implementation of this object can be as low
         as read-write depending on which
         IS Objective or MIB desired requirements are
         not being met by the implementation."

    OBJECT		hPPKTrafficEncryptAlgorithm
    MIN-ACCESS	read-only
    DESCRIPTION
        "(U//FOUO) Implementation of this object can be as low
         as read-only depending on which
         IS Objective or MIB desired requirements are
         not being met by the implementation."

    OBJECT		hTopologyDestAdminCost
    MIN-ACCESS	read-write
    DESCRIPTION
        "(U//FOUO) Implementation of this object can be as low
         as read-write depending on which
         IS Objective or MIB desired requirements are
         not being met by the implementation."

    OBJECT		hTPSARemoteCredentialID
    MIN-ACCESS	not-accessible
    DESCRIPTION
        "(U//FOUO) Implementation of this object can be as low
         as not-accessible depending on which
         IS Objective or MIB desired requirements are
         not being met by the implementation."

    OBJECT		hIPhFFSAFlowLabel
    MIN-ACCESS	read-write
    DESCRIPTION
        "(U//FOUO) Implementation of this object can be as low
         as read-write depending on which
         IS Objective or MIB desired requirements are
         not being met by the implementation."

--    OBJECT		hPPKKeyExpirationWarning
--    MIN-ACCESS	accessible-for-notify
--    DESCRIPTION
--        "(U//FOUO) Implementation of this object can be as low
--         as accessible-for-notify depending on which
--         IS Objective or MIB desired requirements are
--         not being met by the implementation."

    OBJECT		hTPSAPPK
    MIN-ACCESS	read-write
    DESCRIPTION
        "(U//FOUO) Implementation of this object can be as low
         as read-write depending on which
         IS Objective or MIB desired requirements are
         not being met by the implementation."

    OBJECT		hIfv6HopLimit
    MIN-ACCESS	read-only
    DESCRIPTION
        "(U//FOUO) Implementation of this object can be as low
         as read-only depending on which
         IS Objective or MIB desired requirements are
         not being met by the implementation."

    OBJECT		hIPhFFSACTOutAddress
    MIN-ACCESS	read-write
    DESCRIPTION
        "(U//FOUO) Implementation of this object can be as low
         as read-write depending on which
         IS Objective or MIB desired requirements are
         not being met by the implementation."

    OBJECT		hIPhRuleSelectorName
    MIN-ACCESS	read-write
    DESCRIPTION
        "(U//FOUO) Implementation of this object can be as low
         as read-write depending on which
         IS Objective or MIB desired requirements are
         not being met by the implementation."

    OBJECT		hTopologyDestHaipeCTAddr
    MIN-ACCESS	read-write
    DESCRIPTION
        "(U//FOUO) Implementation of this object can be as low
         as read-write depending on which
         IS Objective or MIB desired requirements are
         not being met by the implementation."

    OBJECT		hIPhFFSAPopulateFromPacket
    MIN-ACCESS	not-accessible
    DESCRIPTION
        "(U//FOUO) Implementation of this object can be as low
         as not-accessible depending on which
         IS Objective or MIB desired requirements are
         not being met by the implementation."

    OBJECT		hTPSASecurityPayloadType
    MIN-ACCESS	read-only
    DESCRIPTION
        "(U//FOUO) Implementation of this object can be as low
         as read-only depending on which
         IS Objective or MIB desired requirements are
         not being met by the implementation."

    OBJECT		hIPhRuleTableCount
    MIN-ACCESS	read-only
    DESCRIPTION
        "(U//FOUO) Implementation of this object can be as low
         as read-only depending on which
         IS Objective or MIB desired requirements are
         not being met by the implementation."

    OBJECT		hIPhRuleName
    MIN-ACCESS	read-write
    DESCRIPTION
        "(U//FOUO) Implementation of this object can be as low
         as read-write depending on which
         IS Objective or MIB desired requirements are
         not being met by the implementation."

    OBJECT		hFireflyTableCount
    MIN-ACCESS	read-only
    DESCRIPTION
        "(U//FOUO) Implementation of this object can be as low
         as read-only depending on which
         IS Objective or MIB desired requirements are
         not being met by the implementation."

    OBJECT		hTPSAAddressEnd
    MIN-ACCESS	read-write
    DESCRIPTION
        "(U//FOUO) Implementation of this object can be as low
         as read-write depending on which
         IS Objective or MIB desired requirements are
         not being met by the implementation."

    OBJECT		hTPSAAddressType
    MIN-ACCESS	read-write
    DESCRIPTION
        "(U//FOUO) Implementation of this object can be as low
         as read-write depending on which
         IS Objective or MIB desired requirements are
         not being met by the implementation."

    OBJECT		hUniversalID
    MIN-ACCESS	read-only
    DESCRIPTION
        "(U//FOUO) Implementation of this object can be as low
         as read-only depending on which
         IS Objective or MIB desired requirements are
         not being met by the implementation."

--    OBJECT		hPPKEKTable
--    MIN-ACCESS	read-only
--    DESCRIPTION
--        "(U//FOUO) Implementation of this object can be as low
--         as read-only depending on which
--         IS Objective or MIB desired requirements are
--         not being met by the implementation."

    OBJECT		hTopologyDestHostPTPfxLen
    MIN-ACCESS	read-write
    DESCRIPTION
        "(U//FOUO) Implementation of this object can be as low
         as read-write depending on which
         IS Objective or MIB desired requirements are
         not being met by the implementation."

    OBJECT		hIPhSelectorLastChanged
    MIN-ACCESS	read-only
    DESCRIPTION
        "(U//FOUO) Implementation of this object can be as low
         as read-only depending on which
         IS Objective or MIB desired requirements are
         not being met by the implementation."

    OBJECT		hTPSAPHRDRate
    MIN-ACCESS	read-write
    DESCRIPTION
        "(U//FOUO) Implementation of this object can be as low
         as read-write depending on which
         IS Objective or MIB desired requirements are
         not being met by the implementation."

    OBJECT		hiaaInterface
    MIN-ACCESS	not-accessible
    DESCRIPTION
        "(U//FOUO) Implementation of this object can be as low
         as not-accessible depending on which
         IS Objective or MIB desired requirements are
         not being met by the implementation."

    OBJECT		hTPSAAddressStart
    MIN-ACCESS	read-write
    DESCRIPTION
        "(U//FOUO) Implementation of this object can be as low
         as read-write depending on which
         IS Objective or MIB desired requirements are
         not being met by the implementation."

    OBJECT		hTPSAICV
    MIN-ACCESS	not-accessible
    DESCRIPTION
        "(U//FOUO) Implementation of this object can be as low
         as not-accessible depending on which
         IS Objective or MIB desired requirements are
         not being met by the implementation."

    OBJECT		hPPKChainTableLastChanged
    MIN-ACCESS	read-only
    DESCRIPTION
        "(U//FOUO) Implementation of this object can be as low
         as read-only depending on which
         IS Objective or MIB desired requirements are
         not being met by the implementation."

    OBJECT		hIPhSelectorType
    MIN-ACCESS	read-write
    DESCRIPTION
        "(U//FOUO) Implementation of this object can be as low
         as read-write depending on which
         IS Objective or MIB desired requirements are
         not being met by the implementation."

    OBJECT		hTopologyDestHaipeCTAddrType
    MIN-ACCESS	read-write
    DESCRIPTION
        "(U//FOUO) Implementation of this object can be as low
         as read-write depending on which
         IS Objective or MIB desired requirements are
         not being met by the implementation."

    OBJECT		hiaaRowStatus
    MIN-ACCESS	not-accessible
    DESCRIPTION
        "(U//FOUO) Implementation of this object can be as low
         as not-accessible depending on which
         IS Objective or MIB desired requirements are
         not being met by the implementation."

--    OBJECT		hTPiphSATransforms
--    MIN-ACCESS	read-write
--    DESCRIPTION
--        "(U//FOUO) Implementation of this object can be as low
--         as read-write depending on which
--         IS Objective or MIB desired requirements are
--         not being met by the implementation."

    OBJECT		hPPKChainTableCount
    MIN-ACCESS	read-only
    DESCRIPTION
        "(U//FOUO) Implementation of this object can be as low
         as read-only depending on which
         IS Objective or MIB desired requirements are
         not being met by the implementation."

    OBJECT		hTopologyRowStatus
    MIN-ACCESS	read-write
    DESCRIPTION
        "(U//FOUO) Implementation of this object can be as low
         as read-write depending on which
         IS Objective or MIB desired requirements are
         not being met by the implementation."

    OBJECT		hPPKChainEncryptionAlgorithm
    MIN-ACCESS	read-write
    DESCRIPTION
        "(U//FOUO) Implementation of this object can be as low
         as read-write depending on which
         IS Objective or MIB desired requirements are
         not being met by the implementation."

    OBJECT		hIPhSelectorTableCount
    MIN-ACCESS	read-only
    DESCRIPTION
        "(U//FOUO) Implementation of this object can be as low
         as read-only depending on which
         IS Objective or MIB desired requirements are
         not being met by the implementation."
::= { haipeV030002Conformance 9 }

END
