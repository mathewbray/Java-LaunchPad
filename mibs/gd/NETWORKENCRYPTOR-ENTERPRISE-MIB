--BEGIN Revision History
--
--20151019 - M. Coughlin - Add neDiscEnableGDCRouteRefresh, and neDiscGDCRouteRefreshInterval
--
--20140821 - R. Berman - Add neSAConfigScalars
--
--20140804 - R. Berman - Add neSAFailoverEnabled
--
--20140731 - R. Berman - Add neSaMultipleSas
--
--20140723 - R. Berman - Add neRip
--
--20140702 - R. Berman - Add neDiscRouteOfLastResort
--
--20140609 - R. Berman - Add neIpGlobalIGMPLeaveBypassEnabled, neIpGlobalMldDoneBypassEnabled
--
--20140516 - R. Berman - Add nePreferredDiscovery
--
--20140513 - R. Berman - Add neNetworkBridging
--
--20120509 - R. Berman - Add neIFTableSfpModule
--
--20120509 - G. Smith - Add ARP Cache Clear
--
--20140508 - R. Berman - Add neLep
--
--20120508 - E. Clark - Added neSAPairTransmitCount, neSAPairReceiveCount, and neSAPairClearCounts
--to NeSAPairEntry
--
--20120119 - M. Coughlin - Add neManSaPairTable
--
--20120119 - R. Berman - Add IKEv2 tables
--
--20110824 - M. DeVeau - Add IPMEIR flags
--
--20110228 - M. DeVeau DRN MIB 194 - Add Discovery flags
--
--20101014 - T. Huemiller DRN MIB00193 - Removed nePrePlacedKeyTAShortTitle
--from nePreplacedKeyExtensionTable.
--
--20100902 - R. Berman DRN MIB00191 Added nePrePlacedKeyTAShortTitle to nePreplacedKeyExtensionTable.
--Added neAPPKTAExtensionTable and neTAInformation.
--Added conformance groups neAPPKTAExtensionsGroup and neAPPKTAGroup.
--
--MIB00178 - 20090928 - Add IF-MIB extension table to NE-MIB
--
--
--20090928 - DRN MIB00177 - Add neResetSsoPin
--
--
--20090413 T. Huemiller - DRN MIB00167 Added neTPSAAutoCalcSpiAndTime.  Changed deval
--to FALSE for neTPSAAutoConfigLocalAddrs flag
--
--20090409 T. Huemiller - DRN MIB00162 Added neTPSAAutoConfigLocalAddrs object.
--
--20081216 DRN MIB00141 - Removed nePACConfig Group, Added nePACModuliInformation Group
--including neUnInstalledPACModuliTable and neDePACModuliAugmentationTable.
--
--20081008 DRN MIB00139 - Changed description of nePACIndex object to remove reference
--to maximum number of PAC moduli that can be loaded in nePACTable.
--
--20081003 DRN MIB00133 -  Added nePPKChainAssignment object to
--nePreplacedKeyExtensionTable and to conformance group nePPKExtensionsGroup
--
--20080711 DRN MIB00127 - Added neIpGlobalIGMPVersion and neIpGlobalMLDVersion to
--provide the manager the capability to configure the IGMP and MLD versions globally
--for the ECU.
--
--20080711  DRN MIB00115 - Added neConsoleAddressType and neConsoleAddress and
--neConsoleConfigGroup to provide capability for manager to configure console port
--IP address.
--
--200608XY  Updates from 05/19/2006 & 05/22/2006 GigE/Mini R3.4 Enterprise MIBs
--Review (ongoing):
--
--20060811
--a. Added neTPSAExtensionTable, to hold 'Auto PPK SA
--Propagation Enabled' and "PPK SA Established' objects, per GigE/Mini R3.4
--'HMI HLD Rework' AI 7697-5.  For 'post baseline' GigE/Mini R3.4 MIB updates.
--This table 'augments' (extends) the hTPSATable of the
--HAIPE-TRAFFIC-PROTECTION-MIB module of the HAIPE V3 MIBs.
--b. Moved nePPKUpdateCount from the nePPKSlotAssignTable to the new
--nePreplacedKeyExtensionTable in this MIB module that 'augments' (extends)
--the hPreplacedKeyTable of the HAIPE-TRAFFIC-PROTECTION-MIB module of the HAIPE V3
--MIBs.
--
--20060803
--a. Per GigE/Mini R3.4 'HMI HLD Rework' AI 7697-2, added multiple '(sub)groups'
--and 12 MIB objects to the neSASummaryStatistics 'group', replacing the
--following preliminary objects added previous to the 05/19/2006 & 05/22/2006
--GigE/Mini R3.4 Enterprise MIBs Review:
--neTotalDuplexSACount, neTotalDuplexFireflySACount, neTotalDuplexPPKSACount
--b. removed the nenrdOffNetArpND object, 'replaced' it with the
--nenrdDefaultPeerEnclaveEntryLifetime object, per the 05/22/2006 GigE/Mini R3.4
--R3.4 Enterprise MIBs Review.  (The latter is also related to GigE/Mini R3.4
--'HMI HLD Review Part 3' AI 7673-4.)
--
--20060524  Updates for TL-Micro DRNs:
--a. corrected IMPORTS statement for SnmpAdminString, InetAddressType and InetAddress
--b. added ineFixedPacketMode and KeyFillStatus Textual-Conventions
--IneFixedPacketMode used in neFixedPktMode object.  KeyFillStatus used in
--neFireFlyFillStatus and nePPKFillStatus
--c. Changed range of neTOSConstant from 0x00 - 0xFF to 0x00 - 0xFF to have
--have TOSConstant include both DSCP and ECN bits of TOS field.
--
--20060513  Minor updates for GigE/Mini R3.4, for comments from TL-Micro
--Systems & Software preliminary review.
--Also corrected misordering of { neConformance x } OBJECT-GROUP items.
--
--20060508
--a. Added MIB items for total duplex (bi-directional) SA statistics,
--for GigE/Mini R3.4: neSASummaryStatistics group, and neTotalDuplexSACount,
--neTotalDuplexFireflySACount, neTotalDuplexPPKSACount objects.
--b. Updated DESCRIPTION of neDeleteteStaticRoutes object.
--
--20060502  Corrected various syntax errors from MIB items
--originally added for GigE/Mini R3.4, corrected IMPORTS clause
--statements
--
--20060426  Added items for GigE/Mini R3.4
--
--END Revision History

NETWORKENCRYPTOR-ENTERPRISE-MIB DEFINITIONS ::= BEGIN
    IMPORTS
    MODULE-IDENTITY, OBJECT-TYPE, Integer32,
    Unsigned32, Counter32, OBJECT-IDENTITY,
    Counter64
        FROM SNMPv2-SMI
        --J. Holzhauer Note: Counter32, Counter64 added for GigE/Mini R3.4
    applications
        FROM GDC4S-ENCRYPTION-PRODUCTS-MIB
    OBJECT-GROUP
        FROM SNMPv2-CONF
    hTPSAEntry, KMID, HaipeEncryptionAlgorithm,
    HaipeIntegrityAlgorithm, hPreplacedKeyEntry,
    hAPPKTrustAnchorEntry, hFireflyEntry, FFUniversalID,
    hDePACModuliEntry, hIPhRuleEntry, hIPhSelectorEntry
        FROM HAIPE-TRAFFIC-PROTECTION-MIB
    hTopologyEntry
        FROM HAIPE-NETWORKING-DISCOVERY-MIB
    IPAddress, IPAddressType
        FROM HAIPE-V4-TEXTUAL-CONVENTIONS-MIB
    SnmpAdminString
        FROM SNMP-FRAMEWORK-MIB
    InetAddressType, InetAddress
        FROM INET-ADDRESS-MIB
    TruthValue, RowStatus, DateAndTime, RowPointer,
    TimeStamp, TEXTUAL-CONVENTION
        FROM SNMPv2-TC
    ShortTitle64
        FROM HAIPE-TC-MIB
    ifMauEntry
        FROM MAU-MIB
    ifEntry
        FROM IF-MIB;

    networkEncryptor MODULE-IDENTITY
        LAST-UPDATED        "200605130000Z"
        ORGANIZATION        "General Dynamics C4 Systems"
        CONTACT-INFO        "Infosec Support        
                            General Dynamics C4
                            Systems Corporation
                            77 A Street
                            Needham Heights, MA
                            02494-2806
                            Telephone: 877-230-0236
                            email: INFOSECSUPPORT@GDC4S.COM"
        DESCRIPTION         "This MIB supports Network Encryption products
                            developed by General Dynamics C4 Systems."

        REVISION            "200605130000Z"
        DESCRIPTION         "Minor updates for GigE/Mini R3.4, for comments
                            from TL-Micro Systems & Software preliminary
                            review"
        REVISION            "200605082200Z"
        DESCRIPTION         "Added MIB items for total duplex (bi-directional)
                            SA statistics, for GigE/Mini R3.4"
        REVISION            "200605021730Z"
        DESCRIPTION         "Corrected syntax errors from updates for GigE/Mini
                            R3.4"
        REVISION            "200604222230Z"
        DESCRIPTION         "Updates for GigE/Mini R3.4"
        REVISION            "200602031114Z"
        DESCRIPTION         "initial version of this module"
        ::= { applications 1 }

    --T. Huemiller Note: Added IneFixedPacketMode and KeyFillStatus Textual-Conventions.
    --Had been incorrectly listed as Import from GDC4S-HAIPE-TRAFFIC-PROTECTION-MIB
    --IneFixedPacketMoce used in neFixedPktMode object.  KeyFillStatus used in
    --neFireFlyFillStatus and nePPKFillStatus
    --
    IneFixedPacketMode ::= TEXTUAL-CONVENTION
        STATUS              current
        DESCRIPTION         "(U//FOUO) Provides the three modes for the Fixed
                            Packet Mode, OFF, ON/DISCARD and ON/FRAGMENT."
        SYNTAX              INTEGER {
                                off( 1 ),
                                onDiscard( 2 ),
                                onFragment( 3 )
                            }

    KeyFillStatus ::= TEXTUAL-CONVENTION
        STATUS              current
        DESCRIPTION         "(U//FOUO) The status values that are read to determine
                            the progress and results of a key fill operation."
        SYNTAX              INTEGER {
                                noFillCommand( 1 ),
                                inProcess( 2 ),
                                timedOut( 3 ),
                                failed( 4 ),
                                aborted( 5 ),
                                successful( 6 )
                            }

    --
    --MIB00178 - 20090928 - Add IF-MIB extension table to NE-MIB
    --
    NeIFSpeedMode ::= TEXTUAL-CONVENTION
        STATUS              current
        DESCRIPTION         "(U//FOUO) Speed and mode combinations available."
        SYNTAX              BITS {
                                type10Mps-HD( 0 ),
                                type10Mbps-FD( 1 ),
                                type100Mbps-HD( 2 ),
                                type100Mbps-FD( 3 ),
                                type1000Mbps-HD( 4 ),
                                type1000Mbps-FD( 5 ),
                                type10Gbps-FD( 6 )
                            }



    neManageObjs OBJECT IDENTIFIER ::= { networkEncryptor 1 }

    --J. Holzhauer Note: BEGIN MIB items added for GigE/Mini R3.4
    neNetworkObjects OBJECT IDENTIFIER ::= { neManageObjs 1 }

    neNetworkReachabilityDiscovery OBJECT IDENTIFIER ::= { neNetworkObjects 1 }

    --J. Holzhauer Note: the following object added to correspond to a GigE/Mini
    --R3.4 HMI configurable 'Lifetime' timer, per GigE/Mini R3.4 AI 7673-4
    nenrdDefaultPeerEnclaveEntryLifetime OBJECT-TYPE
        SYNTAX              Unsigned32
        MAX-ACCESS          read-write
        STATUS              current
        DESCRIPTION         "(U//FOUO) This object indicates the value of the
                            configurable Default Peer Enclave Entry Lifetime
                            (DPEEL) timer. This value is used in various
                            circumstances for the default value of the 'lifetime
                            parameter' when populating an entry in a routing/topology
                            table related to a peer enclave prefix. For example,
                            when populating an entry in a routing/topology
                            table related to a peer enclave prefix by manual
                            assignment, rather than by the use of discovery
                            services. (U//FOUO) The units, allowable values,
                            and default value for this object are platform
                            and implementation dependent. For example, in
                            the initial HAIPE V3.X implementations, this
                            object is in units of seconds, and is configurable
                            with values from 60 seconds (one minute) to 86400
                            seconds (24 hours), with a default value is 43200
                            seconds (12 hours). (U//FOUO) Note that, if this
                            parameter may be configured by a 'local' operator
                            via the ECU's HMI, the name of the parameter
                            on the HMI display corresponding to this MIB
                            object is also platform and implementation dependent,
                            and may not match the descriptor (textual 'name')
                            of this object. Note that the value of this object
                            may affect Network Discovery (ND)."
        ::= { neNetworkReachabilityDiscovery 1 }

    neNetworkReachDiscExtensions OBJECT IDENTIFIER ::= { neNetworkReachabilityDiscovery 2 }

    neNetworkReachDiscExtensionsScalars
        OBJECT IDENTIFIER ::= { neNetworkReachDiscExtensions 1 }

    neNetworkReachDiscExtensionsTables
        OBJECT IDENTIFIER ::= { neNetworkReachDiscExtensions 2 }

    neTopologyExtensionTable OBJECT-TYPE
        SYNTAX              SEQUENCE OF NeTopologyExtensionEntry
        MAX-ACCESS          not-accessible
        STATUS              current
        DESCRIPTION         "(U//FOUO) A table containing information about
                            the list of known prefix/HAIPE relationships.
                            This table contains additional objects for the
                            hTopologyTable of the HAIPE-NETWORKING-DISCOVERY-MIB
                            of the HAIPE V3 MIBs. (U//FOUO) It extends, or
                            augments, the hTopologyTable by adding GDC4S-specific
                            columnar objects for configuration, status, and
                            other purposes."
        ::= { neNetworkReachDiscExtensionsTables 1 }

    neTopologyExtensionEntry OBJECT-TYPE
        SYNTAX              NeTopologyExtensionEntry
        MAX-ACCESS          not-accessible
        STATUS              current
        DESCRIPTION         "(U//FOUO) An entry (row) containing additional
                            information applicable to known prefix/HAIPE
                            relationships."
        AUGMENTS            {
                                hTopologyEntry
                            }
        ::= { neTopologyExtensionTable 1 }

    NeTopologyExtensionEntry ::= SEQUENCE {
        neTopologyEntryReachable
            TruthValue
    }

    neTopologyEntryReachable OBJECT-TYPE
        SYNTAX              TruthValue
        MAX-ACCESS          read-only
        STATUS              current
        DESCRIPTION         "(U//FOUO) This object indicates whether an entry
                            in the hTopologyTable is reachable. A value of
                            TRUE indicates the topology entry is reachable.
                            A value of FALSE indicates the topology entry
                            is unreachable."
        ::= { neTopologyExtensionEntry 1 }

    neNetworkDiscovery OBJECT IDENTIFIER ::= { neNetworkObjects 2 }

    neLegacyDiscovery OBJECT IDENTIFIER ::= { neNetworkDiscovery 1 }

    neDiscEnableSDD OBJECT-TYPE
        SYNTAX              TruthValue
        MAX-ACCESS          read-write
        STATUS              current
        DESCRIPTION         "(U//FOUO) The object when set to true, enables
                            SDD processing, and when false, disables SDD
                            processing."
        ::= { neLegacyDiscovery 1 }

    neGenericDiscovery OBJECT IDENTIFIER ::= { neNetworkDiscovery 2 }

    neDiscEnableGDC OBJECT-TYPE
        SYNTAX              TruthValue
        MAX-ACCESS          read-write
        STATUS              current
        DESCRIPTION         "(U//FOUO) The object when set to true, enables
                            SDD processing, and when false, disables SDD
                            processing."
        ::= { neGenericDiscovery 1 }

    neDiscEnableGDCRouteRefresh OBJECT-TYPE
        SYNTAX              TruthValue
        MAX-ACCESS          read-write
        STATUS              current
        DESCRIPTION         "(U//FOUO) The object when set to true, enables
                            GDC route refresh allowing the device to periodically
                            re-register all local enclave routes with GDC 
                            registration servers at intervals specified by
                            neDiscGDCRouteRefreshInterval."
        ::= { neGenericDiscovery 2 }

    neDiscGDCRouteRefreshInterval OBJECT-TYPE
        SYNTAX              Unsigned32
        MAX-ACCESS          read-write
        STATUS              current
        DESCRIPTION         "(U//FOUO) The time in minutes specifying how often
                            the device will re-register local enclave routes with
                            GDC registration servers."
        ::= { neGenericDiscovery 3 }

    neIMPEPD OBJECT IDENTIFIER ::= { neNetworkDiscovery 3 }

    neDiscEnableIMPEPD OBJECT-TYPE
        SYNTAX              TruthValue
        MAX-ACCESS          read-write
        STATUS              current
        DESCRIPTION         "(U//FOUO) The object when set to true, enables
                            SDD processing, and when false, disables SDD
                            processing."
        ::= { neIMPEPD 1 }

    nePreferredDiscovery OBJECT IDENTIFIER ::= { neNetworkDiscovery 4 }

    neEnablePrefDisc OBJECT-TYPE
        SYNTAX              TruthValue
        MAX-ACCESS          read-write
        STATUS              current
        DESCRIPTION         "(U//FOUO) This object is set to TRUE to enable
                            preferred discovery. When set to FALSE, preferred
                            discovery is disabled."
        ::= { nePreferredDiscovery 1 }

    nePrefDiscTableCount OBJECT-TYPE
        SYNTAX              Unsigned32
        MAX-ACCESS          read-only
        STATUS              current
        DESCRIPTION         "(U//FOUO) The number of rows in the nePrefDiscTable."
        ::= { nePreferredDiscovery 2 }

    nePrefDiscTable OBJECT-TYPE
        SYNTAX              SEQUENCE OF NePrefDiscTableEntry
        MAX-ACCESS          not-accessible
        STATUS              current
        DESCRIPTION         "(U//FOUO) The table containing a prioritized list
                            of address ranges which are associated with a
                            discovery protocol."
        ::= { nePreferredDiscovery 3 }

    nePrefDiscTableEntry OBJECT-TYPE
        SYNTAX              NePrefDiscTableEntry
        MAX-ACCESS          not-accessible
        STATUS              current
        DESCRIPTION         "(U//FOUO) An entry defines a prioritized address
                            range associated with a discovery protocol."
        INDEX               {
                                nePrefDiscPriority
                            }
        ::= { nePrefDiscTable 1 }

    NePrefDiscTableEntry ::= SEQUENCE {
        nePrefDiscPriority
            Unsigned32,
        nePrefDiscAddressType
            IPAddressType,
        nePrefDiscStartAddress
            IPAddress,
        nePrefDiscEndAddress
            IPAddress,
        nePrefDiscProtocol
            INTEGER,
        nePrefDiscRowStatus
            RowStatus
    }

    nePrefDiscPriority OBJECT-TYPE
        SYNTAX              Unsigned32
        MAX-ACCESS          not-accessible
        STATUS              current
        DESCRIPTION         "(U//FOUO) The priority for the preferred discovery
                            address range."
        ::= { nePrefDiscTableEntry 1 }

    nePrefDiscAddressType OBJECT-TYPE
        SYNTAX              IPAddressType
        MAX-ACCESS          read-create
        STATUS              current
        DESCRIPTION         "(U//FOUO) The Internet Protocol Version, IPv4
                            or IPv6, of the preferred discovery address range."
        ::= { nePrefDiscTableEntry 2 }

    nePrefDiscStartAddress OBJECT-TYPE
        SYNTAX              IPAddress
        MAX-ACCESS          read-create
        STATUS              current
        DESCRIPTION         "(U//FOUO) The start of the preferred discovery
                            address range."
        ::= { nePrefDiscTableEntry 3 }

    nePrefDiscEndAddress OBJECT-TYPE
        SYNTAX              IPAddress
        MAX-ACCESS          read-create
        STATUS              current
        DESCRIPTION         "(U//FOUO) The end of the preferred discovery address
                            range."
        ::= { nePrefDiscTableEntry 4 }

    nePrefDiscProtocol OBJECT-TYPE
        SYNTAX              INTEGER {
                                sdd( 1 ),
                                gdc( 2 ),
                                impepd( 3 )
                            }
        MAX-ACCESS          read-create
        STATUS              current
        DESCRIPTION         "(U//FOUO) The preferred discovery protocol for
                            the address range."
        ::= { nePrefDiscTableEntry 5 }

    nePrefDiscRowStatus OBJECT-TYPE
        SYNTAX              RowStatus
        MAX-ACCESS          read-create
        STATUS              current
        DESCRIPTION         "(U//FOUO) The row status for entries in this table."
        ::= { nePrefDiscTableEntry 6 }

    neDiscRouteOfLastResort OBJECT IDENTIFIER ::= { neNetworkDiscovery 5 }

    neDiscEnableRouteOfLastResort OBJECT-TYPE
        SYNTAX              TruthValue
        MAX-ACCESS          read-write
        STATUS              current
        DESCRIPTION         "(U//FOUO) This object is set to TRUE to enable
                            routing via the Route of Last Resort. When set
                            to FALSE, routing via the Route of Last Resort
                            is disabled."
        ::= { neDiscRouteOfLastResort 1 }

    neDiscRouteOfLastResortTableCount OBJECT-TYPE
        SYNTAX              Unsigned32
        MAX-ACCESS          read-only
        STATUS              current
        DESCRIPTION         "(U//FOUO) The number of rows in the neDiscRouteOfLastResortTable."
        ::= { neDiscRouteOfLastResort 2 }

    neDiscRouteOfLastResortTable OBJECT-TYPE
        SYNTAX              SEQUENCE OF NeDiscRouteOfLastResortTableEntry
        MAX-ACCESS          not-accessible
        STATUS              current
        DESCRIPTION         "(U//FOUO) The table containing the configuration
                            information for routing via the Route of Last
                            Resort."
        ::= { neDiscRouteOfLastResort 3 }

    neDiscRouteOfLastResortTableEntry OBJECT-TYPE
        SYNTAX              NeDiscRouteOfLastResortTableEntry
        MAX-ACCESS          not-accessible
        STATUS              current
        DESCRIPTION         "(U//FOUO) An entry (row) containing the Route
                            of Last Resort configuration information for
                            each Internet Protocol Version."
        INDEX               {
                                neDiscRtOfLstRsrtAddressType
                            }
        ::= { neDiscRouteOfLastResortTable 1 }

    NeDiscRouteOfLastResortTableEntry ::= SEQUENCE {
        neDiscRtOfLstRsrtAddressType
            IPAddressType,
        neDiscRtOfLstRsrtPTAddress
            IPAddress,
        neDiscRtOfLstRsrtCTAddress
            IPAddress,
        neDiscRtOfLstRsrtAdminCost
            Unsigned32,
        neDiscRtOfLstRsrtLifetime
            Unsigned32
    }

    neDiscRtOfLstRsrtAddressType OBJECT-TYPE
        SYNTAX              IPAddressType
        MAX-ACCESS          not-accessible
        STATUS              current
        DESCRIPTION         "(U//FOUO) The Internet Protocol Version, IPv4
                            or IPv6, of the ECU addresses for routing via
                            the Route of Last Resort."
        ::= { neDiscRouteOfLastResortTableEntry 1 }

    neDiscRtOfLstRsrtPTAddress OBJECT-TYPE
        SYNTAX              IPAddress
        MAX-ACCESS          read-write
        STATUS              current
        DESCRIPTION         "(U//FOUO) The ECU PT address to route to when
                            routing via the Route of Last Resort."
        ::= { neDiscRouteOfLastResortTableEntry 2 }

    neDiscRtOfLstRsrtCTAddress OBJECT-TYPE
        SYNTAX              IPAddress
        MAX-ACCESS          read-write
        STATUS              current
        DESCRIPTION         "(U//FOUO) The ECU CT address to route to when
                            routing via the Route of Last Resort."
        ::= { neDiscRouteOfLastResortTableEntry 3 }

    neDiscRtOfLstRsrtAdminCost OBJECT-TYPE
        SYNTAX              Unsigned32 (0..255)
        MAX-ACCESS          read-write
        STATUS              current
        DESCRIPTION         "(U//FOUO) The administrative cost of routing via
                            the Route of Last Resort."
        ::= { neDiscRouteOfLastResortTableEntry 4 }

    neDiscRtOfLstRsrtLifetime OBJECT-TYPE
        SYNTAX              Unsigned32
        MAX-ACCESS          read-write
        STATUS              current
        DESCRIPTION         "(U//FOUO) The lifetime, in seconds, for routing
                            via the Route of Last Resort."
        ::= { neDiscRouteOfLastResortTableEntry 5 }

    neRip OBJECT IDENTIFIER ::= { neNetworkDiscovery 6 }

    neRipMappings OBJECT IDENTIFIER ::= { neRip 1 }

    neRipMetricToACMappings OBJECT IDENTIFIER ::= { neRipMappings 1 }

    neRipMetricToACMapTableCount OBJECT-TYPE
        SYNTAX              Unsigned32
        MAX-ACCESS          read-only
        STATUS              current
        DESCRIPTION         "(U//FOUO) The number of rows in the neRipMetricToACMapTable."
        ::= { neRipMetricToACMappings 1 }

    neRipMetricToACMapTable OBJECT-TYPE
        SYNTAX              SEQUENCE OF NeRipMetricToACMapTableEntry
        MAX-ACCESS          not-accessible
        STATUS              current
        DESCRIPTION         "(U//FOUO) The table containing the set of RIP
                            metric to GDC administrative cost mappings."
        ::= { neRipMetricToACMappings 2 }

    neRipMetricToACMapTableEntry OBJECT-TYPE
        SYNTAX              NeRipMetricToACMapTableEntry
        MAX-ACCESS          not-accessible
        STATUS              current
        DESCRIPTION         "(U//FOUO) An entry defines a one-to-one mapping
                            of a RIP metric to a GDC administrative cost."
        INDEX               {
                                neRipMetricToACMapMetric
                            }
        ::= { neRipMetricToACMapTable 1 }

    NeRipMetricToACMapTableEntry ::= SEQUENCE {
        neRipMetricToACMapMetric
            Unsigned32,
        neRipMetricToACMapAdminCost
            Unsigned32,
        neRipMetricToACMapRowStatus
            RowStatus
    }

    neRipMetricToACMapMetric OBJECT-TYPE
        SYNTAX              Unsigned32 (1..15)
        MAX-ACCESS          not-accessible
        STATUS              current
        DESCRIPTION         "(U//FOUO) The RIP metric to map to the GDC administrative
                            cost."
        ::= { neRipMetricToACMapTableEntry 1 }

    neRipMetricToACMapAdminCost OBJECT-TYPE
        SYNTAX              Unsigned32 (0..255)
        MAX-ACCESS          read-create
        STATUS              current
        DESCRIPTION         "(U//FOUO) The GDC administrative cost that the
                            RIP metric is mapped to."
        ::= { neRipMetricToACMapTableEntry 2 }

    neRipMetricToACMapRowStatus OBJECT-TYPE
        SYNTAX              RowStatus
        MAX-ACCESS          read-create
        STATUS              current
        DESCRIPTION         "(U//FOUO) The row status for entries in this table."
        ::= { neRipMetricToACMapTableEntry 3 }

    neRipACToMetricMappings OBJECT IDENTIFIER ::= { neRipMappings 2 }

    neRipACToMetricMapTableCount OBJECT-TYPE
        SYNTAX              Unsigned32
        MAX-ACCESS          read-only
        STATUS              current
        DESCRIPTION         "(U//FOUO) The number of rows in the neRipACToMetricMapTable."
        ::= { neRipACToMetricMappings 1 }

    neRipACToMetricMapTable OBJECT-TYPE
        SYNTAX              SEQUENCE OF NeRipACToMetricMapTableEntry
        MAX-ACCESS          not-accessible
        STATUS              current
        DESCRIPTION         "(U//FOUO) The table containing the set of GDC
                            administrative cost ranges to RIP metric mappings.
                            The maximal range that must be covered is from
                            0-255. This range can be covered either by one
                            entry specifying the whole range or by numerous
                            entries specifying smaller ranges that add up
                            to the whole range. Each maximum administrative
                            cost should be unique. The first administrative
                            cost range is formed by using zero as the minimum
                            and the lowest maximum administrative cost in
                            the table. Each following range is formed by
                            using the last lowest maximum+1, as the minimum,
                            and the next lowest maximum found in the table.
                            An entry with a maximum value of 255 must always
                            appear in the table to guarantee full coverage."
        ::= { neRipACToMetricMappings 2 }

    neRipACToMetricMapTableEntry OBJECT-TYPE
        SYNTAX              NeRipACToMetricMapTableEntry
        MAX-ACCESS          not-accessible
        STATUS              current
        DESCRIPTION         "(U//FOUO) An entry defines a many-to-one mapping
                            of a GDC administrative cost range to a RIP metric."
        INDEX               {
                                neRipACToMetricMapIndex
                            }
        ::= { neRipACToMetricMapTable 1 }

    NeRipACToMetricMapTableEntry ::= SEQUENCE {
        neRipACToMetricMapIndex
            Unsigned32,
        neRipACToMetricMapMaxAdminCost
            Unsigned32,
        neRipACToMetricMapMetric
            Unsigned32,
        neRipACToMetricMapRowStatus
            RowStatus
    }

    neRipACToMetricMapIndex OBJECT-TYPE
        SYNTAX              Unsigned32
        MAX-ACCESS          not-accessible
        STATUS              current
        DESCRIPTION         "(U//FOUO) A unique numeric identifier for this
                            entry."
        ::= { neRipACToMetricMapTableEntry 1 }

    neRipACToMetricMapMaxAdminCost OBJECT-TYPE
        SYNTAX              Unsigned32 (0..255)
        MAX-ACCESS          read-create
        STATUS              current
        DESCRIPTION         "(U//FOUO) The maximum GDC administrative cost
                            to map the RIP metric to."
        ::= { neRipACToMetricMapTableEntry 2 }

    neRipACToMetricMapMetric OBJECT-TYPE
        SYNTAX              Unsigned32 (1..15)
        MAX-ACCESS          read-create
        STATUS              current
        DESCRIPTION         "(U//FOUO) The RIP metric that the GDC administrative
                            cost range is mapped to."
        ::= { neRipACToMetricMapTableEntry 3 }

    neRipACToMetricMapRowStatus OBJECT-TYPE
        SYNTAX              RowStatus
        MAX-ACCESS          read-create
        STATUS              current
        DESCRIPTION         "(U//FOUO) The row status for entries in this table."
        ::= { neRipACToMetricMapTableEntry 4 }

    neNetworkRouting OBJECT IDENTIFIER ::= { neNetworkObjects 3 }

    neLep OBJECT IDENTIFIER ::= { neNetworkRouting 1 }

    neLepConfigScalars OBJECT IDENTIFIER ::= { neLep 1 }

    neActiveLepSearchEnabled OBJECT-TYPE
        SYNTAX              TruthValue
        MAX-ACCESS          read-write
        STATUS              current
        DESCRIPTION         "(U//FOUO) This object indicates whether active
                            LEP search is enabled or disabled."
        ::= { neLepConfigScalars 1 }

    neNetworkBridging OBJECT IDENTIFIER ::= { neNetworkObjects 4 }

    neProxyAddressResolution OBJECT IDENTIFIER ::= { neNetworkBridging 1 }

    neProxyAddrResTableCount OBJECT-TYPE
        SYNTAX              Unsigned32
        MAX-ACCESS          read-only
        STATUS              current
        DESCRIPTION         "(U//FOUO) The number of rows in the neProxyAddrResTable."
        ::= { neProxyAddressResolution 1 }

    neProxyAddrResTableDeleteAll OBJECT-TYPE
        SYNTAX              TruthValue
        MAX-ACCESS          read-write
        STATUS              current
        DESCRIPTION         "(U//FOUO) This object is set to TRUE to delete
                            all of the entries in the neProxyAddrResTable.
                            When set to FALSE, the set is accepted and no
                            action occurs. When read, it always returns FALSE."
        ::= { neProxyAddressResolution 2 }

    neProxyAddrResTable OBJECT-TYPE
        SYNTAX              SEQUENCE OF NeProxyAddrResTableEntry
        MAX-ACCESS          not-accessible
        STATUS              current
        DESCRIPTION         "(U//FOUO) The table containing a set of IP addresses
                            and prefixes that is search whenever an ARP/NDP
                            request is received on the PT interface to determine
                            if the device should issue an ARP/NDP."
        ::= { neProxyAddressResolution 3 }

    neProxyAddrResTableEntry OBJECT-TYPE
        SYNTAX              NeProxyAddrResTableEntry
        MAX-ACCESS          not-accessible
        STATUS              current
        DESCRIPTION         "(U//FOUO) An entry defines an address range and
                            action for which the device will process the
                            ARP/NDP request received on the PT interface
                            with an IP address which falls within the range."
        INDEX               {
                                neProxyAddrResAddressType,
                                neProxyAddrResAddress,
                                neProxyAddrResPrefix
                            }
        ::= { neProxyAddrResTable 1 }

    NeProxyAddrResTableEntry ::= SEQUENCE {
        neProxyAddrResAddressType
            IPAddressType,
        neProxyAddrResAddress
            IPAddress,
        neProxyAddrResPrefix
            Unsigned32,
        neProxyAddrResAction
            INTEGER,
        neProxyAddrResRowStatus
            RowStatus
    }

    neProxyAddrResAddressType OBJECT-TYPE
        SYNTAX              IPAddressType
        MAX-ACCESS          not-accessible
        STATUS              current
        DESCRIPTION         "(U//FOUO) The Internet Protocol Version, IPv4
                            or IPv6, of the proxy address."
        ::= { neProxyAddrResTableEntry 1 }

    neProxyAddrResAddress OBJECT-TYPE
        SYNTAX              IPAddress
        MAX-ACCESS          not-accessible
        STATUS              current
        DESCRIPTION         "(U//FOUO) The Internet Protocol proxy address."
        ::= { neProxyAddrResTableEntry 2 }

    neProxyAddrResPrefix OBJECT-TYPE
        SYNTAX              Unsigned32 (0..128)
        MAX-ACCESS          not-accessible
        STATUS              current
        DESCRIPTION         "(U//FOUO) The prefix length for the proxy address."
        ::= { neProxyAddrResTableEntry 3 }

    neProxyAddrResAction OBJECT-TYPE
        SYNTAX              INTEGER {
                                include( 1 ),
                                exclude( 2 )
                            }
        MAX-ACCESS          read-create
        STATUS              current
        DESCRIPTION         "(U//FOUO) The proxy action."
        ::= { neProxyAddrResTableEntry 4 }

    neProxyAddrResRowStatus OBJECT-TYPE
        SYNTAX              RowStatus
        MAX-ACCESS          read-create
        STATUS              current
        DESCRIPTION         "(U//FOUO) The row status for entries in this table."
        ::= { neProxyAddrResTableEntry 5 }

    --J. Holzhauer Note: END MIB items added for GigE/Mini R3.4
    neIP OBJECT IDENTIFIER ::= { neManageObjs 2 }

    neIpGlobalConfigs OBJECT IDENTIFIER ::= { neIP 1 }

    neIpGlobalMTU OBJECT-TYPE
        SYNTAX              Integer32
        MAX-ACCESS          read-write
        STATUS              current
        DESCRIPTION         "(U//FOUO) The MTU for the device. The maximum
                            value, and the default value is 1500."
        ::= { neIpGlobalConfigs 1 }

    neGlobalTFSConfig OBJECT IDENTIFIER ::= { neIpGlobalConfigs 2 }

    neIpGlobalBypass OBJECT IDENTIFIER ::= { neGlobalTFSConfig 1 }

    neIpGlobalDFBypassEnable OBJECT-TYPE
        SYNTAX              TruthValue
        MAX-ACCESS          read-write
        STATUS              current
        DESCRIPTION         "(U//FOUO) This object indicates whether the Don't
                            Fragment Field (DF), a single bit IPv4 header
                            flag will be bypassed (TRUE), or replaced with
                            the operator-settable value in the neIpGlobalDFBitValue
                            object (FALSE). (U//FOUO) The default value of
                            this object is to NOT bypass the DF bit but rather
                            set it to the value in neIpGlobalDFBitValue (FASLE)."
        ::= { neIpGlobalBypass 1 }

    neIpGlobalDFBitValue OBJECT-TYPE
        SYNTAX              Integer32
        MAX-ACCESS          read-write
        STATUS              current
        DESCRIPTION         "(U//FOUO) The value held by this object replaces
                            the IPv4 Header Don't Fragment flag when the
                            object neIpGlobalDFBypassEnable is FALSE. (U//FOUO)
                            This object is set by the operator and has a
                            value of either 1 or 0. The value 1 in the header
                            field indicates the packet is not be fragmented.
                            The value 0 in the header field indicates the
                            packet may be fragmented if it exceeds the PMTU
                            of the route."
        ::= { neIpGlobalBypass 2 }

    neIpGlobalIgmpBypass OBJECT-TYPE
        SYNTAX              TruthValue
        MAX-ACCESS          read-write
        STATUS              current
        DESCRIPTION         "(U//FOUO) When enabled, set to TRUE, all IGMP
                            PDUs will be passed through the system without
                            encryption or decryption (will not be tunneled).
                            (U//FOUO) The default value is FALSE (off)."
        ::= { neIpGlobalBypass 3 }

    neIpGlobalTOSConfig OBJECT IDENTIFIER ::= { neIpGlobalBypass 4 }

    neGlobalTOSBypassEnable OBJECT-TYPE
        SYNTAX              TruthValue
        MAX-ACCESS          read-write
        STATUS              current
        DESCRIPTION         "(U//FOUO) This object, when set to TRUE, enables
                            the passing of the Type-of-Service (TOS) IPv4
                            Header Field in the PT-to-CT direction. The TOS
                            field is passed when the DSCP sub-field matches
                            operator specified accepted DSCP values (neDSCPAcceptedValues).
                            The ECN sub-field value is always passed when
                            this object is TRUE. (U//FOUO) When this object
                            is TRUE, but the DSCP sub-field is not an accepted
                            value, the TOS field is set to the value stored
                            in neTOSConstant. (U//FOUO) When this object
                            is set to FALSE, the value of the TOS/Traffic
                            Class Header Field is set to the operator-configurable
                            constant as defined in neTOSConstant. (U//FOUO)
                            The default value of this object is FALSE (OFF)."
        ::= { neIpGlobalTOSConfig 1 }

    --T. Huemiller Note: Changed range of neTOSConstant from 0x00 - 0xFF to 0x00 - 0xFF
    --to
    --have TOSConstant include both DSCP and ECN bits of TOS field.
    neTOSConstant OBJECT-TYPE
        SYNTAX              OCTET STRING (SIZE(1))
        MAX-ACCESS          read-write
        STATUS              current
        DESCRIPTION         "(U//FOUO) This object defines the constant value
                            to which the TOS Header Field will be mapped
                            if the neGlobalTOSBypassEnable object is FALSE.
                            It contains a constant value to which the TOS
                            header field will be mapped if neGlobalTOSBypassEnable
                            is TRUE but the DSCP sub-field does not match
                            one of the operator-specified DSCP-sub-field
                            values (neDSCPAcceptedValues). (U//FOUO) It is
                            an octet string that is one octet in length in
                            the range 0x00 - 0xFF inclusive. (U//FOUO) The
                            default value of this object is zero (0)."
        ::= { neIpGlobalTOSConfig 2 }

    neDSCPAcceptedValues OBJECT-TYPE
        SYNTAX              BITS {
                                cs0( 0 ),
                                dscp1( 1 ),
                                dscp2( 2 ),
                                dscp3( 3 ),
                                dscp4( 4 ),
                                dscp5( 5 ),
                                dscp6( 6 ),
                                dscp7( 7 ),
                                cs1( 8 ),
                                dscp9( 9 ),
                                af11( 10 ),
                                dscp11( 11 ),
                                af12( 12 ),
                                dscp13( 13 ),
                                af13( 14 ),
                                dscp15( 15 ),
                                cs2( 16 ),
                                dscp17( 17 ),
                                af21( 18 ),
                                dscp19( 19 ),
                                af22( 20 ),
                                dscp21( 21 ),
                                af23( 22 ),
                                dscp23( 23 ),
                                cs3( 24 ),
                                dscp25( 25 ),
                                af31( 26 ),
                                dscp27( 27 ),
                                af32( 28 ),
                                dscp29( 29 ),
                                af33( 30 ),
                                dscp31( 31 ),
                                cs4( 32 ),
                                dscp33( 33 ),
                                af41( 34 ),
                                dscp35( 35 ),
                                af42( 36 ),
                                dscp37( 37 ),
                                af43( 38 ),
                                dscp39( 39 ),
                                cs5( 40 ),
                                dscp41( 41 ),
                                dscp42( 42 ),
                                dscp43( 43 ),
                                dscp44( 44 ),
                                dscp45( 45 ),
                                efphb( 46 ),
                                dscp47( 47 ),
                                cs6( 48 ),
                                dscp49( 49 ),
                                dscp50( 50 ),
                                dscp51( 51 ),
                                dscp52( 52 ),
                                dscp53( 53 ),
                                dscp54( 54 ),
                                dscp55( 55 ),
                                cs7( 56 ),
                                dscp57( 57 ),
                                dscp58( 58 ),
                                dscp59( 59 ),
                                dscp60( 60 ),
                                dscp61( 61 ),
                                dscp62( 62 ),
                                dscp63( 63 )
                            }
        MAX-ACCESS          read-write
        STATUS              current
        DESCRIPTION         "(U//FOUO) A bit string to define the set of accepted
                            DSCP values. The default is that all DSCP values
                            are accepted. (U//FOUO) This value is 8 octets
                            in length and provides a list of acceptable DSCP
                            values represented as a 64-bit vector. Each bit
                            of this value represents one acceptable DSCP
                            value and matches when the bit is set, i.e. '1'.
                            If the incoming packet's DSCP value matches a
                            value represented in the vector, that value is
                            placed in the outgoing packet. (U//FOUO) If none
                            of the values in the vector match an incoming
                            packet's DSCP value, the outgoing packet's DSCP
                            value is set to neTOSConstant. (U//FOUO) 64 bit
                            vector representation: Bit set matches DSCP value
                            0 000000 1 000001 2 000010 . . . . . . 62 111110
                            63 111111 (U//FOUO) The DSCP bits are the high/left
                            most bits of Type Of Service (TOS) header. (U//FOUO)
                            Note: This column is only pertinent for traffic
                            being encrypted (i.e. PT->CT traffic)."
        ::= { neIpGlobalTOSConfig 3 }

    neFixedLength OBJECT IDENTIFIER ::= { neGlobalTFSConfig 2 }

    neFixedPktMode OBJECT-TYPE
        SYNTAX              IneFixedPacketMode
        MAX-ACCESS          read-write
        STATUS              current
        DESCRIPTION         "(U//FOUO) This object sets the Fixed Packet Length
                            Mode. Default is ON/FRAGMENT."
        ::= { neFixedLength 1 }

    neGlobalFixedLength OBJECT-TYPE
        SYNTAX              Integer32
        MAX-ACCESS          read-write
        STATUS              current
        DESCRIPTION         "(U//FOUO) This object defines the size of the
                            Fixed Packet Length, the length of the IP PT
                            datagram. This length is realized by fragmentation
                            or padding. It is configurable to the following
                            values: 176; 224; 272; 320; 368; 416; 464; 512;
                            560; 608; 656; 704; 752; 800 (default); 848;
                            896; 944; 992; 1040; 1088; 1136; 1184; 1232;
                            1280; 1328; 1376; 1424."
        ::= { neFixedLength 2 }

    neGlobalPseqnCheckEnable OBJECT-TYPE
        SYNTAX              TruthValue
        MAX-ACCESS          read-write
        STATUS              current
        DESCRIPTION         "(U//FOUO) When set to TRUE, enables PSEQN Checking.
                            The default value of this object is to enable
                            the PSEQN checking feature (TRUE)."
        ::= { neGlobalTFSConfig 3 }

    nePMTUDiscoveryEnable OBJECT-TYPE
        SYNTAX              TruthValue
        MAX-ACCESS          read-write
        STATUS              current
        DESCRIPTION         "(U//FOUO) When set to TRUE, enables the PMTU Discovery
                            feature. (U//FOUO) The default value of this
                            object is to NOT enable the PMTU feature (FALSE)."
        ::= { neGlobalTFSConfig 4 }

    --DEFVAL              { 0 }
    neIpv4ControlMessageMTU OBJECT-TYPE
        SYNTAX              Integer32 (0 | 576..2147483647)
        MAX-ACCESS          read-write
        STATUS              current
        DESCRIPTION         "(U//FOUO) The MTU in octets for IPv4 control messages
                            on this device. When this object is set to the
                            default of 0, control messages will use the configured
                            MTU for IPv4. If this object is set to a value
                            larger than the configured MTU for IPv4, then
                            control messages will use the configured MTU
                            for IPv4."
        ::= { neIpGlobalConfigs 3 }

    --DEFVAL              { 1280 }
    neIpv6ControlMessageMTU OBJECT-TYPE
        SYNTAX              Integer32 (0 | 1280..2147483647)
        MAX-ACCESS          read-write
        STATUS              current
        DESCRIPTION         "(U//FOUO) The MTU in octets for IPv6 control messages
                            on this device. When this object is set to 0,
                            control messages will use the configured MTU
                            for IPv6. If this object is set to a value larger
                            than the configured MTU for IPv6, then control
                            messages will use the configured MTU for IPv6
                            will be used. The default value for this object
                            is 1280"
        ::= { neIpGlobalConfigs 4 }

    --T. Huemiller: added neIplobalIGMPVersion and neIpGlobalMLDVersion objects
    neIpGlobalIGMPVersion OBJECT-TYPE
        SYNTAX              Integer32 (1..3)
        MAX-ACCESS          read-write
        STATUS              current
        DESCRIPTION         "(U//FOUO) This is a global setting for the ECU,
                            such that all interfaces supporting IGMP are
                            constrained by this setting. (U//FOUO) This object
                            defines the maximum version of IPv4 IGMP the
                            ECU can run. A value of 1 indicates that the
                            ECU only supports IGMPv1. A value of 2 indicates
                            that the ECU also supports IGMPv2. A value of
                            3 indicates that the ECU also supports IGMPv3."
        ::= { neIpGlobalConfigs 5 }

    neIpGlobalMLDVersion OBJECT-TYPE
        SYNTAX              Integer32 (1..2)
        MAX-ACCESS          read-write
        STATUS              current
        DESCRIPTION         "(U//FOUO) This is a global setting for the ECU,
                            such that all interfaces supporting MLD are constrained
                            by this setting. (U//FOUO) This object defines
                            the maximum version of IPv6 MLD the ECU can run..
                            A value of 1 indicates that the ECU only supports
                            MLDv1. A value of 2 indicates that the ECU also
                            supports MLDv2."
        ::= { neIpGlobalConfigs 6 }

    neIpGlobalIGMPLeaveBypassEnabled OBJECT-TYPE
        SYNTAX              TruthValue
        MAX-ACCESS          read-write
        STATUS              current
        DESCRIPTION         "(U//FOUO) This is a global setting for the ECU,
                            such that all interfaces supporting IGMP are
                            constrained by this setting.
                            
                            (U//FOUO) This object enables the ECU to bypass
                            and regenerate the IGMP Leave Group message."
        ::= { neIpGlobalConfigs 7 }

    neIpGlobalMldDoneBypassEnabled OBJECT-TYPE
        SYNTAX              TruthValue
        MAX-ACCESS          read-write
        STATUS              current
        DESCRIPTION         "(U//FOUO) This is a global setting for the ECU,
                            such that all interfaces supporting MLD are constrained
                            by this setting.
                            
                            (U//FOUO) This object enables the ECU to bypass
                            and regenerate the MLD Done message."
        ::= { neIpGlobalConfigs 8 }

    neKeyObjects OBJECT IDENTIFIER ::= { neManageObjs 3 }

    neFireflyKeys OBJECT IDENTIFIER ::= { neKeyObjects 1 }

    neFireflyFillConfig OBJECT IDENTIFIER ::= { neFireflyKeys 1 }

    neFireFlyFillCmd OBJECT-TYPE
        SYNTAX              TruthValue
        MAX-ACCESS          read-write
        STATUS              current
        DESCRIPTION         "(U//FOUO) This object, when set to TRUE, initiates
                            the filling of a Firefly Vector Set via the fill
                            port. (U//FOUO) The default value of this object
                            is to not command Firefly filling(FALSE). (U//FOUO)
                            When this object is set to FALSE during a fill
                            operation and before the DTD begins transferring
                            data, the in-process load operation is aborted
                            and the object commonFireflyFillStatus is set
                            to ABORTED. (U//FOUO) Upon completion of the
                            fill operation, either successfully or unsuccessfully,
                            this object is automatically returned to the
                            FALSE value. (U//FOUO) This object always returns
                            FALSE when read."
        ::= { neFireflyFillConfig 1 }

    neFireFlyFillStatus OBJECT-TYPE
        SYNTAX              KeyFillStatus
        MAX-ACCESS          read-only
        STATUS              current
        DESCRIPTION         "(U//FOUO) This object indicates the state of the
                            key fill process. (U//FOUO) The value of this
                            object is set to noFillCommand (1) at startup/restart.
                            It remains at that value until a key fill operation
                            is initiated, at which point the value changes
                            to inProcess (2). At the conclusion of the key
                            fill operation, this object is set to the appropriate
                            value, timedOut, failed, aborted, or successful.
                            It retains that value until a new key fill operation
                            is initiated, at which point the object value
                            returns to inProcess, or until the device is
                            reset and the value returns to noFillCommand."
        ::= { neFireflyFillConfig 2 }

    neACLConfig OBJECT IDENTIFIER ::= { neFireflyKeys 2 }

    neAccessControlEnable OBJECT-TYPE
        SYNTAX              TruthValue
        MAX-ACCESS          read-write
        STATUS              current
        DESCRIPTION         "(U//FOUO) This object, when set to TRUE, enables
                            the Encryptor to only establish Security Associations
                            with remote network encryptors having a FireFly
                            Vector Set that is included in the commonACLKmidTable.
                            (U//FOUO) The default value of this object is
                            to DISABLE Access Control (FALSE)."
        ::= { neACLConfig 1 }

    neACLTableCount OBJECT-TYPE
        SYNTAX              Integer32
        MAX-ACCESS          read-only
        STATUS              current
        DESCRIPTION         "(U//FOUO) The number of rows in the commonACLTable"
        ::= { neACLConfig 2 }

    neACLTable OBJECT-TYPE
        SYNTAX              SEQUENCE OF NeACLEntry
        MAX-ACCESS          not-accessible
        STATUS              current
        DESCRIPTION         "(U//FOUO) A list of FFVS KMIDs that may be used
                            by remote network encryptors to establish a Security
                            Association with this network encryptor when
                            the commonAccessModeEnable object is ENABLE.
                            One ACL applies to all security levels."
        ::= { neACLConfig 3 }

    neACLEntry OBJECT-TYPE
        SYNTAX              NeACLEntry
        MAX-ACCESS          not-accessible
        STATUS              current
        DESCRIPTION         "(U//FOUO) A row identifying a FFVS KMID that may
                            be used by a remote network encryptor to establish
                            a Security Association with this Encryptor when
                            the commonAccessModeEnable object is ENABLE."
        INDEX               {
                                neACLKMID
                            }
        ::= { neACLTable 1 }

    NeACLEntry ::= SEQUENCE {
        neACLKMID
            KMID,
        neACLKMIDRowStatus
            RowStatus
    }

    neACLKMID OBJECT-TYPE
        SYNTAX              KMID
        MAX-ACCESS          read-create
        STATUS              current
        DESCRIPTION         "(U//FOUO) The Key Management Identifier for a
                            FFVS that can be used by a remote network encryptor
                            to establish a Security Association when the
                            commonAccessModeEnable object is set to ENABLE."
        ::= { neACLEntry 1 }

    neACLKMIDRowStatus OBJECT-TYPE
        SYNTAX              RowStatus
        MAX-ACCESS          read-create
        STATUS              current
        DESCRIPTION         "(U//FOUO) The status of this row, by which new
                            entries may be created, or obsolete entries deleted
                            from this table. (U//FOUO) If an attempt to create
                            a new row does not include a value for columns
                            without defaults (neACLKMID) for the new row,
                            an inconsistentName error will be returned. (U//FOUO)
                            The value of this object has no effect on whether
                            other objects in this row can be modified."
        ::= { neACLEntry 2 }

    neFFExtensions OBJECT IDENTIFIER ::= { neFireflyKeys 4 }

    neFFExtensionsScalars OBJECT IDENTIFIER ::= { neFFExtensions 1 }

    neFFExtensionsTables OBJECT IDENTIFIER ::= { neFFExtensions 2 }

    neFireflyExtensionTable OBJECT-TYPE
        SYNTAX              SEQUENCE OF NeFireflyExtensionEntry
        MAX-ACCESS          not-accessible
        STATUS              current
        DESCRIPTION         "(U//FOUO) A table containing information about
                            the filled/loaded Firefly Vector Sets (FFVSs)
                            in the ECU. This table contains additional objects
                            for the hFireflyTable of the HAIPE-TRAFFIC-PROTECTION-MIB
                            of the HAIPE V3 MIBs. (U//FOUO) It extends, or
                            augments, the hFireflyTable by adding GDC4S-specific
                            columnar objects for configuration, status, and
                            other purposes"
        ::= { neFFExtensionsTables 1 }

    neFireflyExtensionEntry OBJECT-TYPE
        SYNTAX              NeFireflyExtensionEntry
        MAX-ACCESS          not-accessible
        STATUS              current
        DESCRIPTION         "(U//FOUO) An entry (row) containing additional
                            information applicable to a firefly vector set
                            (FFVS)."
        AUGMENTS            {
                                hFireflyEntry
                            }
        ::= { neFireflyExtensionTable 1 }

    NeFireflyExtensionEntry ::= SEQUENCE {
        neFFPACModuliId
            OCTET STRING
    }

    neFFPACModuliId OBJECT-TYPE
        SYNTAX              OCTET STRING (SIZE(12))
        MAX-ACCESS          read-only
        STATUS              current
        DESCRIPTION         "(U//FOUO) The Moduli ID of the PAC Module used
                            to dePAC this Firefly VS."
        ::= { neFireflyExtensionEntry 1 }

    nePPKKeys OBJECT IDENTIFIER ::= { neKeyObjects 2 }

    nePPKFillConfig OBJECT IDENTIFIER ::= { nePPKKeys 1 }

    nePPKFillCmd OBJECT-TYPE
        SYNTAX              TruthValue
        MAX-ACCESS          read-write
        STATUS              current
        DESCRIPTION         "(U//FOUO) This object, when set to TRUE, initiates
                            the filling of a Preplaced Key via the fill port.
                            (U//FOUO) When setting this object to TRUE, the
                            set command must always also set nePPKChainIDFillconfig
                            and nePPKEffectiveDate. Furthermore, if the PPK
                            being filled will be the first in the PPK Chain,
                            then nePPKUseConfig and nePPKAlgorith must also
                            be set at the same time. (U//FOUO) The default
                            value of this object is to not command PPK Filling
                            (FALSE). (U//FOUO) When this object is set to
                            FALSE by the operator during a fill operation
                            and before the DTD begins transferring data,
                            the in-process load operation is aborted and
                            the object commonPPKFillStatus is set to ABORTED.
                            (U//FOUO) Upon completion of the fill operation,
                            either successfully or unsuccessfully, this object
                            is automatically returned to the FALSE value.
                            (U//FOUO) This object, when read, returns an
                            error. It is only to be written."
        ::= { nePPKFillConfig 1 }

    nePPKFillStatus OBJECT-TYPE
        SYNTAX              KeyFillStatus
        MAX-ACCESS          read-only
        STATUS              current
        DESCRIPTION         "(U//FOUO) This object indicates the state of the
                            key fill process. (U//FOUO) The value of this
                            object is set to noFillCommand (1) at startup/restart.
                            It remains at that value until a key fill operation
                            is initiated, at which point the value changes
                            to inProcess (2). At the conclusion of the key
                            fill operation, this object is set to the appropriate
                            value, timedOut, failed, aborted, or successful.
                            It retains that value until a new key fill operation
                            is initated, at which point the object value
                            returns to inProcess, or until the device is
                            reset and the value returns to noFillCommand."
        ::= { nePPKFillConfig 2 }

    nePPKUseConfig OBJECT-TYPE
        SYNTAX              INTEGER {
                                user( 1 ),
                                ddPPK( 2 )
                            }
        MAX-ACCESS          read-write
        STATUS              current
        DESCRIPTION         "(U//FOUO) The use, User or Discovery PPK, that
                            the traffic PPK about to be filled is assigned.
                            (U//FOUO) The default value of this object is
                            user (1). (U//FOUO) This object, when read, returns
                            a non-sensical value of USER. It is only to be
                            written."
        ::= { nePPKFillConfig 3 }

    nePPKAlgorithm OBJECT-TYPE
        SYNTAX              HaipeEncryptionAlgorithm
        MAX-ACCESS          read-write
        STATUS              current
        DESCRIPTION         "(U//FOUO) The key type of the PPK being filled.
                            This value is entered as the hPPKTrafficEncryptionAlgorithm
                            object of the row in the hPPKTrafficTable. (U//FOUO)
                            This object, when read, returns a value of UNASSIGNED.
                            It is only to be written."
        ::= { nePPKFillConfig 4 }

    nePPKChainIDFillConfig OBJECT-TYPE
        SYNTAX              SnmpAdminString
        MAX-ACCESS          read-write
        STATUS              current
        DESCRIPTION         "(U//FOUO) The ChainID (slot) to which the PPK
                            about to be filled is assigned. (U//FOUO) This
                            object, when read, returns a value of ZERO (0).
                            It is only to be written."
        ::= { nePPKFillConfig 5 }

    nePPKEffectiveDate OBJECT-TYPE
        SYNTAX              DateAndTime
        MAX-ACCESS          read-write
        STATUS              current
        DESCRIPTION         "(U//FOUO) The effective date of the PPK being
                            filled. The effective date is entered here and
                            displayed as a Read-only object in the hPPKTable.
                            (U//FOUO) This object always returns 0 when read.
                            It is only to be written."
        ::= { nePPKFillConfig 6 }

    nePPKIntegrityAlgorithm OBJECT-TYPE
        SYNTAX              HaipeIntegrityAlgorithm
        MAX-ACCESS          read-write
        STATUS              current
        DESCRIPTION         "(U//FOUO) The integrity algorithm of the PPK being
                            filled. This value is entered as the hPPKTrafficIntegrityAlgorithm
                            object of the row in the hPPKTrafficTable. (U//FOUO)
                            This object, when read, returns a value of UNASSIGNED.
                            It is only to be written."
        ::= { nePPKFillConfig 7 }

    nePPKUsageType OBJECT-TYPE
        SYNTAX              INTEGER {
                                unassigned( 1 ),
                                trafficKey( 2 ),
                                exclusionKeyGlobal( 3 ),
                                exclusionKeyLocal( 4 ),
                                exclusionKeyPrivacy( 5 ),
                                exclusionKeySeparate( 6 )
                            }
        MAX-ACCESS          read-write
        STATUS              current
        DESCRIPTION         "(U//FOUO) The use, traffic or exclusion key, that
                            the PPK is to be assigned. The default value
                            of this object is unassigned(1). This object,
                            when read, returns a value of unassigned(1)."
        ::= { nePPKFillConfig 8 }

    nePPKEKUniversalID OBJECT-TYPE
        SYNTAX              FFUniversalID
        MAX-ACCESS          read-write
        STATUS              current
        DESCRIPTION         "(U//FOUO) The universal this EK is assigned to.
                            This object, when read, returns a value of 0000.
                            It is only to be written."
        ::= { nePPKFillConfig 9 }

    nePPKChangeoverKey OBJECT-TYPE
        SYNTAX              TruthValue
        MAX-ACCESS          read-write
        STATUS              current
        DESCRIPTION         "(U//FOUO) If a ChainID is specified when a PPK
                            is being added to a chain, this object specifies
                            whether the key being added is intended to be
                            a changeover key or not. If the key being added
                            is intended to be a changeover key, then the
                            ChainID should already exist. If the key being
                            added is not intended to be a changeover key
                            then the ChainID should be the name of a new
                            chain. This object, when read, returns a value
                            of true. It is only to be written."
        ::= { nePPKFillConfig 10 }

    nePPKAssignment OBJECT IDENTIFIER ::= { nePPKKeys 2 }

    nePPKAssignmentTableCount OBJECT-TYPE
        SYNTAX              Integer32
        MAX-ACCESS          read-only
        STATUS              current
        DESCRIPTION         "(U//FOUO) The number of rows in the nePPKAsssignmentTable"
        ::= { nePPKAssignment 1 }

    nePPKAssignmentTable OBJECT-TYPE
        SYNTAX              SEQUENCE OF NePPKAssignmentEntry
        MAX-ACCESS          not-accessible
        STATUS              current
        DESCRIPTION         "(U//FOUO) This table identifies the Remote INEs
                            that can establish a Security Association using
                            the PPK assigned to the identified slot. (U//FOUO)
                            This is the PPK Assignment Table."
        ::= { nePPKAssignment 2 }

    nePPKAssignmentEntry OBJECT-TYPE
        SYNTAX              NePPKAssignmentEntry
        MAX-ACCESS          not-accessible
        STATUS              current
        DESCRIPTION         "(U//FOUO) A row mapping the Cipher Text and Plain
                            Text port addresses to the assigned PPK Slot.
                            Each row represents an entry in the PPK Assignment
                            Table"
        INDEX               {
                                nePPKAssignmentChainID,
                                nePPKAssignmentCtAddressType,
                                nePPKAssignmentCtAddr
                            }
        ::= { nePPKAssignmentTable 1 }

    NePPKAssignmentEntry ::= SEQUENCE {
        nePPKAssignmentChainID
            SnmpAdminString,
        nePPKAssignmentCtAddressType
            InetAddressType,
        nePPKAssignmentCtAddr
            InetAddress,
        nePPKAssignmentPtAddressType
            InetAddressType,
        nePPKAssignmentPtAddr
            InetAddress,
        nePPKAssignmentRowStatus
            RowStatus,
        nePPKAssignmentEnable
            TruthValue
    }

    nePPKAssignmentChainID OBJECT-TYPE
        SYNTAX              SnmpAdminString
        MAX-ACCESS          read-create
        STATUS              current
        DESCRIPTION         "(U//FOUO) This object correlates a Chain ID (PPK
                            Slot) with the INE identified by its CT address
                            in this row. (U//FOUO) Chain IDs (Slots) are
                            numbered from 1 through 16 for each security
                            level."
        ::= { nePPKAssignmentEntry 1 }

    nePPKAssignmentCtAddressType OBJECT-TYPE
        SYNTAX              InetAddressType
        MAX-ACCESS          read-create
        STATUS              current
        DESCRIPTION         "(U//FOUO) The Internet address type for the address
                            of the Cipher Text port of the corresponding
                            Remote INE."
        ::= { nePPKAssignmentEntry 2 }

    nePPKAssignmentCtAddr OBJECT-TYPE
        SYNTAX              InetAddress
        MAX-ACCESS          read-create
        STATUS              current
        DESCRIPTION         "(U//FOUO) The Internet address assigned to the
                            Cipher Text port of the corresponding Remote
                            INE."
        ::= { nePPKAssignmentEntry 3 }

    nePPKAssignmentPtAddressType OBJECT-TYPE
        SYNTAX              InetAddressType
        MAX-ACCESS          read-create
        STATUS              current
        DESCRIPTION         "(U//FOUO) The Internet address type for the address
                            of the Plain Text port of the corresponding Remote
                            INE."
        ::= { nePPKAssignmentEntry 4 }

    nePPKAssignmentPtAddr OBJECT-TYPE
        SYNTAX              InetAddress
        MAX-ACCESS          read-create
        STATUS              current
        DESCRIPTION         "(U//FOUO) The Internet address assigned to the
                            Plain Text port of the corresponding Remote INE."
        ::= { nePPKAssignmentEntry 5 }

    nePPKAssignmentEnable OBJECT-TYPE
        SYNTAX              TruthValue
        MAX-ACCESS          read-create
        STATUS              current
        DESCRIPTION         "(U//FOUO) The object is used to enable or disable
                            the PPK Assignement. It is provided so the SNMP
                            Views can filter access such that one manager
                            can Create and Destroy PPK Assignment Table rows
                            through the use of the nePPKAssignmentRowStatus
                            object, and another can enable/disable the PPK
                            Assignment of this row through this object. (U//FOUO)
                            The default value of this object is true (1)"
        ::= { nePPKAssignmentEntry 6 }

    nePPKAssignmentRowStatus OBJECT-TYPE
        SYNTAX              RowStatus
        MAX-ACCESS          read-create
        STATUS              current
        DESCRIPTION         "(U//FOUO) The status of this row, by which new
                            entries may be created, enabled, disabled or
                            deleted from this table. (U//FOUO) 'active' indicates
                            an SA is to be created with the remote INE when
                            the following two conditions occur, 1- the device
                            transitions to the offline state and 2 - the
                            device is set to the same security level as the
                            PPK; or 1 - when the row is first created in
                            the offline or secure comms state, and 2 - the
                            INE security level is set to the same level as
                            the PPK. (U//FOUO) 'notInService' indicates an
                            SA is to not be created with the remote INE,
                            and if an SA had previously been created, that
                            it is to be terminated. (note: When the related
                            PPK is the DDPPK, setting the PPK assignment
                            to notInService disables Secure Dynamic Discovery.)
                            (U//FOUO) 'createAndGo' indicates the newly created
                            row is to have its status automatically set to
                            active. Newly created rows always become active.
                            The operator must explicitly disable rows by
                            setting this object to 'notInService'. (U//FOUO)
                            'destroy' indicates the PPK assignment row is
                            to be deleted and the established SA terminated.
                            (U//FOUO) Note, Only the RowStatus column in
                            this table may be modified, no other column may
                            be modified. Instead, rows must be deleted and
                            then created."
        ::= { nePPKAssignmentEntry 7 }

    nePPKSlotAssignments OBJECT IDENTIFIER ::= { nePPKKeys 3 }

    nePPKSlotAssignTable OBJECT-TYPE
        SYNTAX              SEQUENCE OF NePPKSlotAssignEntry
        MAX-ACCESS          not-accessible
        STATUS              current
        DESCRIPTION         "(U//FOUO) This table identifies the use of the
                            PPKs assigned to the slot (chainID) identified.
                            It identifies those traffic PPKs (hPPKUsageType
                            = trafficKey) that are used to support user traffic
                            and those that are used for Secure Dynamic Discovery."
        ::= { nePPKSlotAssignments 1 }

    nePPKSlotAssignEntry OBJECT-TYPE
        SYNTAX              NePPKSlotAssignEntry
        MAX-ACCESS          not-accessible
        STATUS              current
        DESCRIPTION         "(U//FOUO) A row relating the PPK Slot (Chain ID)
                            to the usage"
        INDEX               {
                                nePPKChainID
                            }
        ::= { nePPKSlotAssignTable 1 }

    NePPKSlotAssignEntry ::= SEQUENCE {
        nePPKChainID
            SnmpAdminString,
        nePPKSlotUse
            INTEGER
    }

    nePPKChainID OBJECT-TYPE
        SYNTAX              SnmpAdminString
        MAX-ACCESS          not-accessible
        STATUS              current
        DESCRIPTION         "(U//FOUO) The slot number for which the PPK Usage
                            identified in this row is assigned."
        ::= { nePPKSlotAssignEntry 1 }

    nePPKSlotUse OBJECT-TYPE
        SYNTAX              INTEGER {
                                userPPK( 1 ),
                                dynamicdiscoveryPPK( 2 )
                            }
        MAX-ACCESS          read-only
        STATUS              current
        DESCRIPTION         "(U//FOUO) The operator-assigned use of the traffic
                            PPK (hPPKUsageType = trafficKey) assigned to
                            this ChainID (Slot)."
        ::= { nePPKSlotAssignEntry 2 }

    --END nePPKSlotAssignments 'group'
    --J. Holzhauer Note: BEGIN MIB items added for GigE/Mini R3.4
    nePPKExtensions OBJECT IDENTIFIER ::= { nePPKKeys 4 }

    --J. Holzhauer Note: the following MIB items added as a placeholder for any
    --scalar MIB objects that are or might be applicable to
    --PPK Extensions
    nePPKExtensionsScalars OBJECT IDENTIFIER ::= { nePPKExtensions 1 }

    neUnassignedPpkCount OBJECT-TYPE
        SYNTAX              Integer32
        MAX-ACCESS          read-only
        STATUS              current
        DESCRIPTION         "(U//FOUO) The number of rows in the hPreplacedKeyTable
                            that have not been assigned to a chain."
        ::= { nePPKExtensionsScalars 1 }

    neChainCount OBJECT-TYPE
        SYNTAX              Integer32
        MAX-ACCESS          read-only
        STATUS              current
        DESCRIPTION         "(U//FOUO) The number of unique values of hPPKChainID
                            that exist in the hPPKChainTable. This is the
                            total number of PPK chains including Traffic
                            and Exclusion Key chains"
        ::= { nePPKExtensionsScalars 2 }

    nePPKExtensionsTables OBJECT IDENTIFIER ::= { nePPKExtensions 2 }

    nePreplacedKeyExtensionTable OBJECT-TYPE
        SYNTAX              SEQUENCE OF NePreplacedKeyExtensionEntry
        MAX-ACCESS          not-accessible
        STATUS              current
        DESCRIPTION         "(U//FOUO) A table containing information about
                            the filled/loaded pre-placed keys (PPKs) in the
                            ECU. This table contains additional objects for
                            the hPreplacedKeyTable of the HAIPE-TRAFFIC-PROTECTION-MIB
                            of the HAIPE V3 MIBs. (U//FOUO) It extends, or
                            augments, the hPreplacedKeyTable by adding GDC4S-specific
                            columnar objects for configuration, status, and
                            other purposes."
        ::= { nePPKExtensionsTables 1 }

    nePreplacedKeyExtensionEntry OBJECT-TYPE
        SYNTAX              NePreplacedKeyExtensionEntry
        MAX-ACCESS          not-accessible
        STATUS              current
        DESCRIPTION         "(U//FOUO) An entry (row) containing additional
                            information applicable to a pre-placed key (PPK)."
        AUGMENTS            {
                                hPreplacedKeyEntry
                            }
        ::= { nePreplacedKeyExtensionTable 1 }

    NePreplacedKeyExtensionEntry ::= SEQUENCE {
        nePPKUpdateCount
            Unsigned32,
        nePPKSuite
            INTEGER,
        nePPKChainAssignment
            SnmpAdminString
    }

    nePPKUpdateCount OBJECT-TYPE
        SYNTAX              Unsigned32
        MAX-ACCESS          read-only
        STATUS              current
        DESCRIPTION         "(U//FOUO) The current update count of this pre-placed
                            key (PPK). This object corresponds to the updateCount
                            columnar object of the preplacedKeyTable of the
                            TACLANE-Enterprise-MIB. This object 'replaces'
                            the hPPKUpdateCount columnar object in the hPreplacedKeyTable
                            of the HAIPE-TRAFFIC-PROTECTION-MIB module of
                            the 07/22/2005 release of the HAIPE V3 MIBs.
                            The hPPKUpdateCount object was removed in subsequent
                            HAIPE V3 MIB releases."
        ::= { nePreplacedKeyExtensionEntry 3 }

    nePPKSuite OBJECT-TYPE
        SYNTAX              INTEGER {
                                suiteA( 1 ),
                                suiteB( 2 )
                            }
        MAX-ACCESS          read-only
        STATUS              current
        DESCRIPTION         "(U//FOUO) The Suite of the filled PPK (PPK/APPK)."
        ::= { nePreplacedKeyExtensionEntry 4 }

    --T. Huemiller 20081003 DRN MIB00133 added nePPKChainAssignment.
    --
    nePPKChainAssignment OBJECT-TYPE
        SYNTAX              SnmpAdminString (SIZE(0..32))
        MAX-ACCESS          read-only
        STATUS              current
        DESCRIPTION         "(U//FOUO) The PPK chain to which this Preplaced
                            Key is assigned. If this PPK is not assigned
                            to a PPK Chain, then this object is blank."
        ::= { nePreplacedKeyExtensionEntry 5 }

    --END nePPKExtensions 'group'
    --J. Holzhauer Note: END MIB items added for GigE/Mini R3.4
    --T. Huemiller 20081216 - Added nePACModuliInformation
    nePACModuliInformation OBJECT IDENTIFIER ::= { neKeyObjects 3 }

    neUnInstalledPACModuliTableCount OBJECT-TYPE
        SYNTAX              Unsigned32
        MAX-ACCESS          read-only
        STATUS              current
        DESCRIPTION         "(U//FOUO) The number of rows in the neUnInstalledPACModuliTable."
        ::= { nePACModuliInformation 1 }

    neUnInstalledPACModuliTable OBJECT-TYPE
        SYNTAX              SEQUENCE OF NeUnInstalledPACModuliEntry
        MAX-ACCESS          not-accessible
        STATUS              current
        DESCRIPTION         "(U//FOUO) The table containing a list of uninstalled
                            DePAC moduli."
        ::= { nePACModuliInformation 2 }

    neUnInstalledPACModuliEntry OBJECT-TYPE
        SYNTAX              NeUnInstalledPACModuliEntry
        MAX-ACCESS          not-accessible
        STATUS              current
        DESCRIPTION         "(U//FOUO) A row describing information about uninstalled
                            DePAC moduli."
        INDEX               {
                                neUnInstalledPACIndex
                            }
        ::= { neUnInstalledPACModuliTable 1 }

    NeUnInstalledPACModuliEntry ::= SEQUENCE {
        neUnInstalledPACIndex
            Unsigned32,
        neUnInstalledPACBaseType
            INTEGER,
        neUnInstalledPACID
            OCTET STRING,
        neUnInstalledPACCOI
            INTEGER,
        neUnInstalledPACUserID
            OCTET STRING,
        neUnInstalledPACSourceID
            OCTET STRING,
        neUnInstalledPACNationalID
            OCTET STRING,
        neUnInstalledPACShortTitleName
            ShortTitle64,
        neUnInstalledPACAction
            INTEGER
    }

    neUnInstalledPACIndex OBJECT-TYPE
        SYNTAX              Unsigned32
        MAX-ACCESS          not-accessible
        STATUS              current
        DESCRIPTION         "(U//FOUO) A unique numeric index per uninstalled
                            DePAC moduli."
        ::= { neUnInstalledPACModuliEntry 1 }

    neUnInstalledPACBaseType OBJECT-TYPE
        SYNTAX              INTEGER {
                                base( 1 ),
                                alternate( 2 )
                            }
        MAX-ACCESS          read-only
        STATUS              current
        DESCRIPTION         "(U//FOUO) Identifies whether this is a Base or
                            Alternate moduli."
        ::= { neUnInstalledPACModuliEntry 2 }

    neUnInstalledPACID OBJECT-TYPE
        SYNTAX              OCTET STRING (SIZE(6))
        MAX-ACCESS          read-only
        STATUS              current
        DESCRIPTION         "(U//FOUO) The 6 byte integer value of the Moduli
                            ID from the CPC/PPC in network byte order."
        ::= { neUnInstalledPACModuliEntry 3 }

    neUnInstalledPACCOI OBJECT-TYPE
        SYNTAX              INTEGER {
                                us( 1 ),
                                nato( 2 ),
                                natoNations( 3 ),
                                cceb( 4 ),
                                coalition( 5 ),
                                foreignSovereign( 6 ),
                                reserved( 7 )
                            }
        MAX-ACCESS          read-only
        STATUS              current
        DESCRIPTION         "(U//FOUO) The COI associated with the Moduli ID
                            indicated by this row."
        ::= { neUnInstalledPACModuliEntry 4 }

    neUnInstalledPACUserID OBJECT-TYPE
        SYNTAX              OCTET STRING (SIZE(16))
        MAX-ACCESS          read-only
        STATUS              current
        DESCRIPTION         "(U//FOUO) 16 Character ASCII value from the User
                            ID from the CPC."
        ::= { neUnInstalledPACModuliEntry 5 }

    neUnInstalledPACSourceID OBJECT-TYPE
        SYNTAX              OCTET STRING (SIZE(16))
        MAX-ACCESS          read-only
        STATUS              current
        DESCRIPTION         "(U//FOUO) 16 Character ASCII value from the Source
                            ID from the CPC."
        ::= { neUnInstalledPACModuliEntry 6 }

    neUnInstalledPACNationalID OBJECT-TYPE
        SYNTAX              OCTET STRING (SIZE(16))
        MAX-ACCESS          read-only
        STATUS              current
        DESCRIPTION         "(U//FOUO) 16 Character ASCII value from the National
                            ID from the PPC."
        ::= { neUnInstalledPACModuliEntry 7 }

    neUnInstalledPACShortTitleName OBJECT-TYPE
        SYNTAX              ShortTitle64
        MAX-ACCESS          read-only
        STATUS              current
        DESCRIPTION         "(U//FOUO) The 64 byte ASCII short title for a
                            DePAC moduli."
        ::= { neUnInstalledPACModuliEntry 8 }

    neUnInstalledPACAction OBJECT-TYPE
        SYNTAX              INTEGER {
                                unInstalled( 1 ),
                                install( 2 ),
                                zeroize( 3 )
                            }
        MAX-ACCESS          read-write
        STATUS              current
        DESCRIPTION         "(U//FOUO) A SET to 'unInstalled' will be accepted
                            but cause no action to be taken by the ECU. 'unInstalled'
                            is the initial value placed in this object when
                            the DePAC Moduli is filled. (U//FOUO) For DePAC
                            Moduli of Base Type BASE, setting this object
                            to 'install' will cause the uninstalled DePAC
                            Moduli to replace the currently installed Base
                            DePAC Moduli. For De PAC Moduli of Base Type
                            ALTERNATE, setting this object to 'install' will
                            cause this DePAC Moduli to be installed in the
                            HAIPE DePACModuliTable with a value in hDModuliIndex
                            above any installed DePACModuli (it is installed
                            at the bottom of the list). Upon a successful
                            installation, this row is deleted from the neUnInstalledPACTable.
                            Once set to 'install' it may not be set to 'unInstalled'.
                            (U//FOUO) Setting this object to 'zeroize' will
                            cause this DePAC Moduli to be zeroized and the
                            corresponding row in this table to be deleted.
                            Once set to 'zeroize', it may not be set to 'install'."
        ::= { neUnInstalledPACModuliEntry 9 }

    neDePACModuliAugmentationTable OBJECT-TYPE
        SYNTAX              SEQUENCE OF NeDePACModuliAugmentationEntry
        MAX-ACCESS          not-accessible
        STATUS              current
        DESCRIPTION         "Table augments hDePACModuliTable."
        ::= { nePACModuliInformation 3 }

    neDePACModuliAugmentationEntry OBJECT-TYPE
        SYNTAX              NeDePACModuliAugmentationEntry
        MAX-ACCESS          not-accessible
        STATUS              current
        DESCRIPTION         "A row containing additional information about
                            installed DePAC Moduli. It augments the hDePACModuliTable
                            in the HAIPE-TRAFFIC-PROTECTION-MIB."
        AUGMENTS            {
                                hDePACModuliEntry
                            }
        ::= { neDePACModuliAugmentationTable 1 }

    NeDePACModuliAugmentationEntry ::= SEQUENCE {
        neDePACModuliZeroizeCMD
            TruthValue
    }

    neDePACModuliZeroizeCMD OBJECT-TYPE
        SYNTAX              TruthValue
        MAX-ACCESS          read-write
        STATUS              current
        DESCRIPTION         "(U//FOUO) This object is set to TRUE to zeroize
                            the corresponding DePAC Moduli and delete the
                            corresponding row of the hDePACModuliTable. (U//FOUO)
                            When set to FALSE, the set is accepted and no
                            action occurs. (U//FOUO) When read, it always
                            returns FALSE."
        ::= { neDePACModuliAugmentationEntry 1 }

    --R. Berman 20100825 DRN MIB00191 - Added neTAInformation
    neTAInformation OBJECT IDENTIFIER ::= { neKeyObjects 4 }

    neUninstalledTAInfo OBJECT IDENTIFIER ::= { neTAInformation 1 }

    neUninstalledTATableCount OBJECT-TYPE
        SYNTAX              Unsigned32
        MAX-ACCESS          read-only
        STATUS              current
        DESCRIPTION         "(U//FOUO) The number of rows in the neUninstalledTATable."
        ::= { neUninstalledTAInfo 1 }

    neUninstalledTATableLastChanged OBJECT-TYPE
        SYNTAX              TimeStamp
        MAX-ACCESS          read-only
        STATUS              current
        DESCRIPTION         "(U//FOUO) The value of the SNMPv2-MIB object SysUpTime
                            the last time any entry in the neUninstalledTATable
                            was modified, created, or deleted by either SNMP
                            or other management method (e.g., via an HMI)."
        ::= { neUninstalledTAInfo 2 }

    neUninstalledTAAction OBJECT-TYPE
        SYNTAX              INTEGER {
                                noAction( 1 ),
                                install( 2 ),
                                zeroize( 3 )
                            }
        MAX-ACCESS          read-write
        STATUS              current
        DESCRIPTION         "(U//FOUO) This object command the ECU to install
                            or zeroize all Trust Anchors held by the Uninstalled
                            TA Table. When read, it always returns 'noAction
                            1 )'. (U//FOUO) A SET to 'noAction' is accepted
                            but causes no action to be taken by the ECU.
                            'noAction' is the initial value of this object.
                            (U//FOUO) Setting this object to 'install' causes
                            all of the trust anchors defined in the Uninstalled
                            TA Table to be installed. (U//FOUO) Setting this
                            object to 'zeroize' causes all entries in the
                            Uninstalled TA Table to be deleted."
        ::= { neUninstalledTAInfo 3 }

    neUninstalledTACheckField OBJECT-TYPE
        SYNTAX              Unsigned32
        MAX-ACCESS          read-only
        STATUS              current
        DESCRIPTION         "(U//FOUO) This is the check field of the filled
                            but not installed Trust Anchor in the ECU. (U//FOUO)
                            If there are no Trust Anchors filled-and-not-installed,
                            then the value of this object is zero (0)."
        ::= { neUninstalledTAInfo 4 }

    neUninstalledTADoi OBJECT-TYPE
        SYNTAX              DateAndTime
        MAX-ACCESS          read-only
        STATUS              current
        DESCRIPTION         "(U//FOUO) This is the date of issuance of the
                            base Q-key filled but not installed in the ECU.
                            (U//FOUO) If there are no Trust Anchors filled-and-not-installed,
                            then the value of this object is 0000:01:01T00:00:00:00."
        ::= { neUninstalledTAInfo 5 }

    neUninstalledTATable OBJECT-TYPE
        SYNTAX              SEQUENCE OF NeUninstalledTATableEntry
        MAX-ACCESS          not-accessible
        STATUS              current
        DESCRIPTION         "(U//FOUO) The table containing a list of uninstalled
                            trust anchors."
        ::= { neUninstalledTAInfo 6 }

    neUninstalledTATableEntry OBJECT-TYPE
        SYNTAX              NeUninstalledTATableEntry
        MAX-ACCESS          not-accessible
        STATUS              current
        DESCRIPTION         "(U//FOUO) An entry (row) containing additional
                            information applicable to the trust anchor."
        INDEX               {
                                neUninstalledTAPartialKeyData
                            }
        ::= { neUninstalledTATable 1 }

    NeUninstalledTATableEntry ::= SEQUENCE {
        neUninstalledTAPartialKeyData
            OCTET STRING,
        neUninstalledTAShortTitle
            ShortTitle64,
        neUninstalledTAKMID
            KMID,
        neUninstalledTAType
            INTEGER,
        neUninstalledTACOI
            SnmpAdminString
    }

    neUninstalledTAPartialKeyData OBJECT-TYPE
        SYNTAX              OCTET STRING (SIZE(8))
        MAX-ACCESS          not-accessible
        STATUS              current
        DESCRIPTION         "(U//FOUO) The low order 64 bits of the ECDSA Public
                            Key. This information is matched against the
                            Partial Key Data inherent in the APPK material."
        ::= { neUninstalledTATableEntry 1 }

    neUninstalledTAShortTitle OBJECT-TYPE
        SYNTAX              ShortTitle64
        MAX-ACCESS          read-only
        STATUS              current
        DESCRIPTION         "(U//FOUO) The 64 byte ASCII short title of the
                            APPK trust anchor."
        ::= { neUninstalledTATableEntry 2 }

    neUninstalledTAKMID OBJECT-TYPE
        SYNTAX              KMID
        MAX-ACCESS          read-only
        STATUS              current
        DESCRIPTION         "(U//FOUO) The Key Management Identifier for the
                            APPK trust anchor."
        ::= { neUninstalledTATableEntry 3 }

    neUninstalledTAType OBJECT-TYPE
        SYNTAX              INTEGER {
                                base( 1 ),
                                alternative( 2 )
                            }
        MAX-ACCESS          read-only
        STATUS              current
        DESCRIPTION         "(U//FOUO) Indicates whether this is a Base or
                            Alternate trust anchor."
        ::= { neUninstalledTATableEntry 4 }

    neUninstalledTACOI OBJECT-TYPE
        SYNTAX              SnmpAdminString (SIZE(1..16))
        MAX-ACCESS          read-only
        STATUS              current
        DESCRIPTION         "(U//FOUO) This object is the COI for the trust
                            anchor."
        ::= { neUninstalledTATableEntry 5 }

    neInstalledTAInfo OBJECT IDENTIFIER ::= { neTAInformation 2 }

    neAPPKTACheckField OBJECT-TYPE
        SYNTAX              Unsigned32 (0..65535)
        MAX-ACCESS          read-only
        STATUS              current
        DESCRIPTION         "(U//FOUO) This is the check field for the Trust
                            Anchors installed in the ECU."
        ::= { neInstalledTAInfo 1 }

    neAPPKTADoi OBJECT-TYPE
        SYNTAX              DateAndTime
        MAX-ACCESS          read-only
        STATUS              current
        DESCRIPTION         "(U//FOUO) This is the date of issuance of the
                            base Q-key installed in the ECU."
        ::= { neInstalledTAInfo 2 }

    neAPPKTASignerId OBJECT-TYPE
        SYNTAX              OCTET STRING (SIZE(4))
        MAX-ACCESS          read-only
        STATUS              current
        DESCRIPTION         "(U//FOUO) This is the signer ID of the Q-keys
                            installed in the ECU."
        ::= { neInstalledTAInfo 3 }

    neAPPKTASignerIdDataBits OBJECT-TYPE
        SYNTAX              OCTET STRING (SIZE(16))
        MAX-ACCESS          read-only
        STATUS              current
        DESCRIPTION         "(U//FOUO) This is the signer ID data bits of the
                            Q-keys installed in the ECU."
        ::= { neInstalledTAInfo 4 }

    --R. Berman 20100825 DRN MIB00191 added neAPPKTAExtensionTable.
    --
    neAPPKTAExtensionTable OBJECT-TYPE
        SYNTAX              SEQUENCE OF NeAPPKTAExtensionEntry
        MAX-ACCESS          not-accessible
        STATUS              current
        DESCRIPTION         "(U//FOUO) The table augments hAPPKTrustAnchorTable."
        ::= { neInstalledTAInfo 5 }

    neAPPKTAExtensionEntry OBJECT-TYPE
        SYNTAX              NeAPPKTAExtensionEntry
        MAX-ACCESS          not-accessible
        STATUS              current
        DESCRIPTION         "(U//FOUO) An entry (row) containing additional
                            information applicable to the trust anchor."
        AUGMENTS            {
                                hAPPKTrustAnchorEntry
                            }
        ::= { neAPPKTAExtensionTable 1 }

    NeAPPKTAExtensionEntry ::= SEQUENCE {
        neAPPKTAZeroizeCMD
            TruthValue,
        neAPPKTAKMID
            KMID,
        neAPPKTAType
            INTEGER
    }

    neAPPKTAZeroizeCMD OBJECT-TYPE
        SYNTAX              TruthValue
        MAX-ACCESS          read-write
        STATUS              current
        DESCRIPTION         "(U//FOUO) This object is set to TRUE to zeroize
                            the corresponding trust anchor and delete the
                            corresponding row in hAPPKTATable. (U//FOUO)
                            When set to FALSE, the set is accepted and no
                            action occurs. (U//FOUO)When read, it always
                            returns FALSE."
        ::= { neAPPKTAExtensionEntry 1 }

    neAPPKTAKMID OBJECT-TYPE
        SYNTAX              KMID
        MAX-ACCESS          read-only
        STATUS              current
        DESCRIPTION         "(U//FOUO) The Key Management Identifier for the
                            APPK trust anchor."
        ::= { neAPPKTAExtensionEntry 2 }

    neAPPKTAType OBJECT-TYPE
        SYNTAX              INTEGER {
                                base( 1 ),
                                alternative( 2 )
                            }
        MAX-ACCESS          read-only
        STATUS              current
        DESCRIPTION         "(U//FOUO) Indicates whether this is a Base or
                            Alternate trust anchor."
        ::= { neAPPKTAExtensionEntry 3 }

    neSA OBJECT IDENTIFIER ::= { neManageObjs 4 }

    neSaNE OBJECT IDENTIFIER ::= { neSA 1 }

    neSAHostTimeOutPeriod OBJECT-TYPE
        SYNTAX              Integer32
        MAX-ACCESS          read-write
        STATUS              current
        DESCRIPTION         "(U//FOUO) the time in minutes that each host will
                            remain in the host table before it is automatically
                            removed (i.e. host administrative timer). (U//FOUO)
                            Range is Zero (0) to 1440 minutes. Default is
                            720 minutes. (U//FOUO) A value of zero (0) disables
                            the host administrative timer."
        ::= { neSaNE 1 }

    neDailyMtekUpdate OBJECT-TYPE
        SYNTAX              TruthValue
        MAX-ACCESS          read-write
        STATUS              current
        DESCRIPTION         "(U//FOUO) Defines which FireFly Vector Set update
                            is advertised during IKE exchanges; TRUE for
                            MTEK/Accordion; or FALSE for Accordion-only."
        ::= { neSaNE 2 }

    neTPSATableAugmentation OBJECT-TYPE
        SYNTAX              SEQUENCE OF NeTPSAEntry
        MAX-ACCESS          not-accessible
        STATUS              current
        DESCRIPTION         "(U//FOUO) This table provides status on the Security
                            Associations currently maintained by this device."
        ::= { neSaNE 3 }

    neTPSAEntry OBJECT-TYPE
        SYNTAX              NeTPSAEntry
        MAX-ACCESS          not-accessible
        STATUS              current
        DESCRIPTION         "(U//FOUO) A row augmenting a row in the hTPSATable,
                            identifying the Key Type and Identity, and PMTU
                            for the corresponding Security Association."
        AUGMENTS            {
                                hTPSAEntry
                            }
        ::= { neTPSATableAugmentation 1 }

    NeTPSAEntry ::= SEQUENCE {
        neSAType
            INTEGER,
        neSAFF
            RowPointer
    }

    neSAType OBJECT-TYPE
        SYNTAX              INTEGER {
                                ppk-Multicast( 1 ),
                                ppk-Unicast( 2 ),
                                ppk-SDD( 3 ),
                                ffvs( 4 )
                            }
        MAX-ACCESS          read-only
        STATUS              current
        DESCRIPTION         "(U//FOUO) The type of cryptographic key used to
                            establish this Security Association (FFVS or
                            PPK), and if PPK, the type of traffic supported
                            (Multicast, Unicast or Secure Dynamic Discovery)."
        ::= { neTPSAEntry 1 }

    neSAFF OBJECT-TYPE
        SYNTAX              RowPointer
        MAX-ACCESS          read-only
        STATUS              current
        DESCRIPTION         "(U//FOUO) A row pointer to a row in the hFireflyTable,
                            identifying the FFVS used for the Security Association
                            corresponding to this row. (U//FOUO) This object
                            returns 0.0 when neSAType is PPK."
        ::= { neTPSAEntry 2 }

    neSACTSortedTable OBJECT-TYPE
        SYNTAX              SEQUENCE OF NeSACTSortedEntry
        MAX-ACCESS          not-accessible
        STATUS              current
        DESCRIPTION         "(U//FOUO) This table maps the Remote CT Address
                            to the Index in the SA Table of the HAIPE-TRAFFIC-PROTECTION-MIB."
        ::= { neSaNE 4 }

    neSACTSortedEntry OBJECT-TYPE
        SYNTAX              NeSACTSortedEntry
        MAX-ACCESS          not-accessible
        STATUS              current
        DESCRIPTION         "(U//FOUO) A row in this table relates a row in
                            the hTPSATable to a known Remote CT Address."
        INDEX               {
                                neSARemoteCTAddrType,
                                neSARemoteCTAddr
                            }
        ::= { neSACTSortedTable 1 }

    NeSACTSortedEntry ::= SEQUENCE {
        neSARemoteCTAddrType
            InetAddressType,
        neSARemoteCTAddr
            InetAddress,
        neSAIndex
            Unsigned32,
        neSARemotePTAddrType
            InetAddressType,
        neSARemotePTAddr
            InetAddress,
        neSAIndexInCurrent
            Unsigned32,
        neSAIndexOutCurrent
            Unsigned32,
        neSAIndexInNext
            Unsigned32,
        neSAIndexOutNext
            Unsigned32,
        neSAKeyType
            INTEGER,
        neSAEstablished
            TruthValue
    }

    neSARemoteCTAddrType OBJECT-TYPE
        SYNTAX              InetAddressType
        MAX-ACCESS          not-accessible
        STATUS              current
        DESCRIPTION         "(U//FOUO) The address type of the CT Port of the
                            remote INE with which this SA has been established."
        ::= { neSACTSortedEntry 1 }

    neSARemoteCTAddr OBJECT-TYPE
        SYNTAX              InetAddress
        MAX-ACCESS          not-accessible
        STATUS              current
        DESCRIPTION         "(U//FOUO) The address of the CT Port of the remote
                            INE with which this SA has been established."
        ::= { neSACTSortedEntry 2 }

    neSAIndex OBJECT-TYPE
        SYNTAX              Unsigned32
        MAX-ACCESS          read-only
        STATUS              current
        DESCRIPTION         "(U//FOUO) The index number for the entry in the
                            SA Table for which an SA exists to the Remote
                            CT Address identified in this row. It is a unique
                            numeric index per SA. The significance and ordering
                            of this number will not reflect on the processing
                            order of lookups within the SAD at all and is
                            merely for management purposes."
        ::= { neSACTSortedEntry 3 }

    neSARemotePTAddrType OBJECT-TYPE
        SYNTAX              InetAddressType
        MAX-ACCESS          read-only
        STATUS              current
        DESCRIPTION         "(U//FOUO) The address type of the PT Port of the
                            remote INE with which this SA has been established."
        ::= { neSACTSortedEntry 4 }

    neSARemotePTAddr OBJECT-TYPE
        SYNTAX              InetAddress
        MAX-ACCESS          read-only
        STATUS              current
        DESCRIPTION         "(U//FOUO) The address of the PT Port of the remote
                            INE with which this SA has been established."
        ::= { neSACTSortedEntry 5 }

    neSAIndexInCurrent OBJECT-TYPE
        SYNTAX              Unsigned32
        MAX-ACCESS          read-only
        STATUS              current
        DESCRIPTION         "(U//FOUO) The index number for the incoming current
                            SA entry in the hTPSATable for which an SA exists
                            to the Remote CT Address identified in this row.
                            It is a unique numeric index per SA. The significance
                            and ordering of this number will not reflect
                            on the processing order of lookups within the
                            SAD at all and is merely for management purposes."
        ::= { neSACTSortedEntry 6 }

    neSAIndexOutCurrent OBJECT-TYPE
        SYNTAX              Unsigned32
        MAX-ACCESS          read-only
        STATUS              current
        DESCRIPTION         "(U//FOUO) The index number for the outgoing current
                            SA entry in the hTPSATable for which an SA exists
                            to the Remote CT Address identified in this row.
                            It is a unique numeric index per SA. The significance
                            and ordering of this number will not reflect
                            on the processing order of lookups within the
                            SAD at all and is merely for management purposes."
        ::= { neSACTSortedEntry 7 }

    neSAIndexInNext OBJECT-TYPE
        SYNTAX              Unsigned32
        MAX-ACCESS          read-only
        STATUS              current
        DESCRIPTION         "(U//FOUO) The index number for the incoming next/changeover
                            SA entry in the hTPSATable for which an SA exists
                            to the Remote CT Address identified in this row.
                            It is a unique numeric index per SA. The significance
                            and ordering of this number will not reflect
                            on the processing order of lookups within the
                            SAD at all and is merely for management purposes."
        ::= { neSACTSortedEntry 8 }

    neSAIndexOutNext OBJECT-TYPE
        SYNTAX              Unsigned32
        MAX-ACCESS          read-only
        STATUS              current
        DESCRIPTION         "(U//FOUO) The index number for the outgoing next/changeover
                            SA entry in the hTPSATable for which an SA exists
                            to the Remote CT Address identified in this row.
                            It is a unique numeric index per SA. The significance
                            and ordering of this number will not reflect
                            on the processing order of lookups within the
                            SAD at all and is merely for management purposes."
        ::= { neSACTSortedEntry 9 }

    neSAKeyType OBJECT-TYPE
        SYNTAX              INTEGER {
                                preplacedKey( 1 ),
                                firefly( 2 )
                            }
        MAX-ACCESS          read-only
        STATUS              current
        DESCRIPTION         "(U//FOUO) The key type (PPK or FIREFLY) used with
                            the SA represented in this table."
        ::= { neSACTSortedEntry 10 }

    neSAEstablished OBJECT-TYPE
        SYNTAX              TruthValue
        MAX-ACCESS          read-only
        STATUS              current
        DESCRIPTION         "(U//FOUO) This object indicates whether or not
                            the Security Association (SA) is fully configured
                            and ready to process traffic. This object returns
                            'true(1)' if the SA is established, and returns
                            'false(2)' if the SA is not established."
        ::= { neSACTSortedEntry 11 }

    neIPMEIRMode OBJECT-TYPE
        SYNTAX              TruthValue
        MAX-ACCESS          read-write
        STATUS              current
        DESCRIPTION         "(U//FOUO) This object enables or disables IPMEIR
                            mode as an option for SA establishment method."
        ::= { neSaNE 5 }

    neSAPairTable OBJECT-TYPE
        SYNTAX              SEQUENCE OF NeSAPairEntry
        MAX-ACCESS          not-accessible
        STATUS              current
        DESCRIPTION         "(U//FOUO) This table maps the Remote CT Address
                            and SA ID to the Indices of the in and out rows
                            in the SAD Tables of the HAIPE-V4-TRAFFIC-PROTECTION-MIB."
        ::= { neSaNE 6 }

    neSAPairEntry OBJECT-TYPE
        SYNTAX              NeSAPairEntry
        MAX-ACCESS          not-accessible
        STATUS              current
        DESCRIPTION         "(U//FOUO) A row in this table relates a row in
                            the HAIPE SAD tables to a known Remote CT Address
                            and SA ID."
        INDEX               {
                                neSAPairAddrType,
                                neSAPairRemoteCTAddr,
                                neSAPairID
                            }
        ::= { neSAPairTable 1 }

    NeSAPairEntry ::= SEQUENCE {
        neSAPairAddrType
            IPAddressType,
        neSAPairRemoteCTAddr
            IPAddress,
        neSAPairID
            Unsigned32,
        neSAPairEstablishmentMethod
            INTEGER,
        neSAPairRemotePTAddr
            IPAddress,
        neSAPairEstablished
            TruthValue,
        neSAPairIndexIn
            Unsigned32,
        neSAPairIndexOut
            Unsigned32,
        neSAPairSPIIn
            Unsigned32,
        neSAPairSPIOut
            Unsigned32,
        neSAPairReachable
            TruthValue,
        neSAPairTransmitCount
            Counter64,
        neSAPairReceiveCount
            Counter64,
        neSAPairClearCounts
            TruthValue
    }

    neSAPairAddrType OBJECT-TYPE
        SYNTAX              IPAddressType
        MAX-ACCESS          not-accessible
        STATUS              current
        DESCRIPTION         "(U//FOUO) The address type of the CT Port of the
                            remote INE with which this SA has been established."
        ::= { neSAPairEntry 1 }

    neSAPairRemoteCTAddr OBJECT-TYPE
        SYNTAX              IPAddress
        MAX-ACCESS          not-accessible
        STATUS              current
        DESCRIPTION         "(U//FOUO) The address of the CT Port of the remote
                            INE with which this SA has been established."
        ::= { neSAPairEntry 2 }

    neSAPairID OBJECT-TYPE
        SYNTAX              Unsigned32
        MAX-ACCESS          not-accessible
        STATUS              current
        DESCRIPTION         "(U//FOUO) The index number to identify this SA
                            pair. The significance and ordering of this number
                            will not reflect on the processing order of lookups
                            within the SAD at all and is merely for management
                            purposes."
        ::= { neSAPairEntry 3 }

    neSAPairEstablishmentMethod OBJECT-TYPE
        SYNTAX              INTEGER {
                                manual( 1 ),
                                ikev1( 2 ),
                                ikev2( 3 )
                            }
        MAX-ACCESS          read-only
        STATUS              current
        DESCRIPTION         "(U//FOUO) The method of establishment for this
                            SA."
        ::= { neSAPairEntry 4 }

    neSAPairRemotePTAddr OBJECT-TYPE
        SYNTAX              IPAddress
        MAX-ACCESS          read-only
        STATUS              current
        DESCRIPTION         "(U//FOUO) The address of the PT Port of the remote
                            INE with which this SA has been established."
        ::= { neSAPairEntry 5 }

    neSAPairEstablished OBJECT-TYPE
        SYNTAX              TruthValue
        MAX-ACCESS          read-only
        STATUS              current
        DESCRIPTION         "(U//FOUO) This object indicates whether or not
                            the Security Association (SA) is fully configured
                            and ready to process traffic. This object returns
                            'true(1)' if the SA is established, and returns
                            'false(2)' if the SA is not established."
        ::= { neSAPairEntry 6 }

    neSAPairIndexIn OBJECT-TYPE
        SYNTAX              Unsigned32
        MAX-ACCESS          read-only
        STATUS              current
        DESCRIPTION         "(U//FOUO) The index number for the incoming SA
                            entry in the SAD Table for which an SA exists
                            to the Remote CT Address identified in this row.
                            It is a unique numeric index per SA."
        ::= { neSAPairEntry 7 }

    neSAPairIndexOut OBJECT-TYPE
        SYNTAX              Unsigned32
        MAX-ACCESS          read-only
        STATUS              current
        DESCRIPTION         "(U//FOUO) The index number for the outgoing SA
                            entry in the SAD Table for which an SA exists
                            to the Remote CT Address identified in this row.
                            It is a unique numeric index per SA."
        ::= { neSAPairEntry 8 }

    neSAPairSPIIn OBJECT-TYPE
        SYNTAX              Unsigned32
        MAX-ACCESS          read-only
        STATUS              current
        DESCRIPTION         "(U//FOUO) The SPI for the incoming SAD entry."
        ::= { neSAPairEntry 9 }

    neSAPairSPIOut OBJECT-TYPE
        SYNTAX              Unsigned32
        MAX-ACCESS          read-only
        STATUS              current
        DESCRIPTION         "(U//FOUO) The SPI for the outgoing SAD entry."
        ::= { neSAPairEntry 10 }

    neSAPairReachable OBJECT-TYPE
        SYNTAX              TruthValue
        MAX-ACCESS          read-only
        STATUS              current
        DESCRIPTION         "(U//FOUO) This object indicates whether or not
                            the Security Association (SA) is reachable or
                            not. This object returns 'true(1)' if the SA
                            is reachable, and returns 'false(2)' if the SA
                            is not reachable."
        ::= { neSAPairEntry 11 }

    neSAPairTransmitCount OBJECT-TYPE
        SYNTAX              Counter64
        MAX-ACCESS          read-only
        STATUS              current
        DESCRIPTION         "(U//FOUO) The number of packets transmited out
                            on this SA. This represents the number of packets
                            that have been encrypted and sent out."
        ::= { neSAPairEntry 12 }

    neSAPairReceiveCount OBJECT-TYPE
        SYNTAX              Counter64
        MAX-ACCESS          read-only
        STATUS              current
        DESCRIPTION         "(U//FOUO) The number of packets received on this
                            SA. This represents the number of packets that
                            have been decrypted."
        ::= { neSAPairEntry 13 }

    neSAPairClearCounts OBJECT-TYPE
        SYNTAX              TruthValue
        MAX-ACCESS          read-write
        STATUS              current
        DESCRIPTION         "(U//FOUO) Setting this object to 'true' will clear
                            the transmit and receive counts in the row. When
                            read this object should return its value. If
                            this object is set to the same value as the current
                            value, the device must not perform any operation
                            but should accept this as a valid SET operation.
                            Once the value is set to true, attempts to set
                            it back to false will return an inconsistentValue
                            error."
        ::= { neSAPairEntry 14 }

    neIKEv2SATable OBJECT-TYPE
        SYNTAX              SEQUENCE OF NeIKEv2SAEntry
        MAX-ACCESS          not-accessible
        STATUS              current
        DESCRIPTION         "(U//FOUO) This table maps the Remote CT Address
                            and SA ID to the Index of the row in the IKEv2
                            SAD Table of the HAIPE-V4-TRAFFIC-PROTECTION-MIB."
        ::= { neSaNE 7 }

    neIKEv2SAEntry OBJECT-TYPE
        SYNTAX              NeIKEv2SAEntry
        MAX-ACCESS          not-accessible
        STATUS              current
        DESCRIPTION         "(U//FOUO) A row in this table relates a row in
                            the HAIPE IKEv2 SAD table to a known Remote CT
                            Address and SA ID."
        INDEX               {
                                neIKEv2SAAddrType,
                                neIKEv2SARemoteCTAddr,
                                neIKEv2SAID
                            }
        ::= { neIKEv2SATable 1 }

    NeIKEv2SAEntry ::= SEQUENCE {
        neIKEv2SAAddrType
            IPAddressType,
        neIKEv2SARemoteCTAddr
            IPAddress,
        neIKEv2SAID
            Unsigned32,
        neIKEv2SASADIndex
            Unsigned32,
        neIKEv2SARemoteSPI
            OCTET STRING,
        neIKEv2SALocalSPI
            OCTET STRING,
        neIKEv2SAReachable
            TruthValue,
        neIKEv2SAChildSACount
            Unsigned32
    }

    neIKEv2SAAddrType OBJECT-TYPE
        SYNTAX              IPAddressType
        MAX-ACCESS          not-accessible
        STATUS              current
        DESCRIPTION         "(U//FOUO) The address type of the CT Port of the
                            remote INE with which this SA has been established."
        ::= { neIKEv2SAEntry 1 }

    neIKEv2SARemoteCTAddr OBJECT-TYPE
        SYNTAX              IPAddress
        MAX-ACCESS          not-accessible
        STATUS              current
        DESCRIPTION         "(U//FOUO) The address of the CT Port of the remote
                            INE with which this SA has been established."
        ::= { neIKEv2SAEntry 2 }

    neIKEv2SAID OBJECT-TYPE
        SYNTAX              Unsigned32
        MAX-ACCESS          not-accessible
        STATUS              current
        DESCRIPTION         "(U//FOUO) The index number to identify the IKE
                            SA. The significance and ordering of this number
                            will not reflect on the processing order of lookups
                            within the SAD at all and is merely for management
                            purposes."
        ::= { neIKEv2SAEntry 3 }

    neIKEv2SASADIndex OBJECT-TYPE
        SYNTAX              Unsigned32
        MAX-ACCESS          read-only
        STATUS              current
        DESCRIPTION         "(U//FOUO) The index number for the IKEv2 IKE SA
                            entry in the SAD Table for which an SA exists
                            to the Remote CT Address identified in this row.
                            It is a unique numeric index per SA."
        ::= { neIKEv2SAEntry 4 }

    neIKEv2SARemoteSPI OBJECT-TYPE
        SYNTAX              OCTET STRING (SIZE(8))
        MAX-ACCESS          read-only
        STATUS              current
        DESCRIPTION         "(U//FOUO) The remote SPI for the SAD entry."
        ::= { neIKEv2SAEntry 5 }

    neIKEv2SALocalSPI OBJECT-TYPE
        SYNTAX              OCTET STRING (SIZE(8))
        MAX-ACCESS          read-only
        STATUS              current
        DESCRIPTION         "(U//FOUO) The local SPI for the SAD entry."
        ::= { neIKEv2SAEntry 6 }

    neIKEv2SAReachable OBJECT-TYPE
        SYNTAX              TruthValue
        MAX-ACCESS          read-only
        STATUS              current
        DESCRIPTION         "(U//FOUO) This object indicates whether or not
                            the Security Association (SA) is reachable or
                            not. This object returns 'true(1)' if the SA
                            is reachable, and returns 'false(2)' if the SA
                            is not reachable."
        ::= { neIKEv2SAEntry 7 }

    neIKEv2SAChildSACount OBJECT-TYPE
        SYNTAX              Unsigned32
        MAX-ACCESS          read-only
        STATUS              current
        DESCRIPTION         "(U//FOUO) The number of Child SAs."
        ::= { neIKEv2SAEntry 8 }

    neIKEv2IKEAndCHILDSATable OBJECT-TYPE
        SYNTAX              SEQUENCE OF NeIKEv2IKEAndCHILDSAEntry
        MAX-ACCESS          not-accessible
        STATUS              current
        DESCRIPTION         "(U//FOUO) This table maps the Remote CT Address,
                            IKEv2 IKE SA ID, and IKEv2 Child SA ID to the
                            Index of the rows in the IKEv2 SAD Tables of
                            the HAIPE-V4-TRAFFIC-PROTECTION-MIB."
        ::= { neSaNE 8 }

    neIKEv2IKEAndCHILDSAEntry OBJECT-TYPE
        SYNTAX              NeIKEv2IKEAndCHILDSAEntry
        MAX-ACCESS          not-accessible
        STATUS              current
        DESCRIPTION         "(U//FOUO) A row in this table relates a row in
                            the HAIPE IKEv2 IKE and Child SAD tables to a
                            known Remote CT Address, IKEv2 IKE SA ID, and
                            IKEv2 Child SA ID."
        INDEX               {
                                neIKEv2IKEAndCHILDSAAddrType,
                                neIKEv2IKEAndCHILDSARemoteCTAddr,
                                neIKEv2IKEAndCHILDSAIkeSAID,
                                neIKEv2IKEAndCHILDSAChildSAID
                            }
        ::= { neIKEv2IKEAndCHILDSATable 1 }

    NeIKEv2IKEAndCHILDSAEntry ::= SEQUENCE {
        neIKEv2IKEAndCHILDSAAddrType
            IPAddressType,
        neIKEv2IKEAndCHILDSARemoteCTAddr
            IPAddress,
        neIKEv2IKEAndCHILDSAIkeSAID
            Unsigned32,
        neIKEv2IKEAndCHILDSAChildSAID
            Unsigned32,
        neIKEv2IKEAndCHILDSAIkeSADIndex
            Unsigned32,
        neIKEv2IKEAndCHILDSAChildSADIndexIn
            Unsigned32,
        neIKEv2IKEAndCHILDSAChildSADIndexOut
            Unsigned32,
        neIKEv2IKEAndCHILDSASPIIn
            Unsigned32,
        neIKEv2IKEAndCHILDSASPIOut
            Unsigned32,
        neIKEv2IKEAndCHILDSAEstablished
            TruthValue,
        neIKEv2IKEAndCHILDSAReachable
            TruthValue,
        neIKEv2IKEAndCHILDSATransmitCount
            Counter64,
        neIKEv2IKEAndCHILDSAReceiveCount
            Counter64,
        neIKEv2IKEAndCHILDSAClearCounts
            TruthValue
    }

    neIKEv2IKEAndCHILDSAAddrType OBJECT-TYPE
        SYNTAX              IPAddressType
        MAX-ACCESS          not-accessible
        STATUS              current
        DESCRIPTION         "(U//FOUO) The address type of the CT Port of the
                            remote INE with which the SAs have been established."
        ::= { neIKEv2IKEAndCHILDSAEntry 1 }

    neIKEv2IKEAndCHILDSARemoteCTAddr OBJECT-TYPE
        SYNTAX              IPAddress
        MAX-ACCESS          not-accessible
        STATUS              current
        DESCRIPTION         "(U//FOUO) The address of the CT Port of the remote
                            INE with which the SAs have been established."
        ::= { neIKEv2IKEAndCHILDSAEntry 2 }

    neIKEv2IKEAndCHILDSAIkeSAID OBJECT-TYPE
        SYNTAX              Unsigned32
        MAX-ACCESS          not-accessible
        STATUS              current
        DESCRIPTION         "(U//FOUO) The index number to identify the IKE
                            SA. The significance and ordering of this number
                            will not reflect on the processing order of lookups
                            within the SAD at all and is merely for management
                            purposes."
        ::= { neIKEv2IKEAndCHILDSAEntry 3 }

    neIKEv2IKEAndCHILDSAChildSAID OBJECT-TYPE
        SYNTAX              Unsigned32
        MAX-ACCESS          not-accessible
        STATUS              current
        DESCRIPTION         "(U//FOUO) The index number to identify the Child
                            SA. The significance and ordering of this number
                            will not reflect on the processing order of lookups
                            within the SAD at all and is merely for management
                            purposes."
        ::= { neIKEv2IKEAndCHILDSAEntry 4 }

    neIKEv2IKEAndCHILDSAIkeSADIndex OBJECT-TYPE
        SYNTAX              Unsigned32
        MAX-ACCESS          read-only
        STATUS              current
        DESCRIPTION         "(U//FOUO) The index number for the IKEv2 IKE SA
                            entry in the SAD Table for which an SA exists
                            to the Remote CT Address identified in this row.
                            It is a unique numeric index per SA."
        ::= { neIKEv2IKEAndCHILDSAEntry 5 }

    neIKEv2IKEAndCHILDSAChildSADIndexIn OBJECT-TYPE
        SYNTAX              Unsigned32
        MAX-ACCESS          read-only
        STATUS              current
        DESCRIPTION         "(U//FOUO) The index number for the IKEv2 Child
                            In SA entry in the SAD Table for which an SA
                            exists to the Remote CT Address identified in
                            this row. It is a unique numeric index per SA."
        ::= { neIKEv2IKEAndCHILDSAEntry 6 }

    neIKEv2IKEAndCHILDSAChildSADIndexOut OBJECT-TYPE
        SYNTAX              Unsigned32
        MAX-ACCESS          read-only
        STATUS              current
        DESCRIPTION         "(U//FOUO) The index number for the IKEv2 Child
                            Out SA entry in the SAD Table for which an SA
                            exists to the Remote CT Address identified in
                            this row. It is a unique numeric index per SA."
        ::= { neIKEv2IKEAndCHILDSAEntry 7 }

    neIKEv2IKEAndCHILDSASPIIn OBJECT-TYPE
        SYNTAX              Unsigned32
        MAX-ACCESS          read-only
        STATUS              current
        DESCRIPTION         "(U//FOUO) The SPI for the Child In SAD entry."
        ::= { neIKEv2IKEAndCHILDSAEntry 8 }

    neIKEv2IKEAndCHILDSASPIOut OBJECT-TYPE
        SYNTAX              Unsigned32
        MAX-ACCESS          read-only
        STATUS              current
        DESCRIPTION         "(U//FOUO) The SPI for the Child Out SAD entry."
        ::= { neIKEv2IKEAndCHILDSAEntry 9 }

    neIKEv2IKEAndCHILDSAEstablished OBJECT-TYPE
        SYNTAX              TruthValue
        MAX-ACCESS          read-only
        STATUS              current
        DESCRIPTION         "(U//FOUO) This object indicates whether or not
                            the Child Security Association (SA) is established
                            or not. This object returns 'true(1)' if the
                            SA is established, and returns 'false(2)' if
                            the SA is not established."
        ::= { neIKEv2IKEAndCHILDSAEntry 10 }

    neIKEv2IKEAndCHILDSAReachable OBJECT-TYPE
        SYNTAX              TruthValue
        MAX-ACCESS          read-only
        STATUS              current
        DESCRIPTION         "(U//FOUO) This object indicates whether or not
                            the Child Security Association (SA) is reachable
                            or not. This object returns 'true(1)' if the
                            SA is reachable, and returns 'false(2)' if the
                            SA is not reachable."
        ::= { neIKEv2IKEAndCHILDSAEntry 11 }

    neIKEv2IKEAndCHILDSATransmitCount OBJECT-TYPE
        SYNTAX              Counter64
        MAX-ACCESS          read-only
        STATUS              current
        DESCRIPTION         "(U//FOUO) The number of packets transmited out
                            on this SA. This represents the number of packets
                            that have been encrypted and sent out."
        ::= { neIKEv2IKEAndCHILDSAEntry 12 }

    neIKEv2IKEAndCHILDSAReceiveCount OBJECT-TYPE
        SYNTAX              Counter64
        MAX-ACCESS          read-only
        STATUS              current
        DESCRIPTION         "(U//FOUO) The number of packets received on this
                            SA. This represents the number of packets that
                            have been decrypted."
        ::= { neIKEv2IKEAndCHILDSAEntry 13 }

    neIKEv2IKEAndCHILDSAClearCounts OBJECT-TYPE
        SYNTAX              TruthValue
        MAX-ACCESS          read-write
        STATUS              current
        DESCRIPTION         "(U//FOUO) Setting this object to 'true' will clear
                            the transmit and receive counts in the row. When
                            read this object should return its value. If
                            this object is set to the same value as the current
                            value, the device must not perform any operation
                            but should accept this as a valid SET operation.
                            Once the value is set to true, attempts to set
                            it back to false will return an inconsistentValue
                            error."
        ::= { neIKEv2IKEAndCHILDSAEntry 14 }

    neManSAPairTable OBJECT-TYPE
        SYNTAX              SEQUENCE OF NeManSAPairEntry
        MAX-ACCESS          not-accessible
        STATUS              current
        DESCRIPTION         "(U//FOUO) This table maps the Remote CT Address
                            and SA ID to the Indices of the in and out rows
                            in the SAD Tables of the HAIPE-V4-TRAFFIC-PROTECTION-MIB."
        ::= { neSaNE 9 }

    neManSAPairEntry OBJECT-TYPE
        SYNTAX              NeManSAPairEntry
        MAX-ACCESS          not-accessible
        STATUS              current
        DESCRIPTION         "(U//FOUO) A row in this table relates a row in
                            the HAIPE SAD tables to a known Remote CT Address
                            and SA ID."
        INDEX               {
                                neManSAPairAddrType,
                                neManSAPairRemoteCTAddr,
                                neManSAPairID
                            }
        ::= { neManSAPairTable 1 }

    NeManSAPairEntry ::= SEQUENCE {
        neManSAPairAddrType
            IPAddressType,
        neManSAPairRemoteCTAddr
            IPAddress,
        neManSAPairID
            Unsigned32,
        neManSAPairRemotePTAddr
            IPAddress,
        neManSAPairIndexIn
            Unsigned32,
        neManSAPairIndexOut
            Unsigned32,
        neManSAPairSPIIn
            Unsigned32,
        neManSAPairSPIOut
            Unsigned32
    }

    neManSAPairAddrType OBJECT-TYPE
        SYNTAX              IPAddressType
        MAX-ACCESS          not-accessible
        STATUS              current
        DESCRIPTION         "(U//FOUO) The address type of the CT Port of the
                            remote INE with which this SA has been established."
        ::= { neManSAPairEntry 1 }

    neManSAPairRemoteCTAddr OBJECT-TYPE
        SYNTAX              IPAddress
        MAX-ACCESS          not-accessible
        STATUS              current
        DESCRIPTION         "(U//FOUO) The address of the CT Port of the remote
                            INE with which this SA has been established."
        ::= { neManSAPairEntry 2 }

    neManSAPairID OBJECT-TYPE
        SYNTAX              Unsigned32
        MAX-ACCESS          not-accessible
        STATUS              current
        DESCRIPTION         "(U//FOUO) The index number to identify this SA
                            pair. The significance and ordering of this number
                            will not reflect on the processing order of lookups
                            within the SAD at all and is merely for management
                            purposes."
        ::= { neManSAPairEntry 3 }

    neManSAPairRemotePTAddr OBJECT-TYPE
        SYNTAX              IPAddress
        MAX-ACCESS          read-only
        STATUS              current
        DESCRIPTION         "(U//FOUO) The address of the PT Port of the remote
                            INE with which this SA has been established."
        ::= { neManSAPairEntry 4 }

    neManSAPairIndexIn OBJECT-TYPE
        SYNTAX              Unsigned32
        MAX-ACCESS          read-only
        STATUS              current
        DESCRIPTION         "(U//FOUO) The index number for the incoming SA
                            entry in the SAD Table for which an SA exists
                            to the Remote CT Address identified in this row.
                            It is a unique numeric index per SA."
        ::= { neManSAPairEntry 5 }

    neManSAPairIndexOut OBJECT-TYPE
        SYNTAX              Unsigned32
        MAX-ACCESS          read-only
        STATUS              current
        DESCRIPTION         "(U//FOUO) The index number for the outgoing SA
                            entry in the SAD Table for which an SA exists
                            to the Remote CT Address identified in this row.
                            It is a unique numeric index per SA."
        ::= { neManSAPairEntry 6 }

    neManSAPairSPIIn OBJECT-TYPE
        SYNTAX              Unsigned32
        MAX-ACCESS          read-only
        STATUS              current
        DESCRIPTION         "(U//FOUO) The SPI for the incoming SAD entry."
        ::= { neManSAPairEntry 7 }

    neManSAPairSPIOut OBJECT-TYPE
        SYNTAX              Unsigned32
        MAX-ACCESS          read-only
        STATUS              current
        DESCRIPTION         "(U//FOUO) The SPI for the outgoing SAD entry."
        ::= { neManSAPairEntry 8 }

    neSaMultipleSas OBJECT IDENTIFIER ::= { neSaNE 10 }

    neSaMultSaInIndex OBJECT-TYPE
        SYNTAX              Unsigned32
        MAX-ACCESS          read-write
        STATUS              current
        DESCRIPTION         "(U//FOUO) The index number of the SA IN row to
                            create multiple SAs from."
        ::= { neSaMultipleSas 1 }

    neSaMultSaOutIndex OBJECT-TYPE
        SYNTAX              Unsigned32
        MAX-ACCESS          read-write
        STATUS              current
        DESCRIPTION         "(U//FOUO) The index number of the SA OUT row to
                            create multiple SAs from."
        ::= { neSaMultipleSas 2 }

    neSaMultSaNumber OBJECT-TYPE
        SYNTAX              Unsigned32
        MAX-ACCESS          read-write
        STATUS              current
        DESCRIPTION         "(U//FOUO) The number of SAs to create."
        ::= { neSaMultipleSas 3 }

    neSaMultSaCreateSas OBJECT-TYPE
        SYNTAX              TruthValue
        MAX-ACCESS          read-write
        STATUS              current
        DESCRIPTION         "(U//FOUO) Setting this object to 'true' will generate
                            the specified number of SAs. When read this object
                            should return false. If this object is set to
                            the same value as the current value, the device
                            must not perform any operation but should accept
                            this as a valid SET operation.
                            
                            (U//FOUO) Note after being set to true, an agent
                            should reset this object to false once the SAs
                            have been created."
        ::= { neSaMultipleSas 4 }

    neSARouteConfigScalars OBJECT IDENTIFIER ::= { neSaNE 11 }

    neSAFailoverEnabled OBJECT-TYPE
        SYNTAX              TruthValue
        MAX-ACCESS          read-write
        STATUS              current
        DESCRIPTION         "(U//FOUO) Defines whether SA failover is enabled."
        ::= { neSARouteConfigScalars 1 }

    neSAConfigScalars OBJECT IDENTIFIER ::= { neSaNE 12 }

    neIkev1SAConfigScalars OBJECT IDENTIFIER ::= { neSAConfigScalars 1 }

    neIKEv1OrphanSaDelay OBJECT-TYPE
        SYNTAX              Unsigned32
        MAX-ACCESS          read-write
        STATUS              current
        DESCRIPTION         "(U//FOUO) The amount of network latency tolerated
                            for SAs."
        ::= { neIkev1SAConfigScalars 1 }

    neStaticRoutes OBJECT IDENTIFIER ::= { neSA 2 }

    --J. Holzhauer Note: DESCRIPTION of the following MIB object updated
    --for GigE/Mini R3.4.
    neDeleteStaticRoutes OBJECT-TYPE
        SYNTAX              TruthValue
        MAX-ACCESS          read-write
        STATUS              current
        DESCRIPTION         "(U//FOUO) This object, when set to TRUE, causes
                            the deletion of all rows (entries) in the hTopologyTable
                            of the HAIPE-NETWORKING-DISCOVERY-MIB module
                            of the HAIPE V3 MIBS having hDiscMethod=3 (manual).
                            Its value is returned to FALSE when all such
                            rows are deleted. When read, it returns a value
                            of FALSE. (U//FOUO) Note that there is no object
                            in the HAIPE-NETWORKING-DISCOVERY-MIB module
                            that allows all rows related of the hTopologyTable
                            to be deleted. An individual row in the hTopologyTable
                            may be deleted by setting its hTopolgyRowStatus
                            variable to 'destroy(6)'."
        ::= { neStaticRoutes 1 }

    neHosts OBJECT IDENTIFIER ::= { neSA 3 }

    neHostTableCount OBJECT-TYPE
        SYNTAX              Integer32
        MAX-ACCESS          read-only
        STATUS              current
        DESCRIPTION         "(U//FOUO) The number of entries in the neHostTable"
        ::= { neHosts 1 }

    neHostTable OBJECT-TYPE
        SYNTAX              SEQUENCE OF NeHostEntry
        MAX-ACCESS          not-accessible
        STATUS              current
        DESCRIPTION         "(U//FOUO) This table is used to display the current
                            entries in the SA Host Table."
        ::= { neHosts 2 }

    neHostEntry OBJECT-TYPE
        SYNTAX              NeHostEntry
        MAX-ACCESS          not-accessible
        STATUS              current
        DESCRIPTION         "(U//FOUO) A row which relates the SA Table Entry
                            to the host."
        INDEX               {
                                neHostSAIndex,
                                neHostAddrType,
                                neHostAddr
                            }
        ::= { neHostTable 1 }

    NeHostEntry ::= SEQUENCE {
        neHostSAIndex
            Unsigned32,
        neHostAddrType
            InetAddressType,
        neHostAddr
            InetAddress,
        neHostDeleteHost
            TruthValue
    }

    neHostSAIndex OBJECT-TYPE
        SYNTAX              Unsigned32
        MAX-ACCESS          not-accessible
        STATUS              current
        DESCRIPTION         "(U//FOUO) The value in hTPSAIndex for the row
                            entry in hTPSATable for the Security Association
                            supporting the connection to this host."
        ::= { neHostEntry 1 }

    neHostAddrType OBJECT-TYPE
        SYNTAX              InetAddressType
        MAX-ACCESS          not-accessible
        STATUS              current
        DESCRIPTION         "(U//FOUO) The type of the host address."
        ::= { neHostEntry 2 }

    neHostAddr OBJECT-TYPE
        SYNTAX              InetAddress
        MAX-ACCESS          not-accessible
        STATUS              current
        DESCRIPTION         "(U//FOUO) The IP address of the Host identified
                            in this row."
        ::= { neHostEntry 3 }

    neHostDeleteHost OBJECT-TYPE
        SYNTAX              TruthValue
        MAX-ACCESS          read-write
        STATUS              current
        DESCRIPTION         "(U//FOUO) When this object is set to TRUE, the
                            INE deletes the Host identified in this row from
                            the SA Host Table. When read, this object returns
                            FALSE."
        ::= { neHostEntry 4 }

    neRoutes OBJECT IDENTIFIER ::= { neSA 4 }

    neDeleteAllRoutes OBJECT-TYPE
        SYNTAX              TruthValue
        MAX-ACCESS          read-write
        STATUS              current
        DESCRIPTION         "(U//FOUO) When set to 'true(1)', this object causes
                            the deletion of all entries in the hTopologyTable
                            of the HAIPE-NETWORKING-DISCOVERY-MIB module
                            of the HAIPE V3 MIBS. When read, it returns a
                            value of false. When set to 'false(2)' this object
                            must not perform any operation but should accept
                            this as a valid SET operation. An individual
                            row in the hTopologyTable may be deleted by setting
                            its hTopolgyRowStatus variable to 'destroy(6)'."
        ::= { neRoutes 1 }

    --J. Holzhauer Note: BEGIN MIB items added for GigE/Mini R3.4
    neSecurityObjects OBJECT IDENTIFIER ::= { neManageObjs 5 }

    neSecurityStatistics OBJECT IDENTIFIER ::= { neSecurityObjects 1 }

    neIPv4SecurityStatistics OBJECT IDENTIFIER ::= { neSecurityStatistics 1 }

    neCtIPv4IcmpPmtuMsgs OBJECT-TYPE
        SYNTAX              Counter32
        MAX-ACCESS          read-only
        STATUS              current
        DESCRIPTION         "(U//FOUO) The number of IPv4 Internet Control
                            Message Protocol (ICMP) PathMTU (PMTU) messages
                            received on the CT interface and indirectly 'passed
                            through' the ECU. This is a 32 bit 'running count'
                            wrap counter that monotonically increases until
                            it reaches its maximum value, when it wraps around
                            and starts increasing again from zero. Discontinuities
                            in the value of this counter normally occur only
                            at re-initialization of the management system,
                            when the value is reset to 0. The value of this
                            counter is NOT reset when retrieved by a network
                            manager."
        ::= { neIPv4SecurityStatistics 1 }

    neCtToPtIPv4IgmpBypassMsgs OBJECT-TYPE
        SYNTAX              Counter32
        MAX-ACCESS          read-only
        STATUS              current
        DESCRIPTION         "(U//FOUO) The number of IPv4 Internet Group Management
                            Protocol (IGMP) messages received on the CT interface
                            and 'passed through' (a.k.a. bypassed, regenerated)
                            the ECU without encryption or decryption (i.e.,
                            will not be 'tunneled' via ESP). This is a 32
                            bit 'running count' wrap counter that monotonically
                            increases until it reaches its maximum value,
                            when it wraps around and starts increasing again
                            from zero. Discontinuities in the value of this
                            counter normally occur only at re-initialization
                            of the management system, when the value is reset
                            to 0. The value of this counter is NOT reset
                            when retrieved by a network manager."
        ::= { neIPv4SecurityStatistics 2 }

    nePtToCtIPv4IgmpBypassMsgs OBJECT-TYPE
        SYNTAX              Counter32
        MAX-ACCESS          read-only
        STATUS              current
        DESCRIPTION         "(U//FOUO) The number of IPv4 Internet Group Management
                            Protocol (IGMP) messages received on the PT interface
                            and 'passed through' (a.k.a. bypassed, regenerated)
                            the ECU without encryption or decryption (i.e.,
                            will not be 'tunneled' via ESP). This is a 32
                            bit 'running count' wrap counter that monotonically
                            increases until it reaches its maximum value,
                            when it wraps around and starts increasing again
                            from zero. Discontinuities in the value of this
                            counter normally occur only at re-initialization
                            of the management system, when the value is reset
                            to 0. management system, when the value is reset
                            to 0. The value of this counter is NOT reset
                            when retrieved by a network manager."
        ::= { neIPv4SecurityStatistics 3 }

    neIPv6SecurityStatistics OBJECT IDENTIFIER ::= { neSecurityStatistics 2 }

    neCtIPv6IcmpPmtuMsgs OBJECT-TYPE
        SYNTAX              Counter32
        MAX-ACCESS          read-only
        STATUS              current
        DESCRIPTION         "(U//FOUO) The number of IPv6 Internet Control
                            Message Protocol (ICMP) Packet Too Big Messages
                            (sometimes also referred to as IPv6 PathMTU (PMTU)
                            messages) received on the CT interface and indirectly
                            'passed through' the ECU. This is a 32 bit 'running
                            count' wrap counter that monotonically increases
                            until it reaches its maximum value, when it wraps
                            around and starts increasing again from zero.
                            Discontinuities in the value of this counter
                            normally occur only at re-initialization of the
                            management system, when the value is reset to
                            0. The value of this counter is NOT reset when
                            retrieved by a network manager."
        ::= { neIPv6SecurityStatistics 1 }

    neCtToPtIPv6MldBypassMsgs OBJECT-TYPE
        SYNTAX              Counter32
        MAX-ACCESS          read-only
        STATUS              current
        DESCRIPTION         "(U//FOUO) The number of IPv6 Multicast Listener
                            Discovery Protocol (MLD) messages received on
                            the PT interface and 'passed through' (a.k.a.
                            bypassed, regenerated) the ECU without encryption
                            or decryption (i.e., will not be 'tunneled' via
                            ESP). This is a 32 bit 'running count' wrap counter
                            that monotonically increases until it reaches
                            its maximum value, when it wraps around and starts
                            increasing again from zero. Discontinuities in
                            the value of this counter normally occur only
                            at re-initialization of the management system,
                            when the value is reset to 0. The value of this
                            counter is NOT reset when retrieved by a network
                            manager."
        ::= { neIPv6SecurityStatistics 2 }

    nePtToCtIPv6MldBypassMsgs OBJECT-TYPE
        SYNTAX              Counter32
        MAX-ACCESS          read-only
        STATUS              current
        DESCRIPTION         "(U//FOUO) The number of IPv6 Multicast Listener
                            Discovery Protocol (MLD) messages received on
                            the PT interface and 'passed through' (a.k.a.
                            bypassed, regenerated) the ECU without encryption
                            or decryption (i.e., will not be 'tunneled' via
                            ESP). This is a 32 bit 'running count' wrap counter
                            that monotonically increases until it reaches
                            its maximum value, when it wraps around and starts
                            increasing again from zero. Discontinuities in
                            the value of this counter normally occur only
                            at re-initialization of the management system,
                            when the value is reset to 0. The value of this
                            counter is NOT reset when retrieved by a network
                            manager."
        ::= { neIPv6SecurityStatistics 3 }

    neESPSecurityStatistics OBJECT IDENTIFIER ::= { neSecurityStatistics 3 }

    neESPPacketIntegrityErrors OBJECT-TYPE
        SYNTAX              Counter32
        MAX-ACCESS          read-only
        STATUS              current
        DESCRIPTION         "(U//FOUO) The number of Encapsulating Security
                            Payload (ESP) Packet Integrity Errors. This object
                            is a single aggregate count of all such errors
                            for all versions of ESP and IP supported by the
                            ECU, and includes Integrity Check Value (ICV)
                            authentication failures. This is a 32 bit 'running
                            count' counter that monotonically increases until
                            it reaches its maximum value. Discontinuities
                            in the value of this counter normally occur only
                            at re-initialization of the management system
                            and when the counter is retrieved by a network
                            manager. In both cases, the value is reset to
                            0."
        ::= { neESPSecurityStatistics 1 }

    --J. Holzhauer Note: TBD if the commonPSEQNError notification and its
    --commonRejectedPSEQN and commonPSEQNRejectCount 'accessible-for-notify'
    --objects defined in the GDC4S-ENCRYPTION-PRODUCTS-COMMON-MIB module
    --are sufficent for GigE/Mini R3.4 PSEQN INITIAL and PSEQN HOURLY
    --audit events.
    --J. Holzhauer Note: END MIB items added for GigE/Mini R3.4
    --J. Holzhauer Note: BEGIN MIB items added for GigE/Mini R3.4
    --
    --Network Encryptor Security Association Information
    --
    --This branch/group provides information about the operational
    --Security Associations (SAs) on the ECU.
    --
    --It includes 'extensions' to Security Association Database (SAD)
    --objects in the HAIPE-TRAFFIC-PROTECTION-MIB module of the HAIPE
    --V3 MIBs.
    neSecurityAssociationInfoObjects OBJECT IDENTIFIER ::= { neManageObjs 6 }

    neSAManagement OBJECT IDENTIFIER
        ::= { neSecurityAssociationInfoObjects 1 }

    neSASummaryStatistics OBJECT IDENTIFIER ::= { neSAManagement 1 }

    neTotalSASummaryStatistics OBJECT IDENTIFIER ::= { neSASummaryStatistics 1 }

    neTotalSACount OBJECT-TYPE
        SYNTAX              Unsigned32
        MAX-ACCESS          read-only
        STATUS              current
        DESCRIPTION         "(U//FOUO) The total number of established Security
                            Associations (SAs) on this ECU. This total includes
                            all SAs that use FIREFLY keys (a.k.a. FIREFLY
                            SAs) and all SAs that use pre-placed keys (PPKs)
                            (a.k.a. PPK SAs). Each SA in this count may represent
                            1 to 4 entries in the hTPSATable due to the incoming/outgoing
                            and current/next SA pairs and quads."
        ::= { neTotalSASummaryStatistics 1 }

    neFireflySASummaryStatistics OBJECT IDENTIFIER ::= { neSASummaryStatistics 2 }

    neTotalFireflySACount OBJECT-TYPE
        SYNTAX              Unsigned32
        MAX-ACCESS          read-only
        STATUS              current
        DESCRIPTION         "(U//FOUO) The total number of established Security
                            Associations (SAs) on this ECU that use FIREFLY
                            keys (a.k.a. FIREFLY SAs). This total includes
                            both of the simplex SAs that make up each duplex
                            channel. Note that an SA is established if and
                            only if it has an associated Traffic Encryption
                            Key (TEK). (U//FOUO) Note that this object is
                            derived from the following MIB objects in this
                            MIB module: neTotalFireflyInCurrentSACount, neTotalFireflyOutCurrentSACount,
                            neTotalFireflyInUpdateSACount, neTotalFireflyOutUpdateSACount"
        ::= { neFireflySASummaryStatistics 1 }

    neTotalFireflyInCurrentSACount OBJECT-TYPE
        SYNTAX              Unsigned32
        MAX-ACCESS          read-only
        STATUS              current
        DESCRIPTION         "(U//FOUO) The total number of established, incoming,
                            uni-directional (a.k.a. simplex) Security Associations
                            (SAs) on this ECU that use current FIREFLY keys.
                            Note that an SA is established if and only if
                            it has an associated Traffic Encryption Key (TEK)."
        ::= { neFireflySASummaryStatistics 2 }

    neTotalFireflyOutCurrentSACount OBJECT-TYPE
        SYNTAX              Unsigned32
        MAX-ACCESS          read-only
        STATUS              current
        DESCRIPTION         "(U//FOUO) The total number of established, outgoing,
                            uni-directional (a.k.a. simplex) Security Associations
                            (SAs) on this ECU that use current FIREFLY keys.
                            Note that an SA is established if and only if
                            it has an associated Traffic Encryption Key (TEK)."
        ::= { neFireflySASummaryStatistics 3 }

    neTotalFireflyInUpdateSACount OBJECT-TYPE
        SYNTAX              Unsigned32
        MAX-ACCESS          read-only
        STATUS              current
        DESCRIPTION         "(U//FOUO) The total number of established, incoming,
                            uni-directional (a.k.a. simplex) Security Associations
                            (SAs) on this ECU that use updated FIREFLY keys.
                            Note that an SA is established if and only if
                            it has an associated Traffic Encryption Key (TEK)."
        ::= { neFireflySASummaryStatistics 4 }

    neTotalFireflyOutUpdateSACount OBJECT-TYPE
        SYNTAX              Unsigned32
        MAX-ACCESS          read-only
        STATUS              current
        DESCRIPTION         "(U//FOUO) The total number of established, outgoing,
                            uni-directional (a.k.a. simplex) Security Associations
                            (SAs) on this ECU that use updated FIREFLY keys.
                            Note that an SA is established if and only if
                            it has an associated Traffic Encryption Key (TEK)."
        ::= { neFireflySASummaryStatistics 5 }

    nePPKSASummaryStatistics OBJECT IDENTIFIER ::= { neSASummaryStatistics 3 }

    neTotalPPKSACount OBJECT-TYPE
        SYNTAX              Unsigned32
        MAX-ACCESS          read-only
        STATUS              current
        DESCRIPTION         "(U//FOUO) The total number of Security Associations
                            (SAs) on this ECU that use pre-placed keys (PPKs)
                            (a.k.a. PPK SAs). This total includes both of
                            the simplex Security Associations that make up
                            each duplex channel. (U//FOUO) Note that this
                            object is derived from the following MIB objects
                            in this MIB module: neTotalPPKInCurrentSACount,
                            neTotalPPKOutCurrentSACount, neTotalPPKInUpdateChangeoverSACount,
                            neTotalPPKOutUpdateChangeoverSACount, neTotalPPKNotEstablishedSACount"
        ::= { nePPKSASummaryStatistics 1 }

    neTotalPPKInCurrentSACount OBJECT-TYPE
        SYNTAX              Unsigned32
        MAX-ACCESS          read-only
        STATUS              current
        DESCRIPTION         "(U//FOUO) The total number of established, incoming,
                            uni-directional (a.k.a. simplex) Security Associations
                            SAs) on this ECU that use current pre-placed
                            keys (PPKs). Note that an SA is established if
                            and only if it has an associated Traffic Encryption
                            Key (TEK)."
        ::= { nePPKSASummaryStatistics 2 }

    neTotalPPKOutCurrentSACount OBJECT-TYPE
        SYNTAX              Unsigned32
        MAX-ACCESS          read-only
        STATUS              current
        DESCRIPTION         "(U//FOUO) The total number of established, outgoing,
                            uni-directional (a.k.a. simplex) Security Associations
                            (SAs) on this ECU that use current pre-placed
                            keys (PPKs). Note that an SA is established if
                            and only if it has an associated Traffic Encryption
                            Key (TEK)."
        ::= { nePPKSASummaryStatistics 3 }

    neTotalPPKInUpdateChangeoverSACount OBJECT-TYPE
        SYNTAX              Unsigned32
        MAX-ACCESS          read-only
        STATUS              current
        DESCRIPTION         "(U//FOUO) The total number of established, incoming,
                            uni-directional (a.k.a. simplex) Security Associations
                            (SAs) on this ECU that use updated and/or changeover
                            pre-placed keys (PPKs). Note that an SA is established
                            if and only if it has an associated Traffic Encryption
                            Key (TEK)."
        ::= { nePPKSASummaryStatistics 4 }

    neTotalPPKOutUpdateChangeoverSACount OBJECT-TYPE
        SYNTAX              Unsigned32
        MAX-ACCESS          read-only
        STATUS              current
        DESCRIPTION         "(U//FOUO) The total number of established, outgoing
                            uni-directional (a.k.a. simplex) Security Associations
                            (SAs) on this ECU that use updated and/or changeover
                            pre-placed keys (PPKs). Note that an SA is established
                            if and only if it has an associated Traffic Encryption
                            Key (TEK)."
        ::= { nePPKSASummaryStatistics 5 }

    neTotalPPKNotEstablishedSACount OBJECT-TYPE
        SYNTAX              Unsigned32
        MAX-ACCESS          read-only
        STATUS              current
        DESCRIPTION         "(U//FOUO) The total number of Security Associations
                            (SAs) on this ECU that use pre-placed keys (PPKs)
                            and are either partially configured and so are
                            not established, or are fully configured but
                            are not yet established. Note that an SA that
                            is not established does NOT have an associated
                            Traffic Encryption Key (TEK)."
        ::= { nePPKSASummaryStatistics 6 }

    neTotalConfiguredPPKSACount OBJECT-TYPE
        SYNTAX              Unsigned32
        MAX-ACCESS          read-only
        STATUS              current
        DESCRIPTION         "(U//FOUO) The total number of configured pre-placed
                            key (PPK) Security Associations (SAs) on this
                            ECU. This total includes all PPK SAs that have
                            been configured but are not necessarily established.
                            Each SA in this count may represent 1 to 4 entries
                            in the hTPSATable due to the incoming/outgoing
                            and current/next SA pairs and quads."
        ::= { nePPKSASummaryStatistics 7 }

    --END neSASummaryStatistics
    --BEGIN neTPSAExtensionTable
    --M. Coughlin: the following is the neTPSAExtensionTable.
    --It was added to allow GigE/Mini to determine extra status
    --information on PPK SAs. It is TBD whether micro will implement
    --this table extension.
    neTPSAExtensionTable OBJECT-TYPE
        SYNTAX              SEQUENCE OF NeTPSAExtensionEntry
        MAX-ACCESS          not-accessible
        STATUS              current
        DESCRIPTION         "(U//FOUO) This table augments th hTPSATable in
                            the HAIPE-Traffic-Protection-MIB."
        ::= { neSAManagement 2 }

    neTPSAExtensionEntry OBJECT-TYPE
        SYNTAX              NeTPSAExtensionEntry
        MAX-ACCESS          not-accessible
        STATUS              current
        DESCRIPTION         "(U//FOUO) A row augmenting a row in the hTPSATable."
        AUGMENTS            {
                                hTPSAEntry
                            }
        ::= { neTPSAExtensionTable 1 }

    NeTPSAExtensionEntry ::= SEQUENCE {
        neTPSAEstablished
            TruthValue,
        neTPSAAutoConfigLocalAddrs
            TruthValue,
        neTPSAAutoCalcSpiAndTime
            TruthValue
    }

    neTPSAEstablished OBJECT-TYPE
        SYNTAX              TruthValue
        MAX-ACCESS          read-only
        STATUS              current
        DESCRIPTION         "(U//FOUO) This object indicates whether or not
                            the Security Association (SA) is fully configured
                            and ready to process traffic. This object returns
                            'true(1)' if the SA is established, and returns
                            'false(2)' if the SA is not established."
        ::= { neTPSAExtensionEntry 1 }

    --20090409 T. Huemiller - DRN MIB00162 Added neTPSAAutoConfigLocalAddrs object.
    neTPSAAutoConfigLocalAddrs OBJECT-TYPE
        SYNTAX              TruthValue
        MAX-ACCESS          read-create
        STATUS              current
        DESCRIPTION         "(U//FOUO) This object, when TRUE, causes the ECU
                            to Auto-Configure the local PT and CT addresses
                            (hTPSALocalCTAddress & hTPSALocalPTAddress) for
                            the Manually-Created, PPK SA represented by this
                            row in the hTPSATable. If this truth-value is
                            true, then any value that is attempted to be
                            set to either or both local address objects (hTPSALocalCTAddress
                            & hTPSALocalPTAddress) is ignored. (U//FOUO)
                            If the PT or CT local IP address is left un-set
                            by the manager during the creation of a manual
                            PPK SA, this object will default to a value of
                            TRUE and the local IP addresses of this SA will
                            be auto-configured. (U//FOUO) When the hTPSATable
                            row is set, it must have the same value for this
                            object as any associated SA's identified in the
                            neSACTSortedTable (Current SA pairs or Current/Next
                            SA double-pairs). (U//FOUO) When read, this object
                            is TRUE if the associated SA was configured using
                            Auto-Configuration to create the Local CT and
                            PT interface IP addresses. (U//FOUO)This object
                            is FALSE for all other rows in the hTPSATable."
        DEFVAL              { false }
        ::= { neTPSAExtensionEntry 2 }

    --20090413 - T. Huemiller - DRN MIB00167 - Auto-Calculate Flag for PPK SA.
    neTPSAAutoCalcSpiAndTime OBJECT-TYPE
        SYNTAX              TruthValue
        MAX-ACCESS          read-create
        STATUS              current
        DESCRIPTION         "(U//FOUO) This object, when TRUE, causes the ECU
                            to automatically calculate values for the hTPSASPI,
                            hTPSAStartTime and hTPSAEndTime for the Manually-Created,
                            PPK SA represented by this row in the hTPSATable.
                            If this truth-value is true, then any value that
                            is attempted to be set to any of these three
                            Auto-Calculated objects is ignored. (U//FOUO)
                            When the hTPSATable row is set, it must have
                            the same value for this object as any associated
                            SA's identified in the neSACTSortedTable (Current
                            SA pairs or Current/Next SA double-pairs). (U//FOUO)
                            When read, this object is TRUE if the associated
                            SA was configured using Auto-Calculation to create
                            the SPI, Start Time and End Time of the associated
                            SA. (U//FOUO) This object is FALSE for all other
                            rows in the hTPSATable."
        DEFVAL              { false }
        ::= { neTPSAExtensionEntry 3 }

    neIpPDUObjects OBJECT IDENTIFIER ::= { neManageObjs 7 }

    neIpPDUStatistics OBJECT IDENTIFIER ::= { neIpPDUObjects 1 }

    neDropCntPTInPTCTProc OBJECT-TYPE
        SYNTAX              Counter32
        MAX-ACCESS          read-only
        STATUS              current
        DESCRIPTION         "(U//FOUO) The number of input IP datagrams received
                            on the plain text side that were discarded by
                            the PT and CT processor."
        ::= { neIpPDUStatistics 1 }

    neDropCntPTOutPTCTProc OBJECT-TYPE
        SYNTAX              Counter32
        MAX-ACCESS          read-only
        STATUS              current
        DESCRIPTION         "(U//FOUO) The number of output IP datagrams being
                            sent out the plain text side that were discarded
                            by the PT and CT processor."
        ::= { neIpPDUStatistics 2 }

    neDropCntCTInPTCTProc OBJECT-TYPE
        SYNTAX              Counter32
        MAX-ACCESS          read-only
        STATUS              current
        DESCRIPTION         "(U//FOUO) The number of input IP datagrams received
                            by the cypher text side that were discarded by
                            the PT and CT processor."
        ::= { neIpPDUStatistics 3 }

    neDropCntCTOutPTCTProc OBJECT-TYPE
        SYNTAX              Counter32
        MAX-ACCESS          read-only
        STATUS              current
        DESCRIPTION         "(U//FOUO) The number of output IP datagrams being
                            sent out the cypher text side that were discarded
                            by the PT and CT processor."
        ::= { neIpPDUStatistics 4 }

    neDropCntPTInFastpathIFMgr OBJECT-TYPE
        SYNTAX              Counter32
        MAX-ACCESS          read-only
        STATUS              current
        DESCRIPTION         "(U//FOUO) The number of input IP datagrams received
                            by the plain text side that were discarded by
                            the fastpath interface manager."
        ::= { neIpPDUStatistics 5 }

    neDropCntPTOutFastpathIFMgr OBJECT-TYPE
        SYNTAX              Counter32
        MAX-ACCESS          read-only
        STATUS              current
        DESCRIPTION         "(U//FOUO) The number of output IP datagrams being
                            sent out the plain text side that were discarded
                            by the fastpath interface manager."
        ::= { neIpPDUStatistics 6 }

    neDropCntCTInFastpathIFMgr OBJECT-TYPE
        SYNTAX              Counter32
        MAX-ACCESS          read-only
        STATUS              current
        DESCRIPTION         "(U//FOUO) The number of input IP datagrams received
                            by the cypher text side that were discarded by
                            the fastpath interface manager."
        ::= { neIpPDUStatistics 7 }

    neDropCntCTOutFastpathIFMgr OBJECT-TYPE
        SYNTAX              Counter32
        MAX-ACCESS          read-only
        STATUS              current
        DESCRIPTION         "(U//FOUO) The number of output IP datagrams being
                            sent out the cypher text side that were discarded
                            by the fastpath interface manager."
        ::= { neIpPDUStatistics 8 }

    neDropCntPTInBufferUtilities OBJECT-TYPE
        SYNTAX              Counter32
        MAX-ACCESS          read-only
        STATUS              current
        DESCRIPTION         "(U//FOUO) The number of input IP datagrams received
                            by the plain text side that were discarded by
                            buffer utilities."
        ::= { neIpPDUStatistics 9 }

    neDropCntPTOutBufferUtilities OBJECT-TYPE
        SYNTAX              Counter32
        MAX-ACCESS          read-only
        STATUS              current
        DESCRIPTION         "(U//FOUO) The number of output IP datagrams being
                            sent out the plain text side that were discarded
                            by buffer utilities."
        ::= { neIpPDUStatistics 10 }

    neDropCntCTInBufferUtilities OBJECT-TYPE
        SYNTAX              Counter32
        MAX-ACCESS          read-only
        STATUS              current
        DESCRIPTION         "(U//FOUO) The number of input IP datagrams received
                            by the cypher text side that were discarded by
                            buffer utilities."
        ::= { neIpPDUStatistics 11 }

    neDropCntCTOutBufferUtilities OBJECT-TYPE
        SYNTAX              Counter32
        MAX-ACCESS          read-only
        STATUS              current
        DESCRIPTION         "(U//FOUO) The number of output IP datagrams being
                            sent out the cypher text side that were discarded
                            by buffer utilities."
        ::= { neIpPDUStatistics 12 }

    neDropCntPTInReassemMgr OBJECT-TYPE
        SYNTAX              Counter32
        MAX-ACCESS          read-only
        STATUS              current
        DESCRIPTION         "(U//FOUO) The number of input IP datagrams received
                            by the plain text side that were discarded by
                            the reassembly manager."
        ::= { neIpPDUStatistics 13 }

    neDropCntPTOutReassemMgr OBJECT-TYPE
        SYNTAX              Counter32
        MAX-ACCESS          read-only
        STATUS              current
        DESCRIPTION         "(U//FOUO) The number of output IP datagrams being
                            sent out the plain text side that were discarded
                            by the reassembly manager."
        ::= { neIpPDUStatistics 14 }

    neDropCntCTInReassemMgr OBJECT-TYPE
        SYNTAX              Counter32
        MAX-ACCESS          read-only
        STATUS              current
        DESCRIPTION         "(U//FOUO) The number of input IP datagrams received
                            by the cypher text side that were discarded by
                            the reassembly manager."
        ::= { neIpPDUStatistics 15 }

    neDropCntCTOutReassemMgr OBJECT-TYPE
        SYNTAX              Counter32
        MAX-ACCESS          read-only
        STATUS              current
        DESCRIPTION         "(U//FOUO) The number of output IP datagrams being
                            sent out the cypher text side that were discarded
                            by the reassembly manager."
        ::= { neIpPDUStatistics 16 }

    neDropCntPTInSPIFMgr OBJECT-TYPE
        SYNTAX              Counter32
        MAX-ACCESS          read-only
        STATUS              current
        DESCRIPTION         "(U//FOUO) The number of input IP datagrams received
                            by the plain text side that were discarded by
                            the SP interface manager."
        ::= { neIpPDUStatistics 17 }

    neDropCntPTOutSPIFMgr OBJECT-TYPE
        SYNTAX              Counter32
        MAX-ACCESS          read-only
        STATUS              current
        DESCRIPTION         "(U//FOUO) The number of output IP datagrams being
                            sent by the plain text side that were discarded
                            by the SP interface manager."
        ::= { neIpPDUStatistics 18 }

    neDropCntCTInSPIFMgr OBJECT-TYPE
        SYNTAX              Counter32
        MAX-ACCESS          read-only
        STATUS              current
        DESCRIPTION         "(U//FOUO) The number of input IP datagrams received
                            by the cypher text side that were discarded by
                            the SP interface manager."
        ::= { neIpPDUStatistics 19 }

    neDropCntCTOutSPIFMgr OBJECT-TYPE
        SYNTAX              Counter32
        MAX-ACCESS          read-only
        STATUS              current
        DESCRIPTION         "(U//FOUO) The number of output IP datagrams being
                            sent by the cypher text side that were discarded
                            by the SP interface manager."
        ::= { neIpPDUStatistics 20 }

    neDropCntPTInPTCTNIDMgr OBJECT-TYPE
        SYNTAX              Counter32
        MAX-ACCESS          read-only
        STATUS              current
        DESCRIPTION         "(U//FOUO) The number of input IP datagrams received
                            by the plain text side that were discarded by
                            the PT and CT NID manager."
        ::= { neIpPDUStatistics 21 }

    neDropCntPTOutPTCTNIDMgr OBJECT-TYPE
        SYNTAX              Counter32
        MAX-ACCESS          read-only
        STATUS              current
        DESCRIPTION         "(U//FOUO) The number of output IP datagrams being
                            sent by the plain text side that were discarded
                            by the PT and CT NID manager."
        ::= { neIpPDUStatistics 22 }

    neDropCntCTInPTCTNIDMgr OBJECT-TYPE
        SYNTAX              Counter32
        MAX-ACCESS          read-only
        STATUS              current
        DESCRIPTION         "(U//FOUO) The number of input IP datagrams received
                            by the cypher text side that were discarded by
                            the PT and CT NID manager."
        ::= { neIpPDUStatistics 23 }

    neDropCntCTOutPTCTNIDMgr OBJECT-TYPE
        SYNTAX              Counter32
        MAX-ACCESS          read-only
        STATUS              current
        DESCRIPTION         "(U//FOUO) The number of output IP datagrams being
                            sent by the cypher text side that were discarded
                            by the PT and CT NID manager."
        ::= { neIpPDUStatistics 24 }

    neDropCntPTInIPStack OBJECT-TYPE
        SYNTAX              Counter32
        MAX-ACCESS          read-only
        STATUS              current
        DESCRIPTION         "(U//FOUO) The number of input IP datagrams received
                            by the plain text side that were discarded by
                            the IP stack."
        ::= { neIpPDUStatistics 25 }

    neDropCntPTOutIPStack OBJECT-TYPE
        SYNTAX              Counter32
        MAX-ACCESS          read-only
        STATUS              current
        DESCRIPTION         "(U//FOUO) The number of output IP datagrams being
                            sent by the plain text side that were discarded
                            by the IP stack."
        ::= { neIpPDUStatistics 26 }

    neDropCntCTInIPStack OBJECT-TYPE
        SYNTAX              Counter32
        MAX-ACCESS          read-only
        STATUS              current
        DESCRIPTION         "(U//FOUO) The number of input IP datagrams received
                            by the cypher text side that were discarded by
                            the IP stack."
        ::= { neIpPDUStatistics 27 }

    neDropCntCTOutIPStack OBJECT-TYPE
        SYNTAX              Counter32
        MAX-ACCESS          read-only
        STATUS              current
        DESCRIPTION         "(U//FOUO) The number of output IP datagrams being
                            sent by the cypher text side that were discarded
                            by the IP stack."
        ::= { neIpPDUStatistics 28 }

    neDropCntPTInAddrConfigMgr OBJECT-TYPE
        SYNTAX              Counter32
        MAX-ACCESS          read-only
        STATUS              current
        DESCRIPTION         "(U//FOUO) The number of input IP datagrams received
                            by the plain text side that were discarded by
                            the Address Configuration manager."
        ::= { neIpPDUStatistics 29 }

    neDropCntPTOutAddrConfigMgr OBJECT-TYPE
        SYNTAX              Counter32
        MAX-ACCESS          read-only
        STATUS              current
        DESCRIPTION         "(U//FOUO) The number of output IP datagrams being
                            sent by the plain text side that were discarded
                            by the Address Configuration manager."
        ::= { neIpPDUStatistics 30 }

    neDropCntCTInAddrConfigMgr OBJECT-TYPE
        SYNTAX              Counter32
        MAX-ACCESS          read-only
        STATUS              current
        DESCRIPTION         "(U//FOUO) The number of input IP datagrams received
                            by the cypher text side that were discarded by
                            the Address Configuration manager."
        ::= { neIpPDUStatistics 31 }

    neDropCntCTOutAddrConfigMgr OBJECT-TYPE
        SYNTAX              Counter32
        MAX-ACCESS          read-only
        STATUS              current
        DESCRIPTION         "(U//FOUO) The number of output IP datagrams being
                            sent by the cypher text side that were discarded
                            by the Address Configuration manager."
        ::= { neIpPDUStatistics 32 }

    neDropCntPTInMulticastGroupMgr OBJECT-TYPE
        SYNTAX              Counter32
        MAX-ACCESS          read-only
        STATUS              current
        DESCRIPTION         "(U//FOUO) The number of input IP datagrams received
                            by the plain text side that were discarded by
                            the Multicast Group manager."
        ::= { neIpPDUStatistics 33 }

    neDropCntPTOutMulticastGroupMgr OBJECT-TYPE
        SYNTAX              Counter32
        MAX-ACCESS          read-only
        STATUS              current
        DESCRIPTION         "(U//FOUO) The number of output IP datagrams being
                            sent by the plain text side that were discarded
                            by the Multicast Group manager."
        ::= { neIpPDUStatistics 34 }

    neDropCntCTInMulticastGroupMgr OBJECT-TYPE
        SYNTAX              Counter32
        MAX-ACCESS          read-only
        STATUS              current
        DESCRIPTION         "(U//FOUO) The number of input IP datagrams received
                            by the cypher text side that were discarded by
                            the Multicast Group manager."
        ::= { neIpPDUStatistics 35 }

    neDropCntCTOutMulticastGroupMgr OBJECT-TYPE
        SYNTAX              Counter32
        MAX-ACCESS          read-only
        STATUS              current
        DESCRIPTION         "(U//FOUO) The number of output IP datagrams being
                            sent by the cypher text side that were discarded
                            by the Multicast Group manager."
        ::= { neIpPDUStatistics 36 }

    neDropCntPTInTFTP OBJECT-TYPE
        SYNTAX              Counter32
        MAX-ACCESS          read-only
        STATUS              current
        DESCRIPTION         "(U//FOUO) The number of input IP datagrams received
                            by the plain text side that were discarded by
                            the TFTP Provider."
        ::= { neIpPDUStatistics 37 }

    neDropCntPTOutTFTP OBJECT-TYPE
        SYNTAX              Counter32
        MAX-ACCESS          read-only
        STATUS              current
        DESCRIPTION         "(U//FOUO) The number of output IP datagrams being
                            sent by the plain text side that were discarded
                            by the TFTP Provider."
        ::= { neIpPDUStatistics 38 }

    neDropCntCTInTFTP OBJECT-TYPE
        SYNTAX              Counter32
        MAX-ACCESS          read-only
        STATUS              current
        DESCRIPTION         "(U//FOUO) The number of input IP datagrams received
                            by the cypher text side that were discarded by
                            the TFTP Provider."
        ::= { neIpPDUStatistics 39 }

    neDropCntCTOutTFTP OBJECT-TYPE
        SYNTAX              Counter32
        MAX-ACCESS          read-only
        STATUS              current
        DESCRIPTION         "(U//FOUO) The number of output IP datagrams being
                            sent by the cypher text side that were discarded
                            by the TFTP Provider."
        ::= { neIpPDUStatistics 40 }

    neDropCntInSNMPAgent OBJECT-TYPE
        SYNTAX              Counter32
        MAX-ACCESS          read-only
        STATUS              current
        DESCRIPTION         "(U//FOUO) The number of input IP datagrams received
                            that were discarded by the SNMP Agent."
        ::= { neIpPDUStatistics 41 }

    neDropCntCTInIKEMgr OBJECT-TYPE
        SYNTAX              Counter32
        MAX-ACCESS          read-only
        STATUS              current
        DESCRIPTION         "(U//FOUO) The number of input IP datagrams received
                            by the cypher text side that were discarded by
                            the IKE manager."
        ::= { neIpPDUStatistics 42 }

    neDropCntCTInISAKMPServer OBJECT-TYPE
        SYNTAX              Counter32
        MAX-ACCESS          read-only
        STATUS              current
        DESCRIPTION         "(U//FOUO) The number of input IP datagrams received
                            by the cypher text side that were discarded by
                            the ISAKMP server."
        ::= { neIpPDUStatistics 43 }

    neDropCntCTOutISAKMPServer OBJECT-TYPE
        SYNTAX              Counter32
        MAX-ACCESS          read-only
        STATUS              current
        DESCRIPTION         "(U//FOUO) The number of output IP datagrams being
                            sent by the cypher text side that were discarded
                            by the ISAKMP server."
        ::= { neIpPDUStatistics 44 }

    neDropCntCTInISAKMPMgr OBJECT-TYPE
        SYNTAX              Counter32
        MAX-ACCESS          read-only
        STATUS              current
        DESCRIPTION         "(U//FOUO) The number of input IP datagrams received
                            by the cypher text side that were discarded by
                            the ISAKMP manager."
        ::= { neIpPDUStatistics 45 }

    neDropCntCTOutESP OBJECT-TYPE
        SYNTAX              Counter32
        MAX-ACCESS          read-only
        STATUS              current
        DESCRIPTION         "(U//FOUO) The number of output IP datagrams being
                            sent by the cypher text side that were discarded
                            by the ESP."
        ::= { neIpPDUStatistics 46 }

    neDropCntCTInSDDMgr OBJECT-TYPE
        SYNTAX              Counter32
        MAX-ACCESS          read-only
        STATUS              current
        DESCRIPTION         "(U//FOUO) The number of input IP datagrams received
                            by the cypher text side that were discarded by
                            the SDD manager."
        ::= { neIpPDUStatistics 47 }

    neDropCntCTOutSDDMgr OBJECT-TYPE
        SYNTAX              Counter32
        MAX-ACCESS          read-only
        STATUS              current
        DESCRIPTION         "(U//FOUO) The number of output IP datagrams being
                            sent by the cypher text side that were discarded
                            by the SDD manager."
        ::= { neIpPDUStatistics 48 }

    neDropCntCTInSDDServer OBJECT-TYPE
        SYNTAX              Counter32
        MAX-ACCESS          read-only
        STATUS              current
        DESCRIPTION         "(U//FOUO) The number of input IP datagrams received
                            by the cypher text side that were discarded by
                            the SDD server."
        ::= { neIpPDUStatistics 49 }

    neDropCntCTOutSDDServer OBJECT-TYPE
        SYNTAX              Counter32
        MAX-ACCESS          read-only
        STATUS              current
        DESCRIPTION         "(U//FOUO) The number of output IP datagrams being
                            sent by the cypher text side that were discarded
                            by the SDD server."
        ::= { neIpPDUStatistics 50 }

    neDropCntPTInGDCMgr OBJECT-TYPE
        SYNTAX              Counter32
        MAX-ACCESS          read-only
        STATUS              current
        DESCRIPTION         "(U//FOUO) The number of input IP datagrams received
                            by the plain text side that were discarded by
                            the GDC manager."
        ::= { neIpPDUStatistics 51 }

    neDropCntPTOutGDCMgr OBJECT-TYPE
        SYNTAX              Counter32
        MAX-ACCESS          read-only
        STATUS              current
        DESCRIPTION         "(U//FOUO) The number of output IP datagrams being
                            sent by the plain text side that were discarded
                            by the GDC manager."
        ::= { neIpPDUStatistics 52 }

    neDropCntCTInGDCMgr OBJECT-TYPE
        SYNTAX              Counter32
        MAX-ACCESS          read-only
        STATUS              current
        DESCRIPTION         "(U//FOUO) The number of input IP datagrams received
                            by the cypher text side that were discarded by
                            the GDC manager."
        ::= { neIpPDUStatistics 53 }

    neDropCntCTOutGDCMgr OBJECT-TYPE
        SYNTAX              Counter32
        MAX-ACCESS          read-only
        STATUS              current
        DESCRIPTION         "(U//FOUO) The number of output IP datagrams being
                            sent by the cypher text side that were discarded
                            by the GDC manager."
        ::= { neIpPDUStatistics 54 }

    neDropCntPTInGDCServer OBJECT-TYPE
        SYNTAX              Counter32
        MAX-ACCESS          read-only
        STATUS              current
        DESCRIPTION         "(U//FOUO) The number of input IP datagrams received
                            by the plain text side that were discarded by
                            the GDC server."
        ::= { neIpPDUStatistics 55 }

    neDropCntPTOutGDCServer OBJECT-TYPE
        SYNTAX              Counter32
        MAX-ACCESS          read-only
        STATUS              current
        DESCRIPTION         "(U//FOUO) The number of output IP datagrams being
                            sent by the plain text side that were discarded
                            by the GDC server."
        ::= { neIpPDUStatistics 56 }

    neDropCntCTInGDCServer OBJECT-TYPE
        SYNTAX              Counter32
        MAX-ACCESS          read-only
        STATUS              current
        DESCRIPTION         "(U//FOUO) The number of input IP datagrams received
                            by the cypher text side that were discarded by
                            the GDC server."
        ::= { neIpPDUStatistics 57 }

    neDropCntCTOutGDCServer OBJECT-TYPE
        SYNTAX              Counter32
        MAX-ACCESS          read-only
        STATUS              current
        DESCRIPTION         "(U//FOUO) The number of output IP datagrams being
                            sent by the cypher text side that were discarded
                            by the GDC server."
        ::= { neIpPDUStatistics 58 }

    neDropCntPTInRIPMgr OBJECT-TYPE
        SYNTAX              Counter32
        MAX-ACCESS          read-only
        STATUS              current
        DESCRIPTION         "(U//FOUO) The number of input IP datagrams received
                            by the plain text side that were discarded by
                            the RIP manager."
        ::= { neIpPDUStatistics 59 }

    neDropCntPTInRIPServer OBJECT-TYPE
        SYNTAX              Counter32
        MAX-ACCESS          read-only
        STATUS              current
        DESCRIPTION         "(U//FOUO) The number of input IP datagrams received
                            by the plain text side that were discarded by
                            the RIP server."
        ::= { neIpPDUStatistics 60 }

    neDropCntPTOutRIPServer OBJECT-TYPE
        SYNTAX              Counter32
        MAX-ACCESS          read-only
        STATUS              current
        DESCRIPTION         "(U//FOUO) The number of output IP datagrams being
                            sent by the plain text side that were discarded
                            by the RIP server."
        ::= { neIpPDUStatistics 61 }

    neDropCntPTInDMCoordinator OBJECT-TYPE
        SYNTAX              Counter32
        MAX-ACCESS          read-only
        STATUS              current
        DESCRIPTION         "(U//FOUO) The number of input IP datagrams received
                            by the plain text side that were discarded by
                            the DM Coordinator."
        ::= { neIpPDUStatistics 62 }

    neDropCntPTOutDMCoordinator OBJECT-TYPE
        SYNTAX              Counter32
        MAX-ACCESS          read-only
        STATUS              current
        DESCRIPTION         "(U//FOUO) The number of output IP datagrams being
                            sent by the plain text side that were discarded
                            by the DM Coordinator."
        ::= { neIpPDUStatistics 63 }

    neDropCntCTInDMCoordinator OBJECT-TYPE
        SYNTAX              Counter32
        MAX-ACCESS          read-only
        STATUS              current
        DESCRIPTION         "(U//FOUO) The number of input IP datagrams received
                            by the cypher text side that were discarded by
                            the DM Coordinator."
        ::= { neIpPDUStatistics 64 }

    neDropCntCTOutDMCoordinator OBJECT-TYPE
        SYNTAX              Counter32
        MAX-ACCESS          read-only
        STATUS              current
        DESCRIPTION         "(U//FOUO) The number of output IP datagrams being
                            sent by the cypher text side that were discarded
                            by the DM Coordinator."
        ::= { neIpPDUStatistics 65 }

    neDropCntCCCESPAuthError OBJECT-TYPE
        SYNTAX              Counter32
        MAX-ACCESS          read-only
        STATUS              current
        DESCRIPTION         "(U//FOUO) The number of IP datagrams received
                            that were discarded by the CCC due to ESP authentication
                            errors."
        ::= { neIpPDUStatistics 66 }

    neErrorCntCCCOther OBJECT-TYPE
        SYNTAX              Counter32
        MAX-ACCESS          read-only
        STATUS              current
        DESCRIPTION         "(U//FOUO) The number of errors resulting from
                            datagrams being processed by the CCC. These errors
                            result in IP datagrams being droppped. These
                            errors do not necessarily reflect a one to one
                            count to discarded IP datagrams and therefore
                            cannot be considered a drop count."
        ::= { neIpPDUStatistics 67 }

    neDropCntCTInSAC OBJECT-TYPE
        SYNTAX              Counter32
        MAX-ACCESS          read-only
        STATUS              current
        DESCRIPTION         "(U//FOUO) The number of input IP datagrams received
                            by the cypher text side that were discarded by
                            the Security Association Controler."
        ::= { neIpPDUStatistics 68 }

    neDropCntCTOutSAC OBJECT-TYPE
        SYNTAX              Counter32
        MAX-ACCESS          read-only
        STATUS              current
        DESCRIPTION         "(U//FOUO) The number of output IP datagrams being
                            sent by the cypher text side that were discarded
                            by the Security Association Controler."
        ::= { neIpPDUStatistics 69 }

    neIF OBJECT IDENTIFIER ::= { neManageObjs 8 }

    neIFMauExtensions OBJECT IDENTIFIER ::= { neIF 1 }

    neIFMauExtensionTable OBJECT-TYPE
        SYNTAX              SEQUENCE OF NeIFMauExtensionEntry
        MAX-ACCESS          not-accessible
        STATUS              deprecated
        DESCRIPTION         "(U//FOUO) A table containing additional configuration
                            items for the link-layer interfaces. This table
                            augments the ifMauTable in the MAU-MIB."
        ::= { neIFMauExtensions 1 }

    neIFMauExtensionEntry OBJECT-TYPE
        SYNTAX              NeIFMauExtensionEntry
        MAX-ACCESS          not-accessible
        STATUS              deprecated
        DESCRIPTION         "(U//FOUO) An entry containing additional management
                            information applicable to a particular interface."
        AUGMENTS            {
                                ifMauEntry
                            }
        ::= { neIFMauExtensionTable 1 }

    NeIFMauExtensionEntry ::= SEQUENCE {
        neIFMauRole
            INTEGER
    }

    neIFMauRole OBJECT-TYPE
        SYNTAX              INTEGER {
                                master( 1 ),
                                slave( 2 )
                            }
        MAX-ACCESS          read-write
        STATUS              deprecated
        DESCRIPTION         "(U//FOUO) This object defines the master or slave
                            role of the interface. This object only has meaning
                            when the interface is configurable as master
                            or slave."
        ::= { neIFMauExtensionEntry 1 }

    --MIB00178 - 20090928 - Add IF-MIB extension table to NE-MIB
    --
    neIFTableExtension OBJECT IDENTIFIER ::= { neIF 2 }

    neIFTableExtTable OBJECT-TYPE
        SYNTAX              SEQUENCE OF NeIFTableExtEntry
        MAX-ACCESS          not-accessible
        STATUS              current
        DESCRIPTION         "(U//FOUO) This table extends the IETF Standard
                            IF-MIB to identify the local interface and remote
                            interface capabilities and the negotiated capability
                            (autonegotiated speed and mode) of the interface
                            associated with the IF row."
        ::= { neIFTableExtension 1 }

    neIFTableExtEntry OBJECT-TYPE
        SYNTAX              NeIFTableExtEntry
        MAX-ACCESS          not-accessible
        STATUS              current
        DESCRIPTION         "(U//FOUO) A row extending a row in the IFTable
                            of the IF-MIB."
        AUGMENTS            {
                                ifEntry
                            }
        ::= { neIFTableExtTable 1 }

    NeIFTableExtEntry ::= SEQUENCE {
        neIFTableMedium
            INTEGER,
        neIFTableLocalCapabilities
            NeIFSpeedMode,
        neIFTableRemoteCapabilities
            NeIFSpeedMode,
        neIFTableNegotiatedCapability
            NeIFSpeedMode,
        neIFTableLinkLayerSetting
            INTEGER,
        neIFTableExtARPCacheClear
            TruthValue,
        neIFTableInterfaceAssignment
            INTEGER,
        neIFTableSfpModule
            INTEGER,
        neIFTablePhysicalInterface
            INTEGER
    }

    neIFTableMedium OBJECT-TYPE
        SYNTAX              INTEGER {
                                copper( 1 ),
                                fiber( 2 )
                            }
        MAX-ACCESS          read-write
        STATUS              current
        DESCRIPTION         "(U//FOUO) This object configures and identifies
                            the transmission medium of this interface."
        ::= { neIFTableExtEntry 1 }

    neIFTableLocalCapabilities OBJECT-TYPE
        SYNTAX              NeIFSpeedMode {
                                type10Mps-HD( 0 ),
                                type10Mbps-FD( 1 ),
                                type100Mbps-HD( 2 ),
                                type100Mbps-FD( 3 ),
                                type1000Mbps-HD( 4 ),
                                type1000Mbps-FD( 5 ),
                                type10Gbps-FD( 6 )
                            }
        MAX-ACCESS          read-write
        STATUS              current
        DESCRIPTION         "(U//FOUO) The speed and mode capabilities of this
                            local interface."
        ::= { neIFTableExtEntry 2 }

    neIFTableRemoteCapabilities OBJECT-TYPE
        SYNTAX              NeIFSpeedMode {
                                type10Mps-HD( 0 ),
                                type10Mbps-FD( 1 ),
                                type100Mbps-HD( 2 ),
                                type100Mbps-FD( 3 ),
                                type1000Mbps-HD( 4 ),
                                type1000Mbps-FD( 5 ),
                                type10Gbps-FD( 6 )
                            }
        MAX-ACCESS          read-only
        STATUS              current
        DESCRIPTION         "(U//FOUO) The speed and mode capabilities of the
                            remote interface connecting to this local interface."
        ::= { neIFTableExtEntry 3 }

    neIFTableNegotiatedCapability OBJECT-TYPE
        SYNTAX              NeIFSpeedMode {
                                type10Mps-HD( 0 ),
                                type10Mbps-FD( 1 ),
                                type100Mbps-HD( 2 ),
                                type100Mbps-FD( 3 ),
                                type1000Mbps-HD( 4 ),
                                type1000Mbps-FD( 5 ),
                                type10Gbps-FD( 6 )
                            }
        MAX-ACCESS          read-only
        STATUS              current
        DESCRIPTION         "(U//FOUO) The speed and mode capability that has
                            been negotiated by the local interface and the
                            connected remote interface."
        ::= { neIFTableExtEntry 4 }

    neIFTableLinkLayerSetting OBJECT-TYPE
        SYNTAX              INTEGER {
                                autoNegotiate( 1 ),
                                type10Mbps-HD( 2 ),
                                type10Mbps-FD( 3 ),
                                type100Mbps-HD( 4 ),
                                type100Mbps-FD( 5 ),
                                type1000Mbps-HD( 6 ),
                                type1000Mbps-FD( 7 ),
                                type10Gbps-FD( 8 )
                            }
        MAX-ACCESS          read-write
        STATUS              current
        DESCRIPTION         "(U//FOUO)This object identifies the interface
                            Speed and Mode, to be used in conjunction with
                            the interface medium denoted by neIFTableMedium.
                            This object represents the administratively-configured
                            Speed and Mode of the interface. If this object
                            is not SET to auto-negotiation, the value of
                            this object determines the Speed and Mode of
                            the interface. In this case, a SET to this object
                            will force the interface into the specified Speed
                            and Mode. If auto-negotiation is implemented
                            and enabled for this interface, the Speed and
                            Mode of the interface is determined by auto-negotiation.
                            If auto-negotiation is not implemented for this
                            interface, a SET to auto-negotiate will be rejected."
        ::= { neIFTableExtEntry 5 }

    neIFTableExtARPCacheClear OBJECT-TYPE
        SYNTAX              TruthValue
        MAX-ACCESS          read-write
        STATUS              current
        DESCRIPTION         "(U//FOUO) Setting this object to 'true' will clear
                            all the interface ARP Cache. When read this object
                            should return its value. If this object is set
                            to the same value as the current value, the device
                            must not perform any operation but should accept
                            this as a valid SET operation. Once the value
                            is set to true, attempts to set it back to false
                            will return an inconsistentValue error."
        ::= { neIFTableExtEntry 6 }

    neIFTableInterfaceAssignment OBJECT-TYPE
        SYNTAX              INTEGER {
                                user( 1 ),
                                sensor( 2 )
                            }
        MAX-ACCESS          read-only
        STATUS              current
        DESCRIPTION         "(U//FOUO) This object is how each of physical
                            interfaces are used. In specific modes of operation,
                            the ECU may need to use more than just two interfaces,
                            and this object labels each port and how it is
                            used.
                            
                            (U//FOUO) (1) hAIPE: This is the interface that
                            is used for HAIPE traffic. (2) sensor: This is
                            the interface that will be used for other purposes
                            other than HAIPE traffic. NO HAIPE traffic will
                            flow through this interface when sensor is selected!"
        ::= { neIFTableExtEntry 7 }

    neIFTableSfpModule OBJECT-TYPE
        SYNTAX              INTEGER {
                                none( 0 ),
                                enhancedReachSingleMode( 1 ),
                                longReachMultiMode( 2 ),
                                longReachSingleMode( 3 ),
                                shortReachMultiMode( 4 ),
                                notSupported( 255 )
                            }
        MAX-ACCESS          read-only
        STATUS              current
        DESCRIPTION         "(U//FOUO)This object identifies the interface
                            SFP's Module."
        ::= { neIFTableExtEntry 8 }

    -- unofficial definition (CHIMERA Team)
    neIFTablePhysicalInterface OBJECT-TYPE
        SYNTAX              INTEGER {
                                fiber1( 1 ),
                                fiber2( 2 ),
                                copper( 3 )
                            }
        MAX-ACCESS          read-write
        STATUS              current
        DESCRIPTION         "(U//FOUO)This object identifies the physical
                            interface."
        ::= { neIFTableExtEntry 9 }

    neIFObjects OBJECT IDENTIFIER ::= { neIF 3 }

    neIFOpticalMode OBJECT-TYPE
        SYNTAX              INTEGER {
                                singleMode( 1 ),
                                multiMode( 2 )
                            }
        MAX-ACCESS          read-only
        STATUS              current
        DESCRIPTION         "(U//FOUO) This object indicates if the device's
                            optical interface is operating in single or multi-mode."
        ::= { neIFObjects 1 }

    neSystem OBJECT IDENTIFIER ::= { neManageObjs 9 }

    neSystemCmds OBJECT IDENTIFIER ::= { neSystem 1 }

    neResetConfiguration OBJECT-TYPE
        SYNTAX              INTEGER {
                                all( 1 ),
                                spd( 2 ),
                                snmp( 3 )
                            }
        MAX-ACCESS          read-write
        STATUS              current
        DESCRIPTION         "(U//FOUO) Setting this object to a particular
                            enumeration value causes the device to perform
                            the corresponding reset configuration operation.
                            It will not delete keying and other cryptography
                            material. This object is only meant to be written;
                            when read, 'all( 1 )' is always returned and
                            has no meaning. The enumeration values indicate
                            the following: all( 1 ) - The ECU is reset to
                            a near-factory default configuration, that is,
                            to its factory default configuration values except
                            for key material and the audit/notification log(s).
                            spd( 2 ) - This resets the ECU's Security Policy
                            Database (SPD) to a factory default configuration.
                            snmp( 3 ) - This resets the ECU's SNMP settings."
        ::= { neSystemCmds 1 }

    --
    --20090928 - DRN MIB00177 - Add neResetSsoPin
    --
    neResetSsoPin OBJECT-TYPE
        SYNTAX              TruthValue
        MAX-ACCESS          read-write
        STATUS              current
        DESCRIPTION         "(U//FOUO) Setting this object to TRUE will cause
                            the ECU to reset the SSO PIN to the factory default
                            value. When read, this object should return FALSE.
                            When set to FALSE, this object must not perform
                            any operation, but should accept this as a valid
                            SET operation."
        ::= { neSystemCmds 2 }

    --T. Huemiller: Added  neConsoleAddressType and neConsoleAddress to permit manager
    --to
    --configure IP address of console port.
    neConsoleConfig OBJECT IDENTIFIER ::= { neSystem 2 }

    neConsoleAddressType OBJECT-TYPE
        SYNTAX              InetAddressType
        MAX-ACCESS          read-write
        STATUS              current
        DESCRIPTION         "(U//FOUO) This object is the IP address type of
                            the Console Port."
        ::= { neConsoleConfig 1 }

    neConsoleAddress OBJECT-TYPE
        SYNTAX              InetAddress
        MAX-ACCESS          read-write
        STATUS              current
        DESCRIPTION         "(U//FOUO) This object is the IP address of the
                            Console Port."
        ::= { neConsoleConfig 2 }

    neBatteryConfig OBJECT IDENTIFIER ::= { neSystem 3 }

    neBatteryType OBJECT-TYPE
        SYNTAX              INTEGER {
                                alkaline( 1 ),
                                lithium( 2 )
                            }
        MAX-ACCESS          read-write
        STATUS              current
        DESCRIPTION         "(U//FOUO) The type of battery installed in the
                            ECU. If more than one battery is installed in
                            the ECU, they must all be of the same type. (U//FOUO)
                            This object must be SET coincidentally with the
                            object neBatteryChangeDate. If a SET is received
                            without a SET for nebatteryChangeDate, it will
                            be rejected."
        ::= { neBatteryConfig 1 }

    neBatteryChangeDate OBJECT-TYPE
        SYNTAX              DateAndTime
        MAX-ACCESS          read-write
        STATUS              current
        DESCRIPTION         "(U//FOUO) The date and time at which the battery
                            in this ECU was last changed. If more than one
                            battery is installed in the ECU, they must all
                            be changed at the same time"
        ::= { neBatteryConfig 2 }

    neSystemState OBJECT IDENTIFIER ::= { neSystem 4 }

    neCikPending OBJECT-IDENTITY
        STATUS              current
        DESCRIPTION         "U//FOUO) The system state following restart in
                            which the ECU checks for an active Crypto Ignition
                            Key, and if none is inserted, waits for one to
                            be inserted."
        ::= { neSystemState 1 }

    neNetworkActive OBJECT-IDENTITY
        STATUS              current
        DESCRIPTION         "(U//FOUO) The system state following CIK activation,
                            successful configuration of the subsystems and
                            successful cryptographic diagnostic execution.
                            Alternatively, the successful execution of the
                            command to return to the Network Active state
                            from the Secure Communications state. (U//FOUO)
                            When in this state, the ECU permits management
                            through the Console Interface, full ECU management
                            using SNMP on the PT interface, and when the
                            Security Level is not set to INHIBIT, full SNMP
                            management using SNMP on the CT interface. Key
                            Fill and Field Software Upgrade processing are
                            supported"
        ::= { neSystemState 2 }

    neSecureComm OBJECT-IDENTITY
        STATUS              current
        DESCRIPTION         "(U//FOUO) The system state supporting all user
                            and management traffic. (U//FOUO) This state
                            results from the successful execution of the
                            command to transition to the Secure Communications
                            state when in the Network Active state and the
                            security level is set to a value other than INHIBIT."
        ::= { neSystemState 3 }

    neTampered OBJECT-IDENTITY
        STATUS              current
        DESCRIPTION         "(U//FOUO) The physical boundary of the device
                            has been violated."
        ::= { neSystemState 4 }

    neSWLoadFailed OBJECT-IDENTITY
        STATUS              current
        DESCRIPTION         "(U//FOUO) The ECU goes to this state when the
                            SCP SW Image load error occurs during power-up/restart."
        ::= { neSystemState 5 }

    neAlarmed OBJECT-IDENTITY
        STATUS              current
        DESCRIPTION         "(U//FOUO) The system state resulting from a security
                            failure while the ECU is in the CIK Pending,
                            Network Active or Secure Communications state.
                            Once in the Alarmed state, the ECU is automatically
                            transitioned to Power-up/Restart state, causing
                            the ECU to restart."
        ::= { neSystemState 6 }

    neSWSigConfig OBJECT IDENTIFIER ::= { neSystem 5 }

    neSWSigPkgAppVer OBJECT-TYPE
        SYNTAX              OCTET STRING (SIZE(64))
        MAX-ACCESS          read-only
        STATUS              current
        DESCRIPTION         "(U//FOUO) The ASCII App/Ver of the software package."
        ::= { neSWSigConfig 1 }

    neSWSigAppVer OBJECT-TYPE
        SYNTAX              OCTET STRING (SIZE(64))
        MAX-ACCESS          read-only
        STATUS              current
        DESCRIPTION         "(U//FOUO) The ASCII App/Ver from the software
                            sector 1."
        ::= { neSWSigConfig 2 }

    neSWSigSignerID OBJECT-TYPE
        SYNTAX              OCTET STRING (SIZE(1..16))
        MAX-ACCESS          read-only
        STATUS              current
        DESCRIPTION         "(U//FOUO) The signer of the software in ASCII."
        ::= { neSWSigConfig 3 }

    --END neTPSAExtensionTable
    --J. Holzhauer Note: END MIB items added for GigE/Mini R3.4
    --20090227 - DRN MIB00146 - Begin Augment hIPhRuleTable and hIPhSelectorTable
    neSecurityPolicyDatabase OBJECT IDENTIFIER ::= { neManageObjs 10 }

    neSPDRules OBJECT IDENTIFIER ::= { neSecurityPolicyDatabase 1 }

    neIPhRuleAugmentTable OBJECT-TYPE
        SYNTAX              SEQUENCE OF NeIPhRuleAugmentEntry
        MAX-ACCESS          not-accessible
        STATUS              current
        DESCRIPTION         "(U//FOUO) This table augments the hIPhRuleTable
                            in the HAIPE-TRAFFIC-PROTECTION-MIB."
        ::= { neSPDRules 1 }

    neIPhRuleAugmentEntry OBJECT-TYPE
        SYNTAX              NeIPhRuleAugmentEntry
        MAX-ACCESS          not-accessible
        STATUS              current
        DESCRIPTION         "(U//FOUO) A row augmenting a row in the hIPhRuleTable."
        AUGMENTS            {
                                hIPhRuleEntry
                            }
        ::= { neIPhRuleAugmentTable 1 }

    NeIPhRuleAugmentEntry ::= SEQUENCE {
        neIPhRuleAugPermanentFlag
            TruthValue
    }

    neIPhRuleAugPermanentFlag OBJECT-TYPE
        SYNTAX              TruthValue
        MAX-ACCESS          read-only
        STATUS              current
        DESCRIPTION         "(U//FOUO) This object, when TRUE, identifies the
                            IPhRule defined in this row to be a Permanent
                            rule which may not be changed or deleted by any
                            manager. When FALSE, it identifies the IPhRule
                            defined in the associated row to be a User-Defined
                            or Default (Pre-populated User-Defined) Rule
                            which may be edited or deleted."
        ::= { neIPhRuleAugmentEntry 1 }

    neSPDSelectors OBJECT IDENTIFIER ::= { neSecurityPolicyDatabase 2 }

    neIPhSelectorAugmentTable OBJECT-TYPE
        SYNTAX              SEQUENCE OF NeIPhSelectorAugmentEntry
        MAX-ACCESS          not-accessible
        STATUS              current
        DESCRIPTION         "(U//FOUO) This table augments the hIPhSelectorTable
                            in the HAIPE-TRAFFIC-PROTECTION-MIB."
        ::= { neSPDSelectors 1 }

    neIPhSelectorAugmentEntry OBJECT-TYPE
        SYNTAX              NeIPhSelectorAugmentEntry
        MAX-ACCESS          not-accessible
        STATUS              current
        DESCRIPTION         "(U//FOUO) A row augmenting a row in the hIPhSelectorTable"
        AUGMENTS            {
                                hIPhSelectorEntry
                            }
        ::= { neIPhSelectorAugmentTable 1 }

    NeIPhSelectorAugmentEntry ::= SEQUENCE {
        neIPhSelectorAugPermanentFlag
            TruthValue
    }

    neIPhSelectorAugPermanentFlag OBJECT-TYPE
        SYNTAX              TruthValue
        MAX-ACCESS          read-only
        STATUS              current
        DESCRIPTION         "(U//FOUO) This object, when TRUE, identifies the
                            IPhSelector defined in this row to be a Permanent
                            selector which may not be changed or deleted
                            by any manager. When FALSE, it identifies the
                            IPhSelector defined in the associated row to
                            be a User-Defined or Default (Pre-populated User-Defined)
                            Selector which may be edited or deleted."
        ::= { neIPhSelectorAugmentEntry 1 }

    --20090227 - DRN MIB00146 - End Augment hIPhRuleTable and hIPhSelectorTable
    neNotifications OBJECT IDENTIFIER ::= { networkEncryptor 2 }

    neConformance OBJECT IDENTIFIER ::= { networkEncryptor 3 }

    --J. Holzhauer Note: TBD 'conformance' additions to OBJECT-GROUPS for
    --MIB items added for GigE/Mini.
    --See groups below 'automatically' added by SimpleMIBEditor!
    networkEncryptorGroup OBJECT-GROUP
        OBJECTS {           
                        neIpGlobalDFBypassEnable,
                        nePMTUDiscoveryEnable,
                        neGlobalTOSBypassEnable,
                        neTOSConstant,
                        neIpGlobalDFBitValue,
                        neDSCPAcceptedValues,
                        neIpGlobalIgmpBypass,
                        neIpGlobalMTU,
                        neFixedPktMode,
                        neGlobalFixedLength,
                        neGlobalPseqnCheckEnable,
                        neIpv4ControlMessageMTU,
                        neIpv6ControlMessageMTU,
                        neIpGlobalIGMPVersion,
                        neIpGlobalMLDVersion
                }
        STATUS              current
        DESCRIPTION         "(U//FOUO) The neManageObjects Group"
        ::= { neConformance 1 }

    neIFGroup OBJECT-GROUP
        OBJECTS {           
                        neIFMauRole
                }
        STATUS              current
        DESCRIPTION         "(U//FOUO) The objects supporting the configuring
                            of the link-layer interfaces."
        ::= { neConformance 2 }

    nePPKAssignmentTableGroup OBJECT-GROUP
        OBJECTS {           
                        nePPKAssignmentTableCount,
                        nePPKAssignmentChainID,
                        nePPKAssignmentCtAddressType,
                        nePPKAssignmentCtAddr,
                        nePPKAssignmentPtAddressType,
                        nePPKAssignmentPtAddr,
                        nePPKAssignmentRowStatus,
                        nePPKAssignmentEnable
                }
        STATUS              current
        DESCRIPTION         "(U//FOUO) The objects making up the PPK Assignment
                            Table in the neKeyObjects tree."
        ::= { neConformance 4 }

    neUsageAssignmentGroup OBJECT-GROUP
        OBJECTS {           
                        nePPKSlotUse,
                        neSAType,
                        neSAFF
                }
        STATUS              current
        DESCRIPTION         "(U//FOUO) The objects making up the PPK Usage
                            Table in the neKeyObjects Tree and the TPSAAugmentation
                            Table in the neSAKeys tree."
        ::= { neConformance 5 }

    neStaticRouteTableGroup OBJECT-GROUP
        OBJECTS {           
                        neDeleteStaticRoutes
                }
        STATUS              current
        DESCRIPTION         "(U//FOUO) The objects supporting the Static Routing
                            Table in the neStaticRoutes tree."
        ::= { neConformance 6 }

    neHostTableGroup OBJECT-GROUP
        OBJECTS {           
                        neHostTableCount,
                        neHostDeleteHost,
                        neSAHostTimeOutPeriod
                }
        STATUS              current
        DESCRIPTION         "(U//FOUO) The objects supporting the Security
                            Association Host Table in the neHosts tree."
        ::= { neConformance 7 }

    neFFFillGroup OBJECT-GROUP
        OBJECTS {           
                        neFireFlyFillCmd,
                        neFireFlyFillStatus,
                        neAccessControlEnable,
                        neACLTableCount,
                        neACLKMID,
                        neACLKMIDRowStatus,
                        neDailyMtekUpdate
                }
        STATUS              current
        DESCRIPTION         "(U//FOUO) The objects relating to filling FFVS
                            keys."
        ::= { neConformance 8 }

    nePPKFillGroup OBJECT-GROUP
        OBJECTS {           
                        nePPKFillCmd,
                        nePPKFillStatus,
                        nePPKUseConfig,
                        nePPKAlgorithm,
                        nePPKChainIDFillConfig,
                        nePPKEffectiveDate,
                        nePPKIntegrityAlgorithm,
                        nePPKUsageType,
                        nePPKEKUniversalID,
                        nePPKChangeoverKey
                }
        STATUS              current
        DESCRIPTION         "(U//FOUO) The objects relating to filling PrePlaced
                            Keys."
        ::= { neConformance 9 }

    neSATableSortGroup OBJECT-GROUP
        OBJECTS {           
                        neSAIndex,
                        neSARemotePTAddrType,
                        neSARemotePTAddr,
                        neSAIndexInCurrent,
                        neSAIndexOutCurrent,
                        neSAIndexInNext,
                        neSAIndexOutNext,
                        neSAKeyType,
                        neSAEstablished
                }
        STATUS              current
        DESCRIPTION         "(U//FOUO) the objects supporting the lookup table
                            to locate an hTPSATable entry based on Remote
                            INE CT Address."
        ::= { neConformance 10 }

    neIpPDUStatisticsGroup OBJECT-GROUP
        OBJECTS {           
                        neDropCntPTInPTCTProc,
                        neDropCntPTOutPTCTProc,
                        neDropCntCTInPTCTProc,
                        neDropCntCTOutPTCTProc,
                        neDropCntPTInFastpathIFMgr,
                        neDropCntPTOutFastpathIFMgr,
                        neDropCntCTInFastpathIFMgr,
                        neDropCntCTOutFastpathIFMgr,
                        neDropCntPTInBufferUtilities,
                        neDropCntPTOutBufferUtilities,
                        neDropCntCTInBufferUtilities,
                        neDropCntCTOutBufferUtilities,
                        neDropCntPTInReassemMgr,
                        neDropCntPTOutReassemMgr,
                        neDropCntCTInReassemMgr,
                        neDropCntCTOutReassemMgr,
                        neDropCntPTInSPIFMgr,
                        neDropCntPTOutSPIFMgr,
                        neDropCntCTInSPIFMgr,
                        neDropCntCTOutSPIFMgr,
                        neDropCntPTInPTCTNIDMgr,
                        neDropCntPTOutPTCTNIDMgr,
                        neDropCntCTInPTCTNIDMgr,
                        neDropCntCTOutPTCTNIDMgr,
                        neDropCntPTInIPStack,
                        neDropCntPTOutIPStack,
                        neDropCntCTInIPStack,
                        neDropCntCTOutIPStack,
                        neDropCntPTInAddrConfigMgr,
                        neDropCntPTOutAddrConfigMgr,
                        neDropCntCTInAddrConfigMgr,
                        neDropCntCTOutAddrConfigMgr,
                        neDropCntPTInMulticastGroupMgr,
                        neDropCntPTOutMulticastGroupMgr,
                        neDropCntCTInMulticastGroupMgr,
                        neDropCntCTOutMulticastGroupMgr,
                        neDropCntPTInTFTP,
                        neDropCntPTOutTFTP,
                        neDropCntCTInTFTP,
                        neDropCntCTOutTFTP,
                        neDropCntInSNMPAgent,
                        neDropCntCTInIKEMgr,
                        neDropCntCTInISAKMPServer,
                        neDropCntCTOutISAKMPServer,
                        neDropCntCTInISAKMPMgr,
                        neDropCntCTOutESP,
                        neDropCntCTInSDDMgr,
                        neDropCntCTOutSDDMgr,
                        neDropCntCTInSDDServer,
                        neDropCntCTOutSDDServer,
                        neDropCntPTInGDCMgr,
                        neDropCntPTOutGDCMgr,
                        neDropCntCTInGDCMgr,
                        neDropCntCTOutGDCMgr,
                        neDropCntPTInGDCServer,
                        neDropCntPTOutGDCServer,
                        neDropCntCTInGDCServer,
                        neDropCntCTOutGDCServer,
                        neDropCntPTInRIPMgr,
                        neDropCntPTInRIPServer,
                        neDropCntPTOutRIPServer,
                        neDropCntPTInDMCoordinator,
                        neDropCntPTOutDMCoordinator,
                        neDropCntCTInDMCoordinator,
                        neDropCntCTOutDMCoordinator,
                        neDropCntCCCESPAuthError,
                        neErrorCntCCCOther,
                        neDropCntCTInSAC,
                        neDropCntCTOutSAC
                }
        STATUS              current
        DESCRIPTION         "(U//FOUO) the objects supporting the statistics
                            collection for dropped PDUs."
        ::= { neConformance 11 }

    --T. Huemiller 20081216 Added nePACModuliGroup per DRN MIB00141
    nePACModuliGroup OBJECT-GROUP
        OBJECTS {           
                        neUnInstalledPACModuliTableCount,
                        neUnInstalledPACBaseType,
                        neUnInstalledPACID,
                        neUnInstalledPACCOI,
                        neUnInstalledPACUserID,
                        neUnInstalledPACSourceID,
                        neUnInstalledPACNationalID,
                        neUnInstalledPACShortTitleName,
                        neUnInstalledPACAction,
                        neDePACModuliZeroizeCMD
                }
        STATUS              current
        DESCRIPTION         "(U//FOUO) The objects relating to PAC Moduli management."
        ::= { neConformance 12 }

    neNetworkReachabilityDiscoveryGroup OBJECT-GROUP
        OBJECTS {           
                        nenrdDefaultPeerEnclaveEntryLifetime,
                        neTopologyEntryReachable
                }
        STATUS              current
        DESCRIPTION         "(U//FOUO) The objects relating to network reachability
                            discovery."
        ::= { neConformance 13 }

    --T. Huemiller 20081003 Added nePPKChainAssignment to nePPKExtensionsGroup
    nePPKExtensionsGroup OBJECT-GROUP
        OBJECTS {           
                        nePPKUpdateCount,
                        nePPKSuite,
                        nePPKChainAssignment
                }
        STATUS              current
        DESCRIPTION         "(U//FOUO) The objects relating to Preplaced Keys
                            that belong to extensions to existing key tables."
        ::= { neConformance 14 }

    neSecurityStatisticsGroup OBJECT-GROUP
        OBJECTS {           
                        neCtIPv4IcmpPmtuMsgs,
                        neCtToPtIPv4IgmpBypassMsgs,
                        nePtToCtIPv4IgmpBypassMsgs,
                        neCtIPv6IcmpPmtuMsgs,
                        neCtToPtIPv6MldBypassMsgs,
                        nePtToCtIPv6MldBypassMsgs,
                        neESPPacketIntegrityErrors
                }
        STATUS              current
        DESCRIPTION         "(U//FOUO) The objects relating to security statistic
                            collection."
        ::= { neConformance 15 }

    neSASummaryStatisticsGroup OBJECT-GROUP
        OBJECTS {           
                        neTotalSACount,
                        neTotalFireflySACount,
                        neTotalFireflyInCurrentSACount,
                        neTotalFireflyOutCurrentSACount,
                        neTotalFireflyInUpdateSACount,
                        neTotalFireflyOutUpdateSACount,
                        neTotalPPKSACount,
                        neTotalPPKInCurrentSACount,
                        neTotalPPKOutCurrentSACount,
                        neTotalPPKInUpdateChangeoverSACount,
                        neTotalPPKOutUpdateChangeoverSACount,
                        neTotalPPKNotEstablishedSACount,
                        neTotalConfiguredPPKSACount
                }
        STATUS              current
        DESCRIPTION         "(U//FOUO) The objects relating to security association
                            statistic collection."
        ::= { neConformance 16 }

    neTPSAExtensionTableGroup OBJECT-GROUP
        OBJECTS {           
                        neTPSAEstablished,
                        neUnassignedPpkCount,
                        neChainCount,
                        neTPSAAutoConfigLocalAddrs,
                        neTPSAAutoCalcSpiAndTime
                }
        STATUS              current
        DESCRIPTION         "(U//FOUO) The objects making up the SA ExtensionTable
                            in the neSecurityAssociationInfoObjects tree."
        ::= { neConformance 17 }

    neFFExtensionsGroup OBJECT-GROUP
        OBJECTS {           
                        neFFPACModuliId
                }
        STATUS              current
        DESCRIPTION         "(U//FOUO) The objects relating to Firefly Vector
                            Sets that belong to extensions to the existing
                            FFVS table."
        ::= { neConformance 18 }

    neRouteTableGroup OBJECT-GROUP
        OBJECTS {           
                        neDeleteAllRoutes
                }
        STATUS              current
        DESCRIPTION         "(U//FOUO) The objects supporting the Routing Table
                            in the neRoutes tree."
        ::= { neConformance 19 }

    --
    --20090924 - DRN MIB00177 - Add neResetSsoPin
    --
    neSystemGroup OBJECT-GROUP
        OBJECTS {           
                        neResetConfiguration,
                        neBatteryType,
                        neBatteryChangeDate,
                        neResetSsoPin,
                        neIPMEIRMode,
                        neIFOpticalMode
                }
        STATUS              current
        DESCRIPTION         "(U//FOUO) The neSystemGroup Group."
        ::= { neConformance 20 }

    --T. Huemiller: Added neConsoleConfigGroup.
    neConsoleConfigGroup OBJECT-GROUP
        OBJECTS {           
                        neConsoleAddressType,
                        neConsoleAddress
                }
        STATUS              current
        DESCRIPTION         "(U//FOUO) These objects are used to define the
                            IP address of the console port on the ECU."
        ::= { neConformance 21 }

    --20090227 - DRN MIB00146 - Begin Add Object-group
    neIPhRuleSelectorGroup OBJECT-GROUP
        OBJECTS {           
                        neIPhRuleAugPermanentFlag,
                        neIPhSelectorAugPermanentFlag
                }
        STATUS              current
        DESCRIPTION         "(U//FOUO) This object group contains the objects
                            augmenting the hIPhRuleTable and the hIPhSelectorTable
                            of the HAIPE-Traffic-Protection-MIB."
        ::= { neConformance 22 }

    --
    --MIB00178 - 20090928 - Add IF-MIB extension table to NE-MIB
    --
    ifTableExtentionGroup OBJECT-GROUP
        OBJECTS {           
                        neIFTableMedium,
                        neIFTableLocalCapabilities,
                        neIFTableRemoteCapabilities,
                        neIFTableNegotiatedCapability,
                        neIFTableLinkLayerSetting,
                        neIFTableExtARPCacheClear,
                        neIFTableInterfaceAssignment,
                        neIFTableSfpModule
                }
        STATUS              current
        DESCRIPTION         "U(//FOUO) Objects of the neIFTableExtTable."
        ::= { neConformance 23 }

    --20090227 - DRN MIB00146 - End Add Object-group
    --R. Berman 20100902 DRN MIB00191 - Added neAPPKTAExtensionsGroup and neAPPKTAGroup
    neAPPKTAGroup OBJECT-GROUP
        OBJECTS {           
                        neAPPKTAZeroizeCMD,
                        neAPPKTAKMID,
                        neAPPKTAType,
                        neUninstalledTATableCount,
                        neUninstalledTATableLastChanged,
                        neUninstalledTAPartialKeyData,
                        neUninstalledTAShortTitle,
                        neUninstalledTAKMID,
                        neUninstalledTAType,
                        neUninstalledTACOI,
                        neUninstalledTAAction,
                        neAPPKTACheckField,
                        neAPPKTADoi,
                        neAPPKTASignerId,
                        neAPPKTASignerIdDataBits,
                        neUninstalledTACheckField,
                        neUninstalledTADoi
                }
        STATUS              current
        DESCRIPTION         "U(//FOUO) The objects relating to APPK trust anchors."
        ::= { neConformance 24 }

    neSAPairTableGroup OBJECT-GROUP
        OBJECTS {           
                        neSAPairAddrType,
                        neSAPairRemoteCTAddr,
                        neSAPairID,
                        neSAPairEstablishmentMethod,
                        neSAPairRemotePTAddr,
                        neSAPairEstablished,
                        neSAPairIndexIn,
                        neSAPairIndexOut,
                        neSAPairSPIIn,
                        neSAPairSPIOut,
                        neSAPairReachable,
                        neSAPairTransmitCount,
                        neSAPairReceiveCount,
                        neSAPairClearCounts
                }
        STATUS              current
        DESCRIPTION         "(U//FOUO) the objects supporting the lookup table
                            to locate an SAD entry based on Remote INE CT
                            Address and SA ID."
        ::= { neConformance 25 }

    neIKEv2SATableGroup OBJECT-GROUP
        OBJECTS {           
                        neIKEv2SAAddrType,
                        neIKEv2SARemoteCTAddr,
                        neIKEv2SAID,
                        neIKEv2SASADIndex,
                        neIKEv2SARemoteSPI,
                        neIKEv2SALocalSPI,
                        neIKEv2SAReachable,
                        neIKEv2SAChildSACount
                }
        STATUS              current
        DESCRIPTION         "(U//FOUO) the objects supporting the lookup table
                            to locate an IKEv2 SAD entry based on Remote
                            INE CT Address and SA ID."
        ::= { neConformance 26 }

    neIKEv2IKEAndCHILDSATableGroup OBJECT-GROUP
        OBJECTS {           
                        neIKEv2IKEAndCHILDSAAddrType,
                        neIKEv2IKEAndCHILDSARemoteCTAddr,
                        neIKEv2IKEAndCHILDSAIkeSAID,
                        neIKEv2IKEAndCHILDSAChildSAID,
                        neIKEv2IKEAndCHILDSAIkeSADIndex,
                        neIKEv2IKEAndCHILDSAChildSADIndexIn,
                        neIKEv2IKEAndCHILDSAChildSADIndexOut,
                        neIKEv2IKEAndCHILDSASPIIn,
                        neIKEv2IKEAndCHILDSASPIOut,
                        neIKEv2IKEAndCHILDSAEstablished,
                        neIKEv2IKEAndCHILDSAReachable,
                        neIKEv2IKEAndCHILDSATransmitCount,
                        neIKEv2IKEAndCHILDSAReceiveCount,
                        neIKEv2IKEAndCHILDSAClearCounts
                }
        STATUS              current
        DESCRIPTION         "(U//FOUO) the objects supporting the lookup table
                            to locate IKEv2 IKE and Child SAD entries based
                            on Remote INE CT Address and SA ID."
        ::= { neConformance 27 }

    neManSAPairTableGroup OBJECT-GROUP
        OBJECTS {           
                        neManSAPairAddrType,
                        neManSAPairRemoteCTAddr,
                        neManSAPairID,
                        neManSAPairRemotePTAddr,
                        neManSAPairIndexIn,
                        neManSAPairIndexOut,
                        neManSAPairSPIIn,
                        neManSAPairSPIOut
                }
        STATUS              current
        DESCRIPTION         "(U//FOUO) the objects supporting the lookup table
                            to locate an SAD entry based on Remote INE CT
                            Address and SA ID."
        ::= { neConformance 28 }

    neNetworkDiscoveryGroup OBJECT-GROUP
        OBJECTS {           
                        neDiscEnableSDD,
                        neDiscEnableGDC,
                        neDiscEnableGDCRouteRefresh,
                        neDiscGDCRouteRefreshInterval,
                        neDiscEnableIMPEPD
                }
        STATUS              current
        DESCRIPTION         "(U//FOUO) The objects relating to network discovery."
        ::= { neConformance 29 }

    neActiveLepSearchGroup OBJECT-GROUP
        OBJECTS {           
                        neActiveLepSearchEnabled
                }
        STATUS              current
        DESCRIPTION         "(U//FOUO) The objects relating to active LEP search."
        ::= { neConformance 30 }

    neProxyAddrResolutionGroup OBJECT-GROUP
        OBJECTS {           
                        neProxyAddrResTableCount,
                        neProxyAddrResTableDeleteAll,
                        neProxyAddrResAction,
                        neProxyAddrResRowStatus
                }
        STATUS              current
        DESCRIPTION         "(U//FOUO) The objects relating to proxy address
                            resolution."
        ::= { neConformance 31 }

    nePreferredDiscoveryGroup OBJECT-GROUP
        OBJECTS {           
                        neEnablePrefDisc,
                        nePrefDiscTableCount,
                        nePrefDiscAddressType,
                        nePrefDiscStartAddress,
                        nePrefDiscEndAddress,
                        nePrefDiscProtocol,
                        nePrefDiscRowStatus
                }
        STATUS              current
        DESCRIPTION         "(U//FOUO) The objects relating to preferred discovery."
        ::= { neConformance 32 }

    neIGMPLeaveMLDDoneGroup OBJECT-GROUP
        OBJECTS {           
                        neIpGlobalIGMPLeaveBypassEnabled,
                        neIpGlobalMldDoneBypassEnabled
                }
        STATUS              current
        DESCRIPTION         "(U//FOUO) The objects relating to IGMP Leave and
                            MLD Done."
        ::= { neConformance 33 }

    neDiscRouteOfLastResortGroup OBJECT-GROUP
        OBJECTS {           
                        neDiscEnableRouteOfLastResort,
                        neDiscRouteOfLastResortTableCount,
                        neDiscRtOfLstRsrtPTAddress,
                        neDiscRtOfLstRsrtCTAddress,
                        neDiscRtOfLstRsrtAdminCost,
                        neDiscRtOfLstRsrtLifetime
                }
        STATUS              current
        DESCRIPTION         "(U//FOUO) The objects relating to Route of Last
                            Resort."
        ::= { neConformance 34 }

    neRipMappingGroup OBJECT-GROUP
        OBJECTS {           
                        neRipMetricToACMapTableCount,
                        neRipMetricToACMapAdminCost,
                        neRipMetricToACMapRowStatus,
                        neRipACToMetricMapTableCount,
                        neRipACToMetricMapMaxAdminCost,
                        neRipACToMetricMapMetric,
                        neRipACToMetricMapRowStatus
                }
        STATUS              current
        DESCRIPTION         "(U//FOUO) The objects relating to RIP Mappings."
        ::= { neConformance 35 }

    neSaMultipleSasGroup OBJECT-GROUP
        OBJECTS {           
                        neSaMultSaInIndex,
                        neSaMultSaOutIndex,
                        neSaMultSaNumber,
                        neSaMultSaCreateSas
                }
        STATUS              current
        DESCRIPTION         "(U//FOUO) The objects relating to generating multiple
                            SAs."
        ::= { neConformance 36 }

    neSAFailoverGroup OBJECT-GROUP
        OBJECTS {           
                        neSAFailoverEnabled
                }
        STATUS              current
        DESCRIPTION         "(U//FOUO) The objects relating to SA Failover."
        ::= { neConformance 37 }

    neSASettingsGroup OBJECT-GROUP
        OBJECTS {           
                        neIKEv1OrphanSaDelay
                }
        STATUS              current
        DESCRIPTION         "(U//FOUO) The objects relating to SA settings."
        ::= { neConformance 38 }

    neSWSigGroup OBJECT-GROUP
        OBJECTS {           
                        neSWSigPkgAppVer,
                        neSWSigAppVer,
                        neSWSigSignerID
                }
        STATUS              current
        DESCRIPTION         "(U//FOUO) The objects relating to software signature."
        ::= { neConformance 39 }


END
