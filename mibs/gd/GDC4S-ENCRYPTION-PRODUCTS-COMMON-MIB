--BEGIN Revision History
--
--20150918 - M. Coughlin - Add commonAuditUploadInterface and commonAuditUploadProgress
--
--20100415 DRN MIB187. Added commonAuditUpload and commonUserDeviceSettings.
--(commonManageObjects 6, 7, and 8)
--
--20090625 - MIB00174 - Add Ping Test Group.
--
--20090227 - MIB00142 - Add commonRenderUseless group, commonRenderUselessStatus
--and commonRenderUselessSignalEnableCmd in support of ANE development.
--Placed objects in commonRenderUselessAdmin Conformance Group( 10 ).
--
--200608XY  Updates from 05/19/2006 & 05/22/2006 GigE/Mini R3.4 Enterprise MIBs
--Review (ongoing):
--a. Added commonSystemRestartReason object, per AI 7667-17
--b. Updated DESCRIPTIONs of commonSWFltAddressID and commonSWFltStackDump objects,
--describing 'default' values to be used when values are unknown, cannot be
--determined, or objects are otherwise unsupported.  per Ai 7667-
--
--20060810  Updates related to 'environmental faults' per GigE/Mini R3.4
--Enterprise MIBs Review AI 7667-12
--
--20060808  Added CommonDefaultUSASecurityLevel and CommonDefaultGRBSecurityLevel
--TCs
--
--20060807
--a. Added CommonSecurityLevel TC, changed commonNlmLogAuditSecurityLevel
--SYNTAX to this new TC.
--b. Refined commonNlmLogMgmtTable and commonNlmLogExtensionTable for
--objects ensuring that Audit Log is read before being deleted, per
--GigE/Mini 'R3.4 GigE/Mini SRS Requirements Review' AI 7629-1.
--
--20060804  Added commonNlmLogMgmtTable, extended commonNlmLogExtensionTable
--to provide objects to ensure that Audit Log is read before being deleted,
--per GigE/Mini 'R3.4 GigE/Mini SRS Requirements Review' AI 7629-1.
--
--20060803
--a. Added 'groups' commonLoggingCmds/commonStatisticsLoggingCmds and object
--commonFastPathStatisticsCollectionEnabled, per GigE/Mini R3.4
--'HMI HLD Review Part 2.5' AI 7656-1
--b. Moved tlgmcnaNlmLogExtensionTable/Entry, columnar objects and parent
--groups/branches from the TACLANE-GIGE-MINI-COMMON-MIB module, renamed
--as commonNlmLogExtensionTable/Entry.  Related to GigE/Mini R3.4 AI
--7667-14, about adding Audit CIK and Audit Security Level to every
--audit event.
--
--20060726  Added 'group' commonDeviceCtrlCmds and object
--commonResetFactoryDefaults, per GigE/Mini R3.4 AI ???-??
--
--20060613  Updates for TL-Micro DRNs:
--a. Added commonInstallDecryptProgress object to support Field Software Upgrade functionality.
--b. Changed syntax of commonPSEQNRejectCount from Counter64 to Unsigned32 per TACLANE-Micro
--UDRN00349.
--
--20060524 Added commonInstallDecryptProgress object to commonFirmwareDownloadGroup
--in support of FieldSoftwareUpgrade functionality
--
--20060513  Minor updates for GigE/Mini R3.4, for comments from TL-Micro
--Systems & Software preliminary review.
--Also corrected mispelling/type in commonSNMPEventVariables OBJECT-GROUP.
--
--20060510  Minor updates for GigE/Mini R3.4
--
--20060502  Corrected various syntax errors from MIB items
--originally added for GigE/Mini R3.4, corrected IMPORTS clause
--statements
--
--20060428  Added MIB items added for GigE/Mini R3.4
--
--20060327 Added dscpAcceptedValueLow (15) and dscpAcceptedValueHigh (16) enumerations
--to commonPrivModItemName.
--increased value of saHostTimerEnable to (17) and saHostTimerValue to (18).
--
--Added notReady (1) enumeration to cikReceptacleStatus and incremented all other enumerations.
--
--Added commonIFSpeedModeMismatch notification, and commonPTSpeedMode and commonCTSpeedMode
--notification variable objects.  Created commonIFEventGroup and commonIFEventVariables
--conformance groups.
--
--20060328 Added commonFirmwareDownload group containing commonFdsURI object.
--
--END Revision History

GDC4S-ENCRYPTION-PRODUCTS-COMMON-MIB DEFINITIONS ::= BEGIN
    IMPORTS
    Integer32, OBJECT-TYPE, MODULE-IDENTITY,
    Unsigned32, NOTIFICATION-TYPE
        FROM SNMPv2-SMI
    TruthValue, TestAndIncr, TimeStamp, AutonomousType,
    TEXTUAL-CONVENTION, DateAndTime, RowStatus
        FROM SNMPv2-TC
    InetAddressIPv4, InetAddressType, InetAddress
        FROM INET-ADDRESS-MIB
    OBJECT-GROUP, NOTIFICATION-GROUP
        FROM SNMPv2-CONF
    InterfaceIndex
        FROM IF-MIB
    snmpTargetAddrEntry
        FROM SNMP-TARGET-MIB
    SnmpAdminString
        FROM SNMP-FRAMEWORK-MIB
    gdc4sEncryptionProductsMIB
        FROM GDC4S-ENCRYPTION-PRODUCTS-MIB
        --hStationID
    --FROM HAIPE-MANAGEMENT-MIB
    --HAIPE-MANAGEMENT-MIB.hStationID
    --FROM HAIPE-MANAGEMENT-MIB
    nlmLogEntry
        FROM NOTIFICATION-LOG-MIB
    hrSystemDate
        FROM HOST-RESOURCES-MIB
    hStationID
        FROM HAIPE-MANAGEMENT-MIB
    KMID
        FROM HAIPE-TRAFFIC-PROTECTION-MIB
    usmUserSecurityName
        FROM SNMP-USER-BASED-SM-MIB;

    --The NOTIFICATION-LOG-MIB is defined in RFC 3014 or its replacement.
    gdc4sEncryptionProductsCommonMIB MODULE-IDENTITY
        LAST-UPDATED        "200708161030Z"
        ORGANIZATION        "General Dynamics C4 Systems"
        CONTACT-INFO        "Infosec Support                               
                            
                            
                            
                            
                            
                            General Dynamics C4
                            Systems Corporation
                            77 A Street
                            Needham Heights, MA
                            02494-2806
                            Telephone: 877-230-0236
                            email: INFOSECSUPPORT@GDC4S.COM"
        DESCRIPTION         "This MIB supports communications products developed
                            by General Dynamics C4 Systems."

        REVISION            "200708161030Z"
        DESCRIPTION         "Updates for GigE/Mini R3.4"
        REVISION            "200605130000Z"
        DESCRIPTION         "Minor updates for GigE/Mini R3.4, for comments
                            from TL-Micro Systems & Software preliminary
                            review"
        REVISION            "200605102200Z"
        DESCRIPTION         "Minor updates for GigE/Mini R3.4"
        REVISION            "200605021730Z"
        DESCRIPTION         "Corrected syntax errors from updates for GigE/Mini
                            R3.4"
        REVISION            "200604282230Z"
        DESCRIPTION         "Updates for GigE/Mini R3.4"
        REVISION            "200602081320Z"
        DESCRIPTION         "Initial version of this module"
        REVISION            "201005131208Z"
        DESCRIPTION         "Removed auditAuthKeyMissing from commonAuditUploadOperStatus"
        REVISION            "201007091114Z"
        DESCRIPTION         "Made commonACLKMID not-accessible."
        REVISION            "201009271344Z"
        DESCRIPTION         "Deleted gdc4sEncryptionProductsCommonMIBConformance"
        REVISION            "201010111627Z"
        DESCRIPTION         "Updated audit upload notifications. Includes deleting
                            some notifications, adding commonAuditUploadInit,
                            and modifying commonAuditKeyPairGen."
        REVISION            "201102011035Z"
        DESCRIPTION         "Added usmUserSecurityName to commonAuditUploadInit
                            notification."
        ::= { gdc4sEncryptionProductsMIB 2 }

    --BEGIN common textual conventions
    --J. Holzhauer Note: the following TC added for GigE/Mini R3.4
    CommonSecurityLevel ::= TEXTUAL-CONVENTION
        DISPLAY-HINT        "d"
        STATUS              current
        DESCRIPTION         "(U//FOUO) A generic security level. This TC is
                            a global place holder for a more specific security
                            level which is interpreted within the context
                            of some corresponding object (or possibly a portion
                            of some corresponding object, such as an object
                            with SYNTAX of SnmpAdminString). Generally, any
                            object making use of this TC should have a corresponding
                            object that specifies the exact TC that should
                            be used to define the acceptable values to be
                            used by this object. Such exact TCs are platform
                            and implementation dependent: for example, GDC4S
                            HAIPE V3.0.X implementations might use the HaipeUSASecurityLevel
                            or HaipeGRBSecurityLevel TCs defined in the HAIPE-MANAGENT-MIB,
                            while GDC4S Media Encryptor implementations are
                            likely to use the SecurityLevel TC defined in
                            the GDC4S MediaEncryptor-Enterprise-MIB. Other
                            GDC4S encryptor implementations might also use
                            the 'default' security level TCS defined in this
                            module itself, which at the time of this writing
                            include: CommonDefaultUSASecurityLevel, CommonDefaultGRBSecurityLevel.
                            (U//FOUO) Implementations of objects based on
                            the CommonSecurityLevel or associated TCs MUST
                            expect future modifications and additional types
                            to be defined in the future and MUST NOT solely
                            rely on the exclusivity of existing enumeration
                            lists at the time of implementation. (U//FOUO)
                            Note that this TC is modeled after the HaipeSecurityLevel
                            TC defined in the HAIPE-MANAGEMENT-MIB, and in
                            fact has identical SYNTAX. This TC is included
                            in this MIB module to avoid IMPORTS dependencies
                            upon the HAIPE-MANAGEMENT-MIB."
        SYNTAX              Integer32 (0..2147483647)

    --J. Holzhauer Note: the following TC added for GigE/Mini R3.4
    CommonDefaultUSASecurityLevel ::= TEXTUAL-CONVENTION
        STATUS              current
        DESCRIPTION         "(U//FOUO) Note that this TC is modeled after the
                            HaipeUSASecurityLevel TC defined in the HAIPE-MANAGEMENT-MIB,
                            and in fact has identical SYNTAX. This TC is
                            included in this MIB module to avoid IMPORTS
                            dependencies upon the HAIPE-MANAGEMENT-MIB. The
                            reminder of this DESCRIPTION is identical to
                            the DESCRIPTION clause of the HaipeUSASecurityLevel
                            TC. '(U//FOUO) A security level as defined by
                            the 'usa' security authority. For objects that
                            require the ability to have multiple security
                            levels to be set at once, the HaipeUSASecurityLevels
                            TC should be used instead. The value of none(4)
                            should only be used to indicate the absence of
                            level information.'"
        SYNTAX              INTEGER {
                                unclassified( 0 ),
                                confidential( 1 ),
                                secret( 2 ),
                                topSecret( 3 ),
                                none( 4 )
                            }



    --END common textual conventions
    commonManageObjects OBJECT IDENTIFIER
        ::= { gdc4sEncryptionProductsCommonMIB 1 }

    commonSystem OBJECT IDENTIFIER ::= { commonManageObjects 1 }

    commonState OBJECT IDENTIFIER ::= { commonSystem 1 }

    commonSystemState OBJECT-TYPE
        SYNTAX              AutonomousType
        MAX-ACCESS          read-write
        STATUS              current
        DESCRIPTION         "(U//FOUO) This object sets the state of the system
                            and identifies that state. If the system is unable
                            to go to the commanded state, for whatever reason,
                            the object will reject the set command used to
                            set the state."
        ::= { commonState 1 }

    --J. Holzhauer Note: the following object added for GigE/Mini R3.4
    commonSystemRestartReason OBJECT-TYPE
        SYNTAX              SnmpAdminString
        MAX-ACCESS          read-only
        STATUS              current
        DESCRIPTION         "(U//FOUO) This object contains a human-readable
                            octet string which indicates the reason why the
                            system was last restarted. (U//FOUO) Note that
                            it is recommended that coldStart and warmStart
                            notifications generated by the device contain
                            commonSystemRestartReason.0 in their variable-bindings,
                            preceeded by: 1. (U//FOUO) a variable uniquely
                            identifying the device, such as hStationID.0
                            from the HAIPE-MANAGEMENT-MIB module (for GDC4S
                            HAIPE devices) or meStationID.0 from the GDC4S
                            MEDIA-ENCRYPTOR-ENTERPRISE-MIB (for GDC4S Media
                            Encryptor devices, such as the Fibre Channel
                            Encryptor); 2. (U//FOUO) hrSystemDate.0 from
                            the HOST-RESOURCES-MIB module defined in RFC
                            2790 or its successors."
        ::= { commonState 2 }

    commonSNMPManageObjects OBJECT IDENTIFIER ::= { commonSystem 2 }

    commonSpinLock OBJECT-TYPE
        SYNTAX              TestAndIncr
        MAX-ACCESS          read-write
        STATUS              current
        DESCRIPTION         "(U//FOUO) Control for concurrent update of MIB
                            objects under the top-level OID defined within
                            the GDC4S-ENCRYPTION-PRODUCTS-MIB module."
        ::= { commonSNMPManageObjects 1 }

    commonLastChanged OBJECT-TYPE
        SYNTAX              TimeStamp
        MAX-ACCESS          read-only
        STATUS              current
        DESCRIPTION         "(U//FOUO) This object indicates the last time
                            any entry in the MIB was modified, by either
                            SNMP or via the HMI. (U//FOUO) Managers can use
                            this object to ensure that no changes to MIB
                            objects under the top-level OID defined within
                            the GDC4S-ENCRYPTION-PRODUCTS-MIB module have
                            occurred since the last time examined. (U//FOUO)
                            A value of zero (0) indicates that no entry has
                            been changed since the agent initialized."
        ::= { commonSNMPManageObjects 2 }

    commonCik OBJECT IDENTIFIER ::= { commonSystem 3 }

    commonCikManagement OBJECT IDENTIFIER ::= { commonCik 1 }

    cikReceptacleTableCount OBJECT-TYPE
        SYNTAX              Integer32
        MAX-ACCESS          read-only
        STATUS              current
        DESCRIPTION         "(U//FOUO) This object indicates the number of
                            rows in the CikReceptacleTable"
        ::= { commonCikManagement 1 }

    cikReceptacleTable OBJECT-TYPE
        SYNTAX              SEQUENCE OF CikReceptacleEntry
        MAX-ACCESS          not-accessible
        STATUS              current
        DESCRIPTION         "(U//FOUO) This table is used to indicate the status
                            of the CIK receptacle or multiple receptacles.
                            This receptacle status is used to manage the
                            insertion and creation of CIKs. There is one
                            row in this table for each CIK receptacle."
        ::= { commonCikManagement 2 }

    cikReceptacleEntry OBJECT-TYPE
        SYNTAX              CikReceptacleEntry
        MAX-ACCESS          not-accessible
        STATUS              current
        DESCRIPTION         "(U//FOUO) A row containing a CIK receptacle status
                            and requested operator action for the identified
                            CIK receptacle."
        INDEX               {
                                cikReceptacleId
                            }
        ::= { cikReceptacleTable 1 }

    CikReceptacleEntry ::= SEQUENCE {
        cikReceptacleId
            Integer32,
        cikActionRequest
            INTEGER,
        cikReceptacleStatus
            INTEGER
    }

    cikReceptacleId OBJECT-TYPE
        SYNTAX              Integer32 (1..2147483647)
        MAX-ACCESS          read-only
        STATUS              current
        DESCRIPTION         "(U//FOUO) The numerical identifier of the CIK
                            receptacle managed by this row."
        ::= { cikReceptacleEntry 1 }

    cikActionRequest OBJECT-TYPE
        SYNTAX              INTEGER {
                                noAction( 1 ),
                                removeCik( 2 ),
                                insertKsd( 3 ),
                                insertNonCikKsd( 4 ),
                                insertActiveCik( 5 )
                            }
        MAX-ACCESS          read-only
        STATUS              current
        DESCRIPTION         "(U//FOUO) This object, indicates the action the
                            operator should perform with regard to the inserting
                            and removing the KSD/CIK. It is used in conjunction
                            with the commonCikReceptacleStatus object to
                            generate messages directing the SSO (or Remote
                            Manager) to remove/insert the appropriate KSD,
                            CIK or Active CIK. (U//FOUO) The enumeration
                            insertKSD is set immediately after the active
                            CIK is removed during normal execution. (U//FOUO)
                            the enumeration insertNonCikKsd is set when,
                            in error, a CIK already created for this unit
                            is inserted following removal of the active CIK.
                            (U//FOUO) The default value for this object is
                            noAction (1)"
        ::= { cikReceptacleEntry 2 }

    cikReceptacleStatus OBJECT-TYPE
        SYNTAX              INTEGER {
                                notReady( 1 ),
                                noKsdPresent( 2 ),
                                ksdInserted( 3 ),
                                invalidCik( 4 ),
                                ksdMalfunction( 5 ),
                                cikActivated( 6 ),
                                cikCreateInProcess( 7 ),
                                cikCreated( 8 ),
                                cikCreateAborted( 9 ),
                                ksdWriteFailed( 10 )
                            }
        MAX-ACCESS          read-only
        STATUS              current
        DESCRIPTION         "(U//FOUO) The status of the KSD/CIK receptacle
                            or the KSD/CIK inserted in the receptacle. (U//FOUO)
                            This status information is used along with the
                            cikActionRequest object to direct the operator
                            during startup and during the CIK Create operation.
                            (U//FOUO) notReady is used during startup/restart
                            before the ECU processing has determined the
                            status of the CIK Receptacle."
        ::= { cikReceptacleEntry 3 }

    commonCikInventory OBJECT IDENTIFIER ::= { commonCik 2 }

    cikTableCount OBJECT-TYPE
        SYNTAX              Integer32
        MAX-ACCESS          read-only
        STATUS              current
        DESCRIPTION         "(U//FOUO) The number of rows in the commonCikTable.
                            The number of CIKs supported by the device."
        ::= { commonCikInventory 1 }

    cikTable OBJECT-TYPE
        SYNTAX              SEQUENCE OF CikEntry
        MAX-ACCESS          not-accessible
        STATUS              current
        DESCRIPTION         "(U//FOUO) This table contains a list of the CIKs
                            that can be supported by the device, each row
                            indicating if the respective CIK has been created
                            (or is empty)."
        ::= { commonCikInventory 2 }

    cikEntry OBJECT-TYPE
        SYNTAX              CikEntry
        MAX-ACCESS          not-accessible
        STATUS              current
        DESCRIPTION         "(U//FOUO) A row mapping the status of a CIK to
                            its identifying number."
        INDEX               {
                                cikId
                            }
        ::= { cikTable 1 }

    CikEntry ::= SEQUENCE {
        cikId
            Integer32,
        cikCreateCmd
            INTEGER,
        cikCreateReceptacle
            Integer32,
        cikDelete
            TruthValue,
        cikStatus
            INTEGER
    }

    cikId OBJECT-TYPE
        SYNTAX              Integer32 (1..2147483647)
        MAX-ACCESS          read-only
        STATUS              current
        DESCRIPTION         "(U//FOUO) The identifying number of the Crypto
                            Ignition Key controlled by this row."
        ::= { cikEntry 1 }

    cikCreateCmd OBJECT-TYPE
        SYNTAX              INTEGER {
                                noAction( 1 ),
                                create( 2 ),
                                abortCreate( 3 )
                            }
        MAX-ACCESS          read-write
        STATUS              current
        DESCRIPTION         "(U//FOUO) The object provides the remote manager
                            or operator to create a CIK based on the current
                            state of the CIK"
        ::= { cikEntry 2 }

    cikCreateReceptacle OBJECT-TYPE
        SYNTAX              Integer32
        MAX-ACCESS          read-write
        STATUS              current
        DESCRIPTION         "(U//FOUO) The receptacle to be used in creating
                            a CIK. This must match a valid cikReceptacleId,
                            and is required when setting cikCmd to CREATE.
                            When read, this object will return zero (0)."
        ::= { cikEntry 3 }

    cikDelete OBJECT-TYPE
        SYNTAX              TruthValue
        MAX-ACCESS          read-write
        STATUS              current
        DESCRIPTION         "(U//FOUO) This object provides the remote manager
                            or operator the ability to delete a previously
                            defined CIK from the device."
        ::= { cikEntry 4 }

    cikStatus OBJECT-TYPE
        SYNTAX              INTEGER {
                                empty( 1 ),
                                created( 2 ),
                                active( 3 )
                            }
        MAX-ACCESS          read-only
        STATUS              current
        DESCRIPTION         "(U//FOUO) Indicates status of CIK identified in
                            this row. (U//FOUO) The default value for this
                            object is EMPTY (1)."
        ::= { cikEntry 5 }

    commonSystemCmds OBJECT IDENTIFIER ::= { commonSystem 4 }

    --J. Holzhauer Note: the following '(sub)group' is for 'system' commands
    --related to the (Security) Audit Log and/or Event/Notification Log(s).
    commonLogCmds OBJECT IDENTIFIER ::= { commonSystemCmds 1 }

    commonClearAuditLog OBJECT-TYPE
        SYNTAX              TruthValue
        MAX-ACCESS          read-write
        STATUS              current
        DESCRIPTION         "(U//FOUO) When set to TRUE, this object directs
                            the ECU to remove all entries from the Audit
                            Log. When the Audit Log is cleared, this object
                            is set to False."
        ::= { commonLogCmds 1 }

    --J. Holzhauer Note: BEGIN MIB items added for GigE/Mini R3.4
    commonDeviceCtrlCmds OBJECT IDENTIFIER ::= { commonSystemCmds 2 }

    commonResetDevice OBJECT-TYPE
        SYNTAX              TruthValue
        MAX-ACCESS          read-write
        STATUS              current
        DESCRIPTION         "(U//FOUO) The indication of whether a device should
                            be reset. Setting this object to 'true' will
                            perform a reset operation of the device. This
                            must not affect the state of any persistent configuration
                            data, zeroize any of the key material or erase
                            the audit log. When read this object should return
                            false. When set to false this object must not
                            perform any operation but should accept this
                            as a valid SET operation."
        ::= { commonDeviceCtrlCmds 1 }

    commonZeroizeCmd OBJECT-TYPE
        SYNTAX              INTEGER {
                                partial( 1 ),
                                full( 2 ),
                                renderInoperable( 3 )
                            }
        MAX-ACCESS          read-write
        STATUS              current
        DESCRIPTION         "(U//FOUO) Setting this object to a particular
                            enumeration value causes the device to perform
                            the corresponding zeroize operation. This object
                            is only meant to be written; when read, 'partial(
                            1 )' is always returned and has no meaning. The
                            enumeration values indicate the following: partial(
                            1 ) - delete all application key material, common
                            KEK, and credentials full( 2 ) - perform a partial
                            zeroize and in addition delete all delivery key
                            material (e.g., Benign Fill FFVS) renderInoperable(
                            3 ) - perform a full zeroize and in addition
                            render the device inoperable"
        ::= { commonDeviceCtrlCmds 2 }

    --J. Holzhauer Note: the following '(sub)group' is for 'system' commands
    --for 'logging' separate from the (Security) Audit Log and/or
    --Event/Notification Log(s).
    commonLoggingCmds OBJECT IDENTIFIER ::= { commonSystemCmds 3 }

    commonStatisticsLoggingCmds OBJECT IDENTIFIER ::= { commonLoggingCmds 1 }

    commonFastPathStatisticsCollectionEnabled OBJECT-TYPE
        SYNTAX              TruthValue
        MAX-ACCESS          read-write
        STATUS              current
        DESCRIPTION         "(U//FOUO) This object indicates whether the ECU's
                            collection of Fast Path statistics is enabled
                            or disabled. This collection can be disabled
                            to provide better ECU performance. The actual
                            Fast Path statistics collected are platform and
                            implementation dependent. When enabled (value
                            = 'true(1)'), appropriate Fast Path statistics
                            are collected, and may be requested by a network
                            manager via SNMP retrieval requests for the appropriate,
                            corresponding MIB objects containing those statistics.
                            When disabled (value = 'false(2)'), no Fast Path
                            Statistics are collected, and network manager
                            SNMP retrieval requests for the corresponding
                            MIB objects will typically yield the last statistics
                            collected just before Fast Path statistics collection
                            was last disabled. he default value for this
                            object is platform and implementation. For example,
                            in the initial HAIPE V3.X implementations, the
                            default value is for Fast Path Statistics Collection
                            to be enabled (value = 'true(1)')."
        ::= { commonStatisticsLoggingCmds 1 }

    --T. Huemiller - 20090227 - MIB00142 - Begin Render Useless Signal edit.
    commonRenderUseless OBJECT IDENTIFIER ::= { commonSystemCmds 4 }

    commonRenderUselessStatus OBJECT-TYPE
        SYNTAX              BITS {
                                positiveRenderUselessSignal( 0 ),
                                negativeRenderUselessSignal( 1 )
                            }
        MAX-ACCESS          read-only
        STATUS              current
        DESCRIPTION         "(U//FOUO) These two bits indicate the status of
                            the Positive-Render-Useless Signal and the Negative-Render-Useless
                            Signal. For each signal represented by a bit,
                            when the signal is not in the alarm state, the
                            corresponding bit value is zero (0). For each
                            signal represented by a bit, when the signal
                            is in an alarm state, the corresponding bit value
                            is one (1)."
        ::= { commonRenderUseless 1 }

    commonRenderUselessSignalEnableCmd OBJECT-TYPE
        SYNTAX              TruthValue
        MAX-ACCESS          read-write
        STATUS              current
        DESCRIPTION         "(U//FOUO) This object, when set to TRUE, causes
                            the ECU to respond to an alarm state for one
                            or more of the external Render Useless Signal
                            lines. This ECU response is to render the ECU
                            useless. When this object is set to FALSE, the
                            ECU monitors the external status lines but does
                            not respond to an alarm state on any of the external
                            status lines."
        ::= { commonRenderUseless 2 }

    --T. Huemiller - 20090227 - MIB00142 - End Render Useless Signal edit.
    commonSystemInformation OBJECT IDENTIFIER ::= { commonSystem 5 }

    commonSystemSerialNumber OBJECT-TYPE
        SYNTAX              SnmpAdminString (SIZE(0..32))
        MAX-ACCESS          read-write
        STATUS              current
        DESCRIPTION         "(U//FOUO) The unique serial number assigned to
                            the ECU. This is usually the serial number seen
                            on the outside of the ECU chassis."
        ::= { commonSystemInformation 1 }

    commonSystemSecurityLevel OBJECT-TYPE
        SYNTAX              Unsigned32
        MAX-ACCESS          read-only
        STATUS              current
        DESCRIPTION         "(U//FOUO) The security level of the ECU. The possible
                            values are: unclassified(24), restricted(142),
                            confidential(36), secret(66), top secret(129),
                            and inhibit(240)."
        ::= { commonSystemInformation 2 }

    --J. Holzhauer Note: END MIB items added for GigE/Mini R3.4
    commonIP OBJECT IDENTIFIER ::= { commonManageObjects 2 }

    commonIpManageObjects OBJECT IDENTIFIER ::= { commonIP 1 }

    ipInterfaceLvlCfgs OBJECT IDENTIFIER ::= { commonIpManageObjects 1 }

    ipInterfaceLvlCfgTable OBJECT-TYPE
        SYNTAX              SEQUENCE OF IpInterfaceLvlCfgEntry
        MAX-ACCESS          not-accessible
        STATUS              current
        DESCRIPTION         "(U//FOUO) This table contains the IP configuration
                            data that is specified by interface."
        ::= { ipInterfaceLvlCfgs 1 }

    ipInterfaceLvlCfgEntry OBJECT-TYPE
        SYNTAX              IpInterfaceLvlCfgEntry
        MAX-ACCESS          not-accessible
        STATUS              current
        DESCRIPTION         "(U//FOUO) A row providing the IP configuration
                            settings that are done on an interface level."
        INDEX               {
                                ipInterfaceIfIndex
                            }
        ::= { ipInterfaceLvlCfgTable 1 }

    IpInterfaceLvlCfgEntry ::= SEQUENCE {
        ipInterfaceIfIndex
            InterfaceIndex,
        ipv4GatewayAddr
            InetAddressIPv4,
        ipPingEnable
            TruthValue
    }

    ipInterfaceIfIndex OBJECT-TYPE
        SYNTAX              InterfaceIndex
        MAX-ACCESS          read-only
        STATUS              current
        DESCRIPTION         "(U//FOUO) This index relates the data defined
                            in this row with the corresponding row of interface
                            information in the ifTable of the IF-MIB"
        ::= { ipInterfaceLvlCfgEntry 1 }

    ipv4GatewayAddr OBJECT-TYPE
        SYNTAX              InetAddressIPv4
        MAX-ACCESS          read-write
        STATUS              current
        DESCRIPTION         "(U//FOUO) The IPv4 gateway address for the interface."
        ::= { ipInterfaceLvlCfgEntry 2 }

    ipPingEnable OBJECT-TYPE
        SYNTAX              TruthValue
        MAX-ACCESS          read-write
        STATUS              current
        DESCRIPTION         "(U//FOUO) When TRUE, an Echo Reply is to be sent
                            from the interface in response to an Echo Request
                            received on that same interface. (U//FOUO) The
                            default value for this object is to disable pings
                            (FALSE)."
        ::= { ipInterfaceLvlCfgEntry 3 }

    --DRN MIB00174 - 20090625 - Add Ping Test - T. Humeiller
    pingTest OBJECT IDENTIFIER ::= { commonIpManageObjects 2 }

    configPingTest OBJECT IDENTIFIER ::= { pingTest 1 }

    pingTestInterface OBJECT-TYPE
        SYNTAX              InterfaceIndex
        MAX-ACCESS          read-write
        STATUS              current
        DESCRIPTION         "(U//FOUO) The ECU interface from which the ICMP
                            type 8 message (echo message; PING) will be sent.
                            (U//FOUO) The index value that uniquely identifies
                            the interface to which this entry is applicable.
                            The interface identified by a particular value
                            of this index is the same interface as identified
                            by the same value of the IF-MIB's ifIndex."
        ::= { configPingTest 1 }

    pingTestAddrType OBJECT-TYPE
        SYNTAX              InetAddressType
        MAX-ACCESS          read-write
        STATUS              current
        DESCRIPTION         "(U//FOUO) The Internet address type for pingTestSrcAddr
                            and pingTestDestAddr. Only ipv4(1) and ipv6(2)
                            address types are supported. This object is assigned
                            as ipv4(1) at startup."
        ::= { configPingTest 2 }

    pingTestSrcAddr OBJECT-TYPE
        SYNTAX              InetAddress
        MAX-ACCESS          read-write
        STATUS              current
        DESCRIPTION         "(U//FOUO) The Internet address to be placed in
                            the header of the ICMP Type 8 message (echo),
                            and to which the ICMP Type 0 message (echo reply)
                            is sent. This object is assigned the IPv4 value
                            0.0.0.0 at ECU startup."
        ::= { configPingTest 3 }

    pingTestDestAddr OBJECT-TYPE
        SYNTAX              InetAddress
        MAX-ACCESS          read-write
        STATUS              current
        DESCRIPTION         "(U//FOUO) The Internet address for the ECU that
                            receives the ICMP Type 8 message (echo), and
                            composes the ICMP Type 0 message (echo reply).
                            This object is assigned the IPv4 value 0.0.0.0
                            at ECU startup."
        ::= { configPingTest 4 }

    pingTestMessagesToSend OBJECT-TYPE
        SYNTAX              Unsigned32 (1..1000)
        MAX-ACCESS          read-write
        STATUS              current
        DESCRIPTION         "(U//FOUO) The number of ICMP Type 8 messages to
                            be sent during one ping test. This object is
                            assigned the value three (3) at ECU startup."
        ::= { configPingTest 5 }

    pingTestPacketSize OBJECT-TYPE
        SYNTAX              Unsigned32 (0..9200)
        MAX-ACCESS          read-write
        STATUS              current
        DESCRIPTION         "(U//FOUO) The size (in octets) of the ICMP Type
                            8 message. This object is assigned the value
                            64 at ECU startup."
        ::= { configPingTest 6 }

    pingTestEnable OBJECT-TYPE
        SYNTAX              TruthValue
        MAX-ACCESS          read-write
        STATUS              current
        DESCRIPTION         "(U//FOUO) This object enables the sending of ICMP
                            Type 8 messages (echo messages; Pings) from the
                            interface identified by the object pingTestInterface.
                            When set to TRUE, ICMP Type 8 messages (echo
                            messages; Pings) are sent, configured as defined
                            in this group. When set to FALSE, ICMP Type 8
                            messages (echo messages; Pings) are not sent.
                            The initial value following an ECU start is FALSE.
                            The Ping Test is initiated by setting this object
                            to TRUE and halted by setting this object to
                            FALSE. This object is set to FALSE when a Ping
                            Test completes the number of Pings configured
                            in pingTestMessagesToSend."
        ::= { configPingTest 7 }

    pingTestResults OBJECT IDENTIFIER ::= { pingTest 2 }

    pingTestTableCount OBJECT-TYPE
        SYNTAX              Unsigned32 (0..64)
        MAX-ACCESS          read-only
        STATUS              current
        DESCRIPTION         "(U//FOUO) The number of rows in the pingTestTable.
                            This value is assigned a zero-value at startup
                            and upon initiation of a pingTest (pingTestEnable
                            set to TRUE). It is updated with each addition
                            to the pingTestTable to reflect the actual number
                            of ICMP Type 0 messages (echo reply messages)
                            received, or timed-out during the latest or currently
                            executing pingTest up to a maximum of 64."
        ::= { pingTestResults 1 }

    pingTestRepliesTable OBJECT-TYPE
        SYNTAX              SEQUENCE OF PingTestRepliesEntry
        MAX-ACCESS          not-accessible
        STATUS              current
        DESCRIPTION         "(U//FOUO) This table contains the data from the
                            ICMP echo reply messages received in response
                            to the most recent or in-process pingTest. All
                            current table rows are destroyed upon the initiation
                            of a pingTest (pingTestAdminStatus set to send(
                            1 )) and the table is re-populated as the echo
                            reply messages are received or time-out. Once
                            the 64 echo replies have been received, the table
                            entry with the lowest index value is deleted
                            and the most resent test result is added so only
                            the most recently received 64 echo replies from
                            the most recent Ping Test are included."
        ::= { pingTestResults 2 }

    pingTestRepliesEntry OBJECT-TYPE
        SYNTAX              PingTestRepliesEntry
        MAX-ACCESS          not-accessible
        STATUS              current
        DESCRIPTION         "(U//FOUO) A row in the pingTestRepliesTable created
                            in response to the receipt or timeout of an ICMP
                            Type 0 message (echo reply message)."
        INDEX               {
                                pingTestReplyIndex
                            }
        ::= { pingTestRepliesTable 1 }

    PingTestRepliesEntry ::= SEQUENCE {
        pingTestReplyIndex
            Unsigned32,
        pingTestReplyType
            INTEGER,
        pingTestReplyOctets
            Unsigned32,
        pingTestReplyTime
            Unsigned32
    }

    pingTestReplyIndex OBJECT-TYPE
        SYNTAX              Unsigned32
        MAX-ACCESS          not-accessible
        STATUS              current
        DESCRIPTION         "(U//FOUO) A sequentially assigned value, starting
                            with 1, enumerating a received ICMP echo reply
                            or requested-but-not-received ICMP echo reply
                            message, each corresponding to an ICMP echo message
                            sent as part of the most recently commanded Ping
                            Test ."
        ::= { pingTestRepliesEntry 1 }

    pingTestReplyType OBJECT-TYPE
        SYNTAX              INTEGER {
                                reply( 1 ),
                                timeout( 2 )
                            }
        MAX-ACCESS          read-only
        STATUS              current
        DESCRIPTION         "(U//FOUO) Indicates whether the row represents
                            an echo reply that was received, or a time-out
                            that occurred before an echo reply was received."
        ::= { pingTestRepliesEntry 2 }

    pingTestReplyOctets OBJECT-TYPE
        SYNTAX              Unsigned32
        MAX-ACCESS          read-only
        STATUS              current
        DESCRIPTION         "(U//FOUO) The number of octets in the echo reply
                            message. If pingTestReplyType is timeout( 2 ),
                            then the value of pingTestReplyOctets is zero
                            (0)"
        ::= { pingTestRepliesEntry 3 }

    pingTestReplyTime OBJECT-TYPE
        SYNTAX              Unsigned32
        MAX-ACCESS          read-only
        STATUS              current
        DESCRIPTION         "(U//FOUO) The time in msec from when the ICMP
                            Type 8 message (echo message; PING) is transmitted
                            to the time the ICMP Type 0 message (echo reply
                            message; PING Reply) is received by the initiating
                            ECU. If pingTestType is timeout( 2 ), then the
                            value of pingTestReplyTime is the time-out period."
        ::= { pingTestRepliesEntry 4 }

    pingTestSummaryStats OBJECT IDENTIFIER ::= { pingTestResults 3 }

    pingTestDate OBJECT-TYPE
        SYNTAX              DateAndTime
        MAX-ACCESS          read-only
        STATUS              current
        DESCRIPTION         "(U//FOUO) The date and time that the pingTest
                            was initiated. This object is assigned a zero-date
                            at startup (00000101000000). When the object
                            pingTestEnable is set to TRUE, pingTestDate is
                            assigned the current value of hrSystemDate."
        ::= { pingTestSummaryStats 1 }

    pingTestNumberSent OBJECT-TYPE
        SYNTAX              Unsigned32
        MAX-ACCESS          read-only
        STATUS              current
        DESCRIPTION         "(U//FOUO) The number of ICMP Type 8 messages (pings)
                            sent during the most recent pingTest. This object
                            is assigned a zero-value at startup and when
                            the object pingTestEnable is set to TRUE. It
                            is incremented each time an ICMP Type 8 message
                            is sent until pingTestEnabled transitions from
                            TRUE to FALSE."
        ::= { pingTestSummaryStats 2 }

    pingTestRepliesReceived OBJECT-TYPE
        SYNTAX              Unsigned32
        MAX-ACCESS          read-only
        STATUS              current
        DESCRIPTION         "(U//FOUO) The number of ICMP Type 0 messages,
                            (echo reply messages) received before timing
                            out in response to ICMP Type 8 messages (echo
                            messages) sent in this pingTest. This object
                            is assigned a zero-value at startup and when
                            the object pingTestEnable is set to TRUE. It
                            is incremented each time an echo reply message
                            is received before a time out occurs."
        ::= { pingTestSummaryStats 3 }

    pingTestRepliesLost OBJECT-TYPE
        SYNTAX              Unsigned32
        MAX-ACCESS          read-only
        STATUS              current
        DESCRIPTION         "(U//FOUO) The number of ICMP Type 8 messages (echo
                            messages) that timed out before receipt of a
                            corresponding ICMP Type 0 message (echo reply)
                            in response. This object is assigned a zero-value
                            at startup and when pingTestEnable is set to
                            TRUE. It is incremented each time a time out
                            condition occurs in response to a sent ping during
                            a ping test."
        ::= { pingTestSummaryStats 4 }

    pingTestTotalOctetsReceived OBJECT-TYPE
        SYNTAX              Unsigned32
        MAX-ACCESS          read-only
        STATUS              current
        DESCRIPTION         "(U//FOUO) The total number of octets in ICMP Type
                            0 messages (echo reply messages) received before
                            timing out, for the most recent ping test. This
                            value the sum of the octets in all the echo reply
                            messages received before a time out occurs. This
                            object is assigned a zero-value at startup and
                            when the object pingTestEnable is set to TRUE."
        ::= { pingTestSummaryStats 5 }

    pingTestAvgReplyTime OBJECT-TYPE
        SYNTAX              Unsigned32
        MAX-ACCESS          read-only
        STATUS              current
        DESCRIPTION         "(U//FOUO) The average time for the most recent
                            ping test between the transmission of an ICMP
                            Type 8 message (echo message; Ping) and the receipt
                            before time out occurs of the corresponding ICMP
                            Type 0 messages (echo reply messages). This object
                            is assigned a zero-value at startup and when
                            the object pingTestEnable is set to TRUE."
        ::= { pingTestSummaryStats 6 }

    --DRN MIB00174 - 20090625 - End of Add Ping Test - T. Humeiller
    commonSNMPNotificationAugmentation
        OBJECT IDENTIFIER ::= { commonManageObjects 3 }

    commonSNMPTargetTableAugmentation OBJECT-TYPE
        SYNTAX              SEQUENCE OF CommonSNMPTargetEntry
        MAX-ACCESS          not-accessible
        STATUS              current
        DESCRIPTION         "(U//FOUO) This table identifies the interface
                            through which the corresponding SNMP Target connects."
        ::= { commonSNMPNotificationAugmentation 1 }

    commonSNMPTargetEntry OBJECT-TYPE
        SYNTAX              CommonSNMPTargetEntry
        MAX-ACCESS          not-accessible
        STATUS              current
        DESCRIPTION         "(U//FOUO) A row mapping SNMP Target addresses
                            to the interface used to access that address."
        AUGMENTS            {
                                snmpTargetAddrEntry
                            }
        ::= { commonSNMPTargetTableAugmentation 1 }

    CommonSNMPTargetEntry ::= SEQUENCE {
        commonSNMPTargetInterface
            InterfaceIndex
    }

    commonSNMPTargetInterface OBJECT-TYPE
        SYNTAX              InterfaceIndex
        MAX-ACCESS          read-write
        STATUS              current
        DESCRIPTION         "(U//FOUO) The interface through which the device
                            connects to the Target address. This enables
                            the manager to designate which of a number of
                            identical addresses, differing only by the interface
                            through which they connect, should send notifications"
        ::= { commonSNMPTargetEntry 1 }

    --J. Holzhauer Note: BEGIN MIB items added for GigE/Mini R3.4
    commonAuditNotificationExtensions
        OBJECT IDENTIFIER
        ::= { commonSNMPNotificationAugmentation 2 }

    --
    --Common Audit/Notification Log Information
    --commonAuditNotificationExtensions = { commonSNMPNotificationAugmentation 2 }
    --
    --
    commonNotificationExtensions OBJECT IDENTIFIER
        ::= { commonAuditNotificationExtensions 1 }

    --J. Holzhauer Note: the following MIB items added as a placeholder for any
    --scalar MIB objects that are or might be applicable to
    --Notification/Augmentation
    commonNotificationExtensionsScalars
        OBJECT IDENTIFIER ::= { commonNotificationExtensions 1 }

    commonNotificationExtensionsTables
        OBJECT IDENTIFIER ::= { commonNotificationExtensions 2 }

    --BEGIN commonNlmLogExtensionTable
    commonNlmLogExtensionTable OBJECT-TYPE
        SYNTAX              SEQUENCE OF CommonNlmLogExtensionEntry
        MAX-ACCESS          not-accessible
        STATUS              current
        DESCRIPTION         "(U//FOUO) A table of notification/audit log information
                            entries (rows). This table contains additional
                            objects for the Notification Log Table (nlmLogTable)
                            of the NOTIFICATION-LOG-MIB defined in IETF RFC
                            3014 or its replacement. (U//FOUO) It extends,
                            or augments, the nlmLogTable by adding security-relevant
                            columnar objects for auditing purposes, i.e.,
                            for 'security audit log' functions."
        ::= { commonNotificationExtensionsTables 1 }

    commonNlmLogExtensionEntry OBJECT-TYPE
        SYNTAX              CommonNlmLogExtensionEntry
        MAX-ACCESS          not-accessible
        STATUS              current
        DESCRIPTION         "(U//FOUO) An entry (row) containing additional
                            security auditing information applicable to a
                            particular notification log entry."
        AUGMENTS            {
                                nlmLogEntry
                            }
        ::= { commonNlmLogExtensionTable 1 }

    CommonNlmLogExtensionEntry ::= SEQUENCE {
        commonNlmLogAuditSecurityLevel
            CommonSecurityLevel,
        commonNlmLogAuditCIK
            Integer32,
        commonNlmUserSecurityName
            SnmpAdminString
    }

    commonNlmLogAuditSecurityLevel OBJECT-TYPE
        SYNTAX              CommonSecurityLevel
        MAX-ACCESS          read-only
        STATUS              current
        DESCRIPTION         "(U//FOUO) The security level at which the ECU
                            was operating when the entry was placed in this
                            notification log. It is expected that the security
                            level of the ECU will typically be configurable
                            by the 'local' operator only, via the ECU's HMI.
                            The corresponding object that specifies the exact
                            TEXTUAL-CONVENTION used to define and interpret
                            the acceptable values used for this object is
                            platform and implementation dependent."
        ::= { commonNlmLogExtensionEntry 1 }

    --J. Holzhauer clarification: after discussion with T. Huemiller, it
    --seems that the following object and the cikId columnar object of the
    --cikTable in this MIB module are different and independent, and do
    --not necessarily have the same values, or the same SYNTAX.
    --
    commonNlmLogAuditCIK OBJECT-TYPE
        SYNTAX              Integer32 (0..2147483647)
        MAX-ACCESS          read-only
        STATUS              current
        DESCRIPTION         "(U//FOUO) The numerical identifier of the currently
                            active Crypto Ignition Key (CIK) in the ECU,
                            if any, when the entry was placed in this notification
                            log. (U//FOUO) The acceptable values used for
                            this object are platform and implementation dependent.
                            Note that this object is defined with with SYNTAX
                            of Integer32, rather than Unsigned32, to be 'more'
                            compatible with enumerated INTEGER values that
                            are likely to be the implementation dependent
                            acceptables used for this object."
        ::= { commonNlmLogExtensionEntry 2 }

    commonNlmUserSecurityName OBJECT-TYPE
        SYNTAX              SnmpAdminString
        MAX-ACCESS          read-only
        STATUS              current
        DESCRIPTION         "(U//FOUO) The current user active during the entry
                            placement, or responsible for the entry placed
                            in the notification log. This object takes the
                            form of a human readable string representing
                            the user in Security Model independent format.
                            The default transformation of the User-based
                            Security Model dependent security ID to the securityName
                            and vice versa is the identity function so that
                            the securityName is the same as the userName.
                            This object is identical to usmUserSecurityName.
                            It is here in its place because an object that
                            is already in a table elsewhere cannot be imported
                            and added to a table in another MIB."
        ::= { commonNlmLogExtensionEntry 3 }

    --END commonNlmLogExtensionTable
    --J. Holzhauer Note: END MIB items added for GigE/Mini R3.4
    --J. Holzhauer Note: BEGIN MIB items added for GigE/Mini R3.4
    commonFirmwareDownload OBJECT IDENTIFIER ::= { commonManageObjects 4 }

    --J. Holzhauer Note - Decision from 05/19/2006 GigE/Mini R3.4 Enterprise MIB
    --review: do NOT change SYNTAX changing SYNTAX of the following object to
    --'OCTET STRING (SIZE(1..4096))' to match change to SYNTAX of object
    --hFdsURI object of HAIPE-MANAGEMENT-MIB in HAIPE-V3-MIBs
    --Release-2006-04-30!
    --
    commonDownloadFdsURI OBJECT-TYPE
        SYNTAX              SnmpAdminString
        MAX-ACCESS          read-only
        STATUS              current
        DESCRIPTION         "(U//FOUO) The URI indicating the download server,
                            path, etc. ... from which the firmware image
                            stored in the ECU in anticipation of being installed
                            was downloaded."
        ::= { commonFirmwareDownload 1 }

    --J. Holzhauer Note: BEGIN MIB items added for GigE/Mini R3.4
    --
    --J. Holzhauer Note: TL-Micro Systems thinks the following object does
    --NOT follow the HAIPE concept of using URIs for firmware download, but
    --instead perpetuates legacy GigE/Mini R3.2 concepts!
    commonDownloadVersionInfo OBJECT-TYPE
        SYNTAX              SnmpAdminString
        MAX-ACCESS          read-only
        STATUS              current
        DESCRIPTION         "(U//FOUO) The version information for the downloaded
                            firmware image that resides in ECU storage awaiting
                            installation. If no firmware image is resident
                            in the ECU (e.g., no image has ever been downloaded
                            to the ECU, an attempt at downloading an image
                            to the ECU has been unsuccessfull, a downloaded
                            image has been successfully installed into the
                            ECU and subsequently deleted from ECU storage),
                            then this object has a value of the zero-lenth
                            string."
        ::= { commonFirmwareDownload 2 }

    --J. Holzhauer Note: TL-Micro Systems thinks the DESCRIPTION of the
    --following object may need some clarifation about how it is intended to be
    --used.
    commonDownloadZeroizeRequired OBJECT-TYPE
        SYNTAX              TruthValue
        MAX-ACCESS          read-only
        STATUS              current
        DESCRIPTION         "(U//FOUO) This object has the value 'true(1)'
                            if installing the firmware image that resides
                            in ECU storage awaiting will result in zeroizing
                            the ECU. Otherwise, this object has the value
                            'false(2)'. If no firmware image is resident
                            in ECU storage, then this object has the value
                            'false(2)'."
        ::= { commonFirmwareDownload 3 }

    --T. Huemiller Note: Added commonInstallDecryptProgress object to support
    --Field Software Upgrade functionality.
    commonInstallDecryptProgress OBJECT-TYPE
        SYNTAX              Integer32 (0..100)
        MAX-ACCESS          read-only
        STATUS              current
        DESCRIPTION         "(U//FOUO) Contains the percent complete for the
                            Decrypt portion of the Installation command,
                            part of the Field Software Upgrade function.
                            Returns 0 if decryption is not in process. Cleared
                            upon restart."
        ::= { commonFirmwareDownload 4 }

    commonRollbackAvailable OBJECT-TYPE
        SYNTAX              TruthValue
        MAX-ACCESS          read-only
        STATUS              current
        DESCRIPTION         "(U//FOUO) This object when read as true(1) indicates
                            that the installed software can be reverted to
                            the previously installed software version. This
                            object reads false(2) if a previous software
                            version is not available."
        ::= { commonFirmwareDownload 5 }

    commonRollback OBJECT-TYPE
        SYNTAX              TruthValue
        MAX-ACCESS          read-write
        STATUS              current
        DESCRIPTION         "(U//FOUO) This object, when set to TRUE, initiates
                            a software rollback to the previous installed
                            software version. This object, when read, always
                            returns FALSE."
        ::= { commonFirmwareDownload 6 }

    commonPreviousFirmwareVersion OBJECT-TYPE
        SYNTAX              SnmpAdminString
        MAX-ACCESS          read-only
        STATUS              current
        DESCRIPTION         "(U//FOUO) This object contains a human-readable
                            octet string which indicates the previously installed
                            version of firmware/software."
        ::= { commonFirmwareDownload 7 }

    --J. Holzhauer Note: END MIB items added for GigE/Mini R3.4
    --J. Holzhauer Note: BEGIN MIB items added for GigE/Mini R3.4
    --The commonFaultInformation Group allows a network manager to retrieve
    --fault information in the ECU, including which fault conditions
    --are active (present) in the ECU.
    commonFaultInformation OBJECT IDENTIFIER ::= { commonManageObjects 5 }

    --The commonEnvironmentalFaultInformation (Sub)Group allows a network
    --manager to retrieve environmental fault information in the
    --ECU, including which environmental fault conditions are active
    --(present) in the ECU.
    commonEnvironmentalFaultInformation
        OBJECT IDENTIFIER ::= { commonFaultInformation 1 }

    commonOvertemperatureEnvironmentalFault OBJECT-TYPE
        SYNTAX              TruthValue
        MAX-ACCESS          read-only
        STATUS              current
        DESCRIPTION         "(U//FOUO) Indicates whether or not a overtemperature
                            'environmental fault' is currently active/present
                            in the ECU. A value of 'true (1)' indicates that
                            the INE has reached an overtemperature condition.
                            The default value of 'false (2)' indicates that
                            there is no overtemperature problem. ECUs that
                            don't detect this condition will always return
                            'false(2)'. Note that each overtemperature fault
                            will be reported/recorded in the Audit Log."
        ::= { commonEnvironmentalFaultInformation 1 }

    commonFanEnvironmentalFault OBJECT-TYPE
        SYNTAX              TruthValue
        MAX-ACCESS          read-only
        STATUS              current
        DESCRIPTION         "(U//FOUO) Indicates whether or not a fan 'environmental
                            fault' is currently active/present in the ECU.
                            A value of 'true (1)' indicates that the fan
                            within the INE has reported a problem. The default
                            value of 'false (2)' indicates that there is
                            no problem with the fan. ECUs that don't have
                            a fan, or don't detect fan faults will always
                            return 'false(2)'.Note that each fan fault will
                            be reported/recorded in the Audit Log."
        ::= { commonEnvironmentalFaultInformation 2 }

    commonUserManagement OBJECT IDENTIFIER ::= { commonManageObjects 6 }

    commonUserDeviceSettings OBJECT IDENTIFIER ::= { commonUserManagement 1 }

    commonUserDeviceSettingsLockoutTime OBJECT-TYPE
        SYNTAX              Unsigned32 (1..9999)
        UNITS               "Minutes"
        MAX-ACCESS          read-write
        STATUS              current
        DESCRIPTION         "(U//FOUO) This object is the amount of time, in
                            minutes, a user's account will be disabled after
                            they have reached the maximum number of consecutive
                            failed authentications."
        ::= { commonUserDeviceSettings 1 }

    commonUserDeviceSettingsIdleTime OBJECT-TYPE
        SYNTAX              Unsigned32 (1..99)
        UNITS               "Minutes"
        MAX-ACCESS          read-write
        STATUS              current
        DESCRIPTION         "(U//FOUO) This object is the maximum amount of
                            time, in minutes, a session is allowed to be
                            idle before the user is logged off"
        ::= { commonUserDeviceSettings 2 }

    commonUserDeviceSettingsCredentialLifeTime OBJECT-TYPE
        SYNTAX              Unsigned32 (1..999 | 4294967295)
        UNITS               "Days"
        MAX-ACCESS          read-write
        STATUS              current
        DESCRIPTION         "(U//FOUO) This object is the lifetime of a credential
                            (PIN), in days. A value of 4294967295 means infinity
                            (ie, the credential will never expire)."
        ::= { commonUserDeviceSettings 3 }

    commonUserDeviceSettingsMaxAuthFailures OBJECT-TYPE
        SYNTAX              Unsigned32 (1..99)
        MAX-ACCESS          read-write
        STATUS              current
        DESCRIPTION         "(U//FOUO) This object is the maximum failed authentications
                            a user is allowed before they are locked out
                            of their account."
        ::= { commonUserDeviceSettings 4 }

    commonAuditUpload OBJECT IDENTIFIER ::= { commonManageObjects 7 }

    commonAuditUploadServer OBJECT IDENTIFIER ::= { commonAuditUpload 1 }

    commonAuditUploadURI OBJECT-TYPE
        SYNTAX              OCTET STRING (SIZE(1..255))
        MAX-ACCESS          read-write
        STATUS              current
        DESCRIPTION         "(U//FOUO) The URI to indicate an upload server,
                            path, etc... from which to pull an audit from.
                            
                            (U//FOUO) It is important to note that devices
                            may or may not support DNS name resolution and
                            thus some devices may only support URIs containing
                            IP addresses.
                            
                            (U//FOUO) It is also important to note that some
                            protocols may restricted in the size of the URI
                            they can handle, in which case an exception should
                            be returned when an illegally long URI is requested."
        ::= { commonAuditUploadServer 1 }

    commonAuditUploadInterface OBJECT-TYPE
        SYNTAX              Unsigned32
        MAX-ACCESS          read-write
        STATUS              current
        DESCRIPTION         "(U//FOUO) The interface of the device in which
                            the audit log will be uploaded from.
                            
                            (U//FOUO) Each project will define their own
                            interface identification."
        ::= { commonAuditUploadServer 2 }

    commonAuditUploadControls OBJECT IDENTIFIER ::= { commonAuditUpload 2 }

    commonAuditUploadAdminStatus OBJECT-TYPE
        SYNTAX              INTEGER {
                                uploadAudit( 1 ),
                                cancelUpload( 2 ),
                                allowAuditUploadAction( 3 )
                            }
        MAX-ACCESS          read-write
        STATUS              current
        DESCRIPTION         "(U//FOUO) This scalar controls the audit upload
                            process. When read, it will return allowAuditUploadAction
                            if the last action succeeded, or the last requested
                            action, if an action failed or is still in progress.
                            The value cancelUpload will never be returned,
                            as that action should always succeed immediately.
                            
                            (U//FOUO) The values which may be set depend
                            on the current value of this object and the commonAuditUploadOperStatus
                            object.
                            
                            (U//FOUO) To initiate a new upload, this object
                            must contain the value allowAuditUploadAction,
                            and the auditUploadOperStatus must be completeFromMgt.
                            If the requested action is uploadAudit the commonAuditUploadOperStatus
                            should transition to inProgress.
                            
                            (U//FOUO) While an upload is in progress, or
                            if the upload fails (indicated by a auditUploadOperStatus
                            value of uploadFailed), this object will return
                            an inconsistentValue error for any new value
                            except cancelUpload (which will cancel the current
                            upload). If the upload fails, this object must
                            be set to cancelUpload before a new upload may
                            be attempted.
                            
                            (U//FOUO) A summary of allowed values, based
                            on the value of commonAuditUploadOperStatus,
                            is included in the description of the commonAuditUploadOperStatus
                            object."
        ::= { commonAuditUploadControls 1 }

    commonAuditUploadOperStatus OBJECT-TYPE
        SYNTAX              INTEGER {
                                inProgress( 1 ),
                                completeFromMgt( 2 ),
                                uploadFailed( 3 )
                            }
        MAX-ACCESS          read-only
        STATUS              current
        DESCRIPTION         "(U//FOUO) This scalar indicates the current state
                            of a audit upload. inProgress(1) indicates that
                            a upload is underway. completeFromMgt(2) indicates
                            that the last requested audit action was successful.
                            uploadFailed(3) indicates that the last attempted
                            upload failed."
        ::= { commonAuditUploadControls 2 }

    commonAuditUploadProgress OBJECT-TYPE
        SYNTAX              Unsigned32
        MAX-ACCESS          read-only
        STATUS              current
        DESCRIPTION         "(U//FOUO) The percent complete of an audit log
                            upload if in progress."
        ::= { commonAuditUploadControls 3 }

    commonAuditUploadAuthenticationKey
        OBJECT IDENTIFIER ::= { commonAuditUpload 3 }

    commonAuditUploadAuthKeyGeneration OBJECT-TYPE
        SYNTAX              TruthValue
        MAX-ACCESS          read-write
        STATUS              current
        DESCRIPTION         "(U//FOUO) When set to true, generates a new audit
                            authentication key. Setting this field to false
                            does not result in any action taking place. This
                            field is only meant to be written."
        ::= { commonAuditUploadAuthenticationKey 1 }

    commonAuditUploadAuthKeyAlgorithm OBJECT-TYPE
        SYNTAX              INTEGER {
                                ecdsa( 1 )
                            }
        MAX-ACCESS          read-write
        STATUS              current
        DESCRIPTION         "(U//FOUO) Indicates which algorithm was used."
        ::= { commonAuditUploadAuthenticationKey 2 }

    commonAuditUploadAuthKeyStatus OBJECT-TYPE
        SYNTAX              INTEGER {
                                valid( 1 ),
                                invalid( 2 )
                            }
        MAX-ACCESS          read-only
        STATUS              current
        DESCRIPTION         "(U//FOUO) Indicates whether the key valid or not."
        ::= { commonAuditUploadAuthenticationKey 3 }

    commonAuditUploadAuthKeySize OBJECT-TYPE
        SYNTAX              Unsigned32
        MAX-ACCESS          read-only
        STATUS              current
        DESCRIPTION         "(U//FOUO) Indicates the size of the key."
        ::= { commonAuditUploadAuthenticationKey 4 }

    commonAuditUploadAuthKeyPublic OBJECT-TYPE
        SYNTAX              OCTET STRING (SIZE(96))
        MAX-ACCESS          read-only
        STATUS              current
        DESCRIPTION         "(U//FOUO) This is the public key generated."
        ::= { commonAuditUploadAuthenticationKey 5 }

    commonAuditUploadAuthKeyDate OBJECT-TYPE
        SYNTAX              DateAndTime
        MAX-ACCESS          read-only
        STATUS              current
        DESCRIPTION         "(U//FOUO) Indicates the date the key was generated."
        ::= { commonAuditUploadAuthenticationKey 6 }

    commonAuditUploadNotifications OBJECT IDENTIFIER ::= { commonAuditUpload 4 }

    commonAuditUploadError NOTIFICATION-TYPE
        OBJECTS {           
                        hStationID,
                        hrSystemDate,
                        commonAuditUploadErrorCode,
                        commonAuditUploadErrorDetail,
                        commonAuditUploadURI
                }
        STATUS              current
        DESCRIPTION         "(U//FOUO) This notification is sent when an upload
                            fails due to a transfer error. The commonAuditUploadURI
                            object should reference the URI with which the
                            error occurred."
        ::= { commonAuditUploadNotifications 1 }

    commonAuditUploadSuccess NOTIFICATION-TYPE
        OBJECTS {           
                        hStationID,
                        hrSystemDate,
                        commonAuditUploadURI
                }
        STATUS              current
        DESCRIPTION         "(U//FOUO) This notification is sent when an upload
                            has been completed and has succeeded. The commonAuditUploadURI
                            object should reference the URI that was used
                            for the upload."
        ::= { commonAuditUploadNotifications 2 }

    commonAuditUploadInit NOTIFICATION-TYPE
        OBJECTS {           
                        hStationID,
                        hrSystemDate,
                        usmUserSecurityName
                }
        STATUS              current
        DESCRIPTION         "(U//FOUO) Notification indicating an audit upload
                            has been initiated."
        ::= { commonAuditUploadNotifications 3 }

    commonAuditKeyPairGen NOTIFICATION-TYPE
        OBJECTS {           
                        hStationID,
                        hrSystemDate
                }
        STATUS              current
        DESCRIPTION         "(U//FOUO) This notification is sent when an audit
                            key pair is generated."
        ::= { commonAuditUploadNotifications 4 }

    commonAuditUploadEventVarObjects OBJECT IDENTIFIER ::= { commonAuditUpload 5 }

    commonAuditUploadErrorCode OBJECT-TYPE
        SYNTAX              Unsigned32
        MAX-ACCESS          accessible-for-notify
        STATUS              current
        DESCRIPTION         "(U//FOUO) The Error code that triggered the notification.
                            This code is protocol-specific depending on the
                            type of transfer being performed based on the
                            commonAuditUploadURI object."
        ::= { commonAuditUploadEventVarObjects 1 }

    commonAuditUploadErrorDetail OBJECT-TYPE
        SYNTAX              OCTET STRING (SIZE(1..32))
        MAX-ACCESS          accessible-for-notify
        STATUS              current
        DESCRIPTION         "(U//FOUO) The error string, which is likely to
                            be commonAuditUploadURI protocol-specific or
                            action-specific, indicating the nature of the
                            error. The value contained within this object
                            must not be expected to be machine parsable.
                            If no supplemental information is needed to be
                            transmitted, this object should consist of a
                            zero-length string."
        ::= { commonAuditUploadEventVarObjects 2 }

    commonAuditUploadIpAddrType OBJECT-TYPE
        SYNTAX              InetAddressType
        MAX-ACCESS          accessible-for-notify
        STATUS              current
        DESCRIPTION         "(U//FOUO) Type of IP address belonging to manager
                            that requested the audit log auth key."
        ::= { commonAuditUploadEventVarObjects 3 }

    commonAuditUploadIpAddr OBJECT-TYPE
        SYNTAX              InetAddress
        MAX-ACCESS          accessible-for-notify
        STATUS              current
        DESCRIPTION         "(U//FOUO) IP address belonging to manager that
                            requested the audit log auth key."
        ::= { commonAuditUploadEventVarObjects 4 }

    commonACLConfig OBJECT IDENTIFIER ::= { commonManageObjects 8 }

    commonAccessControlEnable OBJECT-TYPE
        SYNTAX              TruthValue
        MAX-ACCESS          read-write
        STATUS              current
        DESCRIPTION         "(U//FOUO) This object, when set to TRUE, enables
                            the Encryptor to only establish Security Associations
                            with remote network encryptors having a FireFly
                            Vector Set that is included in the commonACLKmidTable.
                            (U//FOUO) The default value of this object is
                            to DISABLE Access Control (FALSE)."
        ::= { commonACLConfig 1 }

    commonACLTableCount OBJECT-TYPE
        SYNTAX              Integer32
        MAX-ACCESS          read-only
        STATUS              current
        DESCRIPTION         "(U//FOUO) The number of rows in the commonACLTable"
        ::= { commonACLConfig 2 }

    commonACLTable OBJECT-TYPE
        SYNTAX              SEQUENCE OF CommonACLEntry
        MAX-ACCESS          not-accessible
        STATUS              current
        DESCRIPTION         "(U//FOUO) A list of FFVS KMIDs that may be used
                            by remote network encryptors to establish a Security
                            Association with this network encryptor when
                            the commonAccessModeEnable object is ENABLE.
                            One ACL applies to all security levels."
        ::= { commonACLConfig 3 }

    commonACLEntry OBJECT-TYPE
        SYNTAX              CommonACLEntry
        MAX-ACCESS          not-accessible
        STATUS              current
        DESCRIPTION         "(U//FOUO) A row identifying a FFVS KMID that may
                            be used by a remote network encryptor to establish
                            a Security Association with this Encryptor when
                            the commonAccessModeEnable object is ENABLE."
        INDEX               {
                                commonACLKMID
                            }
        ::= { commonACLTable 1 }

    CommonACLEntry ::= SEQUENCE {
        commonACLKMID
            KMID,
        commonACLKMIDRowStatus
            RowStatus
    }

    commonACLKMID OBJECT-TYPE
        SYNTAX              KMID
        MAX-ACCESS          not-accessible
        STATUS              current
        DESCRIPTION         "(U//FOUO) The Key Management Identifier for a
                            FFVS that can be used by a remote network encryptor
                            to establish a Security Association when the
                            commonAccessModeEnable object is set to ENABLE."
        ::= { commonACLEntry 1 }

    commonACLKMIDRowStatus OBJECT-TYPE
        SYNTAX              RowStatus
        MAX-ACCESS          read-create
        STATUS              current
        DESCRIPTION         "(U//FOUO) The status of this row, by which new
                            entries may be created, or obsolete entries deleted
                            from this table. (U//FOUO) If an attempt to create
                            a new row does not include a value for columns
                            without defaults (commonACLKMID) for the new
                            row, an inconsistentName error will be returned.
                            (U//FOUO) The value of this object has no effect
                            on whether other objects in this row can be modified."
        ::= { commonACLEntry 2 }

    commonFileTransferScalarGroup OBJECT IDENTIFIER ::= { commonManageObjects 9 }

    commonFileTransferURI OBJECT-TYPE
        SYNTAX              SnmpAdminString
        MAX-ACCESS          read-write
        STATUS              current
        DESCRIPTION         "(U//FOUO) The URI indicating the download server,
                            path, etc. ... from which to pull the file to
                            be transfered from."
        ::= { commonFileTransferScalarGroup 1 }

    commonFileTransferInterface OBJECT-TYPE
        SYNTAX              Unsigned32
        MAX-ACCESS          read-write
        STATUS              current
        DESCRIPTION         "(U//FOUO) The interface of the device in which
                            the file transfer will be downloaded.
                            
                            (U//FOUO) Each project will define their own
                            interface identification."
        ::= { commonFileTransferScalarGroup 2 }

    commonFileTransferType OBJECT-TYPE
        SYNTAX              INTEGER {
                                license( 1 )
                            }
        MAX-ACCESS          read-write
        STATUS              current
        DESCRIPTION         "(U//FOUO) The type of file that will be transferred
                            to the ECU. This flag lets the ECU know how to
                            handle this file being downloaded."
        ::= { commonFileTransferScalarGroup 3 }

    commonFileTransferAction OBJECT-TYPE
        SYNTAX              TruthValue
        MAX-ACCESS          read-write
        STATUS              current
        DESCRIPTION         "(U//FOUO) When this value is set to 'true' the
                            file will download from the path indicated in
                            commonFileTransferURI, and process on the ECU.
                            Where the file on the ECU is stored, and how
                            it is handled depends on the value selected in
                            commonFileTransferType. Each type of file is
                            handled differently on the ECU and goes beyond
                            the scope of this description."
        ::= { commonFileTransferScalarGroup 4 }

    commonFileTransferOperStatus OBJECT-TYPE
        SYNTAX              INTEGER {
                                inProgress( 1 ),
                                downloadedFile( 2 ),
                                downloadFailed( 3 )
                            }
        MAX-ACCESS          read-only
        STATUS              current
        DESCRIPTION         "(U//FOUO) This scalar indicates the current state
                            of a file transfer. inProgress(1) indicates that
                            a new file is being downloaded. downloadedFile(2)
                            indicates that a download was successful but
                            it has not yet been installed. downloadFailed(3)
                            indicates that the last attempted download failed.
                            
                            (U//FOUO) This object is used to indicate the
                            status of the file transfer only. Each product
                            needs to handle the installation and status of
                            the installation in it's own way."
        ::= { commonFileTransferScalarGroup 5 }

    --J. Holzhauer Note: END MIB items added for GigE/Mini R3.4
    --J. Holzhauer Note: TBD 'conformance' additions to OBJECT-GROUPS for
    --MIB items added for GigE/Mini.
    --See groups below 'automatically' added by SimpleMIBEditor!
    commonConformance OBJECT IDENTIFIER
        ::= { gdc4sEncryptionProductsCommonMIB 3 }

    --J. Holzhauer Note: added commonResetFactoryDefaults,
    --commonFastPathStatisticsCollectionEnabled to commonSystemGroup
    commonSystemGroup OBJECT-GROUP
        OBJECTS {           
                        commonSystemState,
                        commonSystemRestartReason,
                        commonSpinLock,
                        commonLastChanged,
                        cikReceptacleTableCount,
                        cikReceptacleId,
                        cikReceptacleStatus,
                        cikActionRequest,
                        cikTableCount,
                        cikId,
                        cikCreateCmd,
                        cikStatus,
                        commonClearAuditLog,
                        cikDelete,
                        cikCreateReceptacle,
                        commonResetDevice,
                        commonFastPathStatisticsCollectionEnabled,
                        commonSystemSerialNumber,
                        commonSystemSecurityLevel,
                        commonZeroizeCmd
                }
        STATUS              current
        DESCRIPTION         "(U//FOUO) The commonSystemGroup Group."
        ::= { commonConformance 1 }

    commonIPGroup OBJECT-GROUP
        OBJECTS {           
                        ipv4GatewayAddr,
                        ipPingEnable,
                        ipInterfaceIfIndex
                }
        STATUS              current
        DESCRIPTION         "(U//FOUO) The commonIPGroup Group"
        ::= { commonConformance 2 }

    commonSNMPNotificationAugmentationGroup OBJECT-GROUP
        OBJECTS {           
                        commonSNMPTargetInterface
                }
        STATUS              current
        DESCRIPTION         "(U//FOUO) The commonSNMPNotificationAugmentationGroup
                            Group"
        ::= { commonConformance 4 }

    --J. Holzhauer Note: commonDownloadVersionInfo,
    --commonDownloadZeroizeRequireditems added for GigE/Mini R3.4
    --
    --T. Huemiller Note: Added commonInstallDecryptProgress object to
    --commonFirmwareDownloadGroup.
    commonFirmwareDownloadGroup OBJECT-GROUP
        OBJECTS {           
                        commonDownloadFdsURI,
                        commonDownloadVersionInfo,
                        commonDownloadZeroizeRequired,
                        commonInstallDecryptProgress,
                        commonRollbackAvailable,
                        commonRollback,
                        commonPreviousFirmwareVersion
                }
        STATUS              current
        DESCRIPTION         "(U//FOUO) this group contains the objects used
                            to support Firmware Download functionality."
        ::= { commonConformance 5 }

    -- changed OID from 8 due to conflict with GDC4S-COMMON-NOTIFICATIONS-MIB::
    -- commonNotifEventsGroup (CHIMERA Team)
    commonEnvironmentalFaultInfoGroup OBJECT-GROUP
        OBJECTS {           
                        commonOvertemperatureEnvironmentalFault,
                        commonFanEnvironmentalFault
                }
        STATUS              current
        DESCRIPTION         "(U//FOUO) This group contains the objects used
                            to support Environmental Fault Reporting functionality."
        ::= { commonConformance 101 }

    -- changed OID from 9 due to conflict with GDC4S-COMMON-NOTIFICATIONS-MIB::
    -- commonNotifEventVariableObjectsGroup (CHIMERA Team)
    commonNLMLogGroup OBJECT-GROUP
        OBJECTS {           
                        commonNlmLogAuditSecurityLevel,
                        commonNlmLogAuditCIK,
                        commonNlmUserSecurityName
                }
        STATUS              current
        DESCRIPTION         "(U//FOUO) this group contains the objects used
                            to support Notification Log MIB functionality."
        ::= { commonConformance 102 }

    commonRenderUselessAdmin OBJECT-GROUP
        OBJECTS {           
                        commonRenderUselessStatus,
                        commonRenderUselessSignalEnableCmd
                }
        STATUS              current
        DESCRIPTION         "(U//FOUO) This conformance group contains the
                            objects used to administer the Render Useless
                            functionality."
        ::= { commonConformance 10 }

    commonPingTestAdmin OBJECT-GROUP
        OBJECTS {           
                        pingTestInterface,
                        pingTestAddrType,
                        pingTestSrcAddr,
                        pingTestDestAddr,
                        pingTestMessagesToSend,
                        pingTestPacketSize,
                        pingTestEnable,
                        pingTestTableCount,
                        pingTestDate,
                        pingTestNumberSent,
                        pingTestRepliesReceived,
                        pingTestRepliesLost,
                        pingTestTotalOctetsReceived,
                        pingTestAvgReplyTime,
                        pingTestReplyType,
                        pingTestReplyOctets,
                        pingTestReplyTime
                }
        STATUS              current
        DESCRIPTION         "(U//FOUO) This conformance group contains the
                            objects used to administer the Ping Test functionality."
        ::= { commonConformance 11 }

    commonAuditUploadGroup OBJECT-GROUP
        OBJECTS {           
                        commonAuditUploadURI,
                        commonAuditUploadInterface,
                        commonAuditUploadAdminStatus,
                        commonAuditUploadOperStatus,
                        commonAuditUploadProgress,
                        commonAuditUploadAuthKeyGeneration,
                        commonAuditUploadAuthKeyAlgorithm,
                        commonAuditUploadAuthKeyStatus,
                        commonAuditUploadAuthKeySize,
                        commonAuditUploadAuthKeyPublic,
                        commonAuditUploadAuthKeyDate,
                        commonAuditUploadErrorCode,
                        commonAuditUploadErrorDetail,
                        commonAuditUploadIpAddrType,
                        commonAuditUploadIpAddr
                }
        STATUS              current
        DESCRIPTION         "(U//FOUO) The commonAuditUpload Group."
        ::= { commonConformance 17 }

    commonAuditUploadNotifGroup NOTIFICATION-GROUP
        NOTIFICATIONS       {
                                commonAuditUploadError,
                                commonAuditUploadSuccess,
                                commonAuditKeyPairGen,
                                commonAuditUploadInit
                            }
        STATUS              current
        DESCRIPTION         "(U//FOUO) The commonAuditUploadNotif Group."
        ::= { commonConformance 18 }

    commonUserDeviceSettingsGroup OBJECT-GROUP
        OBJECTS {           
                        commonUserDeviceSettingsLockoutTime,
                        commonUserDeviceSettingsIdleTime,
                        commonUserDeviceSettingsCredentialLifeTime,
                        commonUserDeviceSettingsMaxAuthFailures
                }
        STATUS              current
        DESCRIPTION         "(U//FOUO) This group contains the objects used
                            to support User Device Settings functionality."
        ::= { commonConformance 19 }

    commonACLTableGroup OBJECT-GROUP
        OBJECTS {           
                        commonAccessControlEnable,
                        commonACLTableCount,
                        commonACLKMID,
                        commonACLKMIDRowStatus
                }
        STATUS              current
        DESCRIPTION         "(U//FOUO) The commonACLTable Group."
        ::= { commonConformance 20 }

    commonFileTransferGroup OBJECT-GROUP
        OBJECTS {           
                        commonFileTransferURI,
                        commonFileTransferInterface,
                        commonFileTransferType,
                        commonFileTransferAction,
                        commonFileTransferOperStatus
                }
        STATUS              current
        DESCRIPTION         "(U//FOUO) This group contains the objects used
                            to support file transfer functionality."
        ::= { commonConformance 21 }


END
