--BEGIN Revision History
--
--20120516 - G. Jones - Original
--
--END Revision History

GDC4S-DPI-MIB DEFINITIONS ::= BEGIN
    IMPORTS
    Unsigned32, OBJECT-TYPE, MODULE-IDENTITY,
    NOTIFICATION-TYPE
        FROM SNMPv2-SMI
    OBJECT-GROUP, NOTIFICATION-GROUP
        FROM SNMPv2-CONF
    TruthValue, TimeStamp, RowStatus, DateAndTime,
    TEXTUAL-CONVENTION
        FROM SNMPv2-TC
    SnmpAdminString
        FROM SNMP-FRAMEWORK-MIB
    InetAddressType, InetAddress, InetPortNumber
        FROM INET-ADDRESS-MIB
	commonStationID, commonSystemDate, commonIfIndex,
	commonErrDetail
		FROM GDC4S-COMMON-NOTIFICATIONS-MIB
    gdc4sFeatureHierarchy
        FROM GDC4S-FEATURE-MIB;

    dpiFeature MODULE-IDENTITY
        LAST-UPDATED		"201205160759Z"
        ORGANIZATION		"General Dynamics C4 Systmes"
        CONTACT-INFO    	"Infosec Support                               
							General Dynamics C4
							Systems Corporation
							77 A St
							Needham Hts, MA
							02494-2806
							Telephone: 877-230-0236
							Email: INFOSECSUPPORT@GDC4S.COM"
        DESCRIPTION     	"This MIB supports additional MIB features necessary
							to configure the devices developed by General
							Dynamics C4 Systems."

        REVISION	    	"201205160759Z"
        DESCRIPTION     	"initial version of this module"
        ::= { gdc4sFeatureHierarchy 3 }

    DpiAlertFormat ::= TEXTUAL-CONVENTION
        STATUS		    	current
        DESCRIPTION     	"(U//FOUO) The format of the alerts."
        SYNTAX INTEGER {
			syslog( 1 ),
			syslogCef( 2 ),
			unified2( 3 )
		}

    DpiNtpPollingRate ::= TEXTUAL-CONVENTION
        STATUS		    	current
        DESCRIPTION     	"(U//FOUO) The polling rate of the time server."
        SYNTAX		    	Unsigned32 (64|128|256|512|1024|2048|4096)

    DpiNtpServerStatus ::= TEXTUAL-CONVENTION
        STATUS		    	current
        DESCRIPTION     	"(U//FOUO) The current status of the connection
							to the time server."
        SYNTAX INTEGER {
			unknown( 1 ),
			failed( 2 ),
			operational( 3 )
		}

    --***********************************************************************************
    --DPI
    --***********************************************************************************

    dpiFeatureConfiguration OBJECT IDENTIFIER ::= { dpiFeature 1 }

    dpiFeatureConfigurationScalarGroup OBJECT IDENTIFIER ::= { dpiFeatureConfiguration 1 }

    dpiEnable OBJECT-TYPE
        SYNTAX				TruthValue
        MAX-ACCESS     	 	read-write
        STATUS          	current
        DESCRIPTION     	"(U//FOUO) Allows the manager to enable the DPI
							process by setting this value to 'true'."
        ::= { dpiFeatureConfigurationScalarGroup 1 }
        
    dpiMode OBJECT-TYPE
        SYNTAX INTEGER {
			nonSensor( 0 ),
			sensorIds( 1 ),
			sensorIps( 2 )
        }
        MAX-ACCESS      	read-write
        STATUS          	current
        DESCRIPTION     	"(U//FOUO) Allows the manager to disable DPI
							sensor mode by setting this value to 'nonSensor'.
						
							(U//FOUO) Allows the manager to enable DPI IDS
							sensor mode by setting this value to 'sensorIds'.
						
							(U//FOUO) Allows the manager to enable DPI IPS
							sensor mode by setting this value to 'sensorIps'."
        ::= { dpiFeatureConfigurationScalarGroup 2 }

    dpiUnsupEthFramePrtclAction OBJECT-TYPE
        SYNTAX INTEGER {
			bypass( 1 ),
			drop( 2 )
        }
        MAX-ACCESS          read-write
        STATUS              current
        DESCRIPTION         "(U//FOUO) The action to be taken on a packet when 
							the Ethernet frame protocol is not supported."
        ::= { dpiFeatureConfigurationScalarGroup 3 }
        
    dpiFeatureElements OBJECT IDENTIFIER ::= { dpiFeature 2 }
    
    --*********
    --Netflow
    --*********
    dpiNetflow OBJECT IDENTIFIER ::= { dpiFeatureElements 1 }

    dpiNetflowPTInterface OBJECT IDENTIFIER ::= { dpiNetflow 1 }

    dpiNfPTConfigurationScalarGroup OBJECT IDENTIFIER ::= { dpiNetflowPTInterface 1 }

    dpiNfPTEnable OBJECT-TYPE
        SYNTAX              TruthValue
        MAX-ACCESS          read-write
        STATUS              current
        DESCRIPTION         "(U//FOUO) Allows the manager to enable the Netflow
                            process on the PT User Interface by setting this
                            value to 'true'."
        ::= { dpiNfPTConfigurationScalarGroup 1 }

    dpiNfPTFlowActiveTimeout OBJECT-TYPE
        SYNTAX              Unsigned32 (1..60)
        UNITS               "Minutes"
        MAX-ACCESS          read-write
        STATUS              current
        DESCRIPTION         "(U//FOUO) The timeout period (in minutes) for
                            removing active flows from the cache. Default
                            value is 15 minutes."
        ::= { dpiNfPTConfigurationScalarGroup 2 }

    dpiNfPTFlowInactiveTimeout OBJECT-TYPE
        SYNTAX              Unsigned32 (1..60)
        UNITS               "Seconds"
        MAX-ACCESS          read-write
        STATUS              current
        DESCRIPTION         "(U//FOUO) The timeout period (in seconds) for
                            removing inactive flows from the cache. Default
                            value is 15 seconds."
        ::= { dpiNfPTConfigurationScalarGroup 3 }

    dpiNfPTExportConfiguration OBJECT IDENTIFIER ::= { dpiNetflowPTInterface 2 }

    dpiNfPTExportConfigTableCount OBJECT-TYPE
        SYNTAX              Unsigned32
        MAX-ACCESS          read-only
        STATUS              current
        DESCRIPTION         "(U//FOUO) The number of rows in the dpiNfPTExportConfigTable."
        ::= { dpiNfPTExportConfiguration 1 }

    dpiNfPTExportConfigTableLastChanged OBJECT-TYPE
        SYNTAX              TimeStamp
        MAX-ACCESS          read-only
        STATUS              current
        DESCRIPTION         "(U//FOUO) The value of hSysUpTime the last time
                            any entry in the dpiNfPTExportConfigTable was
                            modified, created, or deleted by either SNMP
                            or other management method (e.g via an HMI).
                            
                            (U//FOUO) Manager can use this object to ensure
                            that no changes to configuration of this table
                            have happened since the last time it examined
                            the table.
                            
                            (U//FOUO) A value of 0 indicates that no entry
                            has been changed since the agent initialized."
        ::= { dpiNfPTExportConfiguration 2 }

    dpiNfPTExportConfigTable OBJECT-TYPE
        SYNTAX              SEQUENCE OF DpiNfPTExpClctrEntry
        MAX-ACCESS          not-accessible
        STATUS              current
        DESCRIPTION         "(U//FOUO) A control table to configure the export
                            characteristics for netflow packets."
        ::= { dpiNfPTExportConfiguration 3 }

    dpiNfPTExpClctrEntry OBJECT-TYPE
        SYNTAX              DpiNfPTExpClctrEntry
        MAX-ACCESS          not-accessible
        STATUS              current
        DESCRIPTION         "(U//FOUO) A row describing the configuration of
                            the Netflow Collector."
        INDEX 				{
								dpiNfPTExpClctrAddressType,
								dpiNfPTExpClctrAddress
							}
        ::= { dpiNfPTExportConfigTable 1 }

    DpiNfPTExpClctrEntry ::= SEQUENCE {
        dpiNfPTExpClctrAddressType 		InetAddressType,
        dpiNfPTExpClctrAddress			InetAddress,
        dpiNfPTExpClctrPortNumber 		InetPortNumber,
        dpiNfPTExpClctrIntf 			Unsigned32,
        dpiNfPTExpClctrTemplateTimeout	Unsigned32,
        dpiNfPTExpClctrRowStatus 		RowStatus
    }

    dpiNfPTExpClctrAddressType OBJECT-TYPE
        SYNTAX              InetAddressType
        MAX-ACCESS          not-accessible
        STATUS              current
        DESCRIPTION         "(U//FOUO) The type of Internet address used by
                            the collector."
        ::= { dpiNfPTExpClctrEntry 1 }

    dpiNfPTExpClctrAddress OBJECT-TYPE
        SYNTAX              InetAddress
        MAX-ACCESS          not-accessible
        STATUS              current
        DESCRIPTION         "(U//FOUO) The Internet address of the collector.
                            (U//FOUO) This IP address must be consistent
                            with the IP address type in dpiNfPTExpClctrAddressType.
                            Attempts to set this object to a value inconsistent
                            with the type must fail with an inconsistentValue
                            error."
        ::= { dpiNfPTExpClctrEntry 2 }

    dpiNfPTExpClctrPortNumber OBJECT-TYPE
        SYNTAX              InetPortNumber
        MAX-ACCESS          read-create
        STATUS              current
        DESCRIPTION         "(U//FOUO) The port number of the collector which
                            the Netflow data is exported to."
        DEFVAL              { 2055 }
        ::= { dpiNfPTExpClctrEntry 3 }

    dpiNfPTExpClctrIntf OBJECT-TYPE
        SYNTAX              Unsigned32
        MAX-ACCESS          read-create
        STATUS              current
        DESCRIPTION         "(U//FOUO) The interface of the server where the
                            netflow packets are exported."
        ::= { dpiNfPTExpClctrEntry 4 }

    dpiNfPTExpClctrTemplateTimeout OBJECT-TYPE
        SYNTAX              Unsigned32 (1..60)
        UNITS               "Minutes"
        MAX-ACCESS          read-create
        STATUS              current
        DESCRIPTION         "(U//FOUO) The timeout period (in minutes) for
                            exporting template records to the collector."
        DEFVAL              { 15 }
        ::= { dpiNfPTExpClctrEntry 5 }

    dpiNfPTExpClctrRowStatus OBJECT-TYPE
        SYNTAX              RowStatus
        MAX-ACCESS          read-create
        STATUS              current
        DESCRIPTION         "(U//FOUO) The status of the row by which new entries
                            may be created, existing entries modified or
                            deleted from this table."
        ::= { dpiNfPTExpClctrEntry 6 }

    dpiNetflowCTInterface OBJECT IDENTIFIER ::= { dpiNetflow 2 }

    dpiNfCTConfigurationScalarGroup OBJECT IDENTIFIER ::= { dpiNetflowCTInterface 1 }

    dpiNfCTEnable OBJECT-TYPE
        SYNTAX              TruthValue
        MAX-ACCESS          read-write
        STATUS              current
        DESCRIPTION         "(U//FOUO) Allows the manager to enable the Netflow
                            process on the CT User Interface by setting this
                            value to 'true'."
        ::= { dpiNfCTConfigurationScalarGroup 1 }

    dpiNfCTFlowActiveTimeout OBJECT-TYPE
        SYNTAX              Unsigned32 (1..60)
        UNITS               "Minutes"
        MAX-ACCESS          read-write
        STATUS              current
        DESCRIPTION         "(U//FOUO) The timeout period (in minutes) for
                            removing active flows from the cache. Default
                            value is 15 minutes."
        ::= { dpiNfCTConfigurationScalarGroup 2 }

    dpiNfCTFlowInactiveTimeout OBJECT-TYPE
        SYNTAX              Unsigned32 (1..60)
        UNITS               "Seconds"
        MAX-ACCESS          read-write
        STATUS              current
        DESCRIPTION         "(U//FOUO) The timeout period (in seconds) for
                            removing inactive flows from the cache. Default
                            value is 15 seconds."
        ::= { dpiNfCTConfigurationScalarGroup 3 }

    dpiNfCTExportConfiguration OBJECT IDENTIFIER ::= { dpiNetflowCTInterface 2 }

    dpiNfCTExportConfigTableCount OBJECT-TYPE
        SYNTAX              Unsigned32
        MAX-ACCESS          read-only
        STATUS              current
        DESCRIPTION         "(U//FOUO) The number of rows in the dpiNfCTExportConfigTable."
        ::= { dpiNfCTExportConfiguration 1 }

    dpiNfCTExportConfigTableLastChanged OBJECT-TYPE
        SYNTAX              TimeStamp
        MAX-ACCESS          read-only
        STATUS              current
        DESCRIPTION         "(U//FOUO) The value of hSysUpTime the last time
                            any entry in the dpiNfCTExportConfigTable was
                            modified, created, or deleted by either SNMP
                            or other management method (e.g via an HMI).
                            
                            (U//FOUO) Manager can use this object to ensure
                            that no changes to configuration of this table
                            have happened since the last time it examined
                            the table.
                            
                            (U//FOUO) A value of 0 indicates that no entry
                            has been changed since the agent initialized."
        ::= { dpiNfCTExportConfiguration 2 }

    dpiNfCTExportConfigTable OBJECT-TYPE
        SYNTAX              SEQUENCE OF DpiNfCTExpClctrEntry
        MAX-ACCESS          not-accessible
        STATUS              current
        DESCRIPTION         "(U//FOUO) A control table to configure the export
                            characteristics for netflow packets."
        ::= { dpiNfCTExportConfiguration 3 }

    dpiNfCTExpClctrEntry OBJECT-TYPE
        SYNTAX              DpiNfCTExpClctrEntry
        MAX-ACCESS          not-accessible
        STATUS              current
        DESCRIPTION         "(U//FOUO) A row describing the configuration of
                            the Netflow Collector."
        INDEX 				{
								dpiNfCTExpClctrAddressType,
								dpiNfCTExpClctrAddress
							}
        ::= { dpiNfCTExportConfigTable 1 }

    DpiNfCTExpClctrEntry ::= SEQUENCE {
        dpiNfCTExpClctrAddressType  	InetAddressType,
        dpiNfCTExpClctrAddress 			InetAddress,
        dpiNfCTExpClctrPortNumber 		InetPortNumber,
        dpiNfCTExpClctrIntf 			Unsigned32,
        dpiNfCTExpClctrTemplateTimeout	Unsigned32,
        dpiNfCTExpClctrRowStatus 		RowStatus
    }

    dpiNfCTExpClctrAddressType OBJECT-TYPE
        SYNTAX              InetAddressType
        MAX-ACCESS          not-accessible
        STATUS              current
        DESCRIPTION         "(U//FOUO) The type of Internet address used by
                            the collector."
        ::= { dpiNfCTExpClctrEntry 1 }

    dpiNfCTExpClctrAddress OBJECT-TYPE
        SYNTAX              InetAddress
        MAX-ACCESS          not-accessible
        STATUS              current
        DESCRIPTION         "(U//FOUO) The Internet address of the collector.
                            This is the address which the Netflow data is
                            exported.(U//FOUO) This IP address must be consistent
                            to the IP address type in dpiNfCTExpClctrAddressType.
                            Attempts to set this object to a value inconsistent
                            with the type must fail with an inconsistentValue
                            error."
        ::= { dpiNfCTExpClctrEntry 2 }

    dpiNfCTExpClctrPortNumber OBJECT-TYPE
        SYNTAX              InetPortNumber
        MAX-ACCESS          read-create
        STATUS              current
        DESCRIPTION         "(U//FOUO) The port number of the collector which
                            the Netflow data is exported to."
        DEFVAL              { 2055 }
        ::= { dpiNfCTExpClctrEntry 3 }

    dpiNfCTExpClctrIntf OBJECT-TYPE
        SYNTAX              Unsigned32
        MAX-ACCESS          read-create
        STATUS              current
        DESCRIPTION         "(U//FOUO) The interface of the server where the
                            netflow packets are exported."
        ::= { dpiNfCTExpClctrEntry 4 }

    dpiNfCTExpClctrTemplateTimeout OBJECT-TYPE
        SYNTAX              Unsigned32 (1..60)
        UNITS               "Minutes"
        MAX-ACCESS          read-create
        STATUS              current
        DESCRIPTION         "(U//FOUO) The timeout period (in minutes) for
                            exporting template records to the collector."
        DEFVAL              { 15 }
        ::= { dpiNfCTExpClctrEntry 5 }

    dpiNfCTExpClctrRowStatus OBJECT-TYPE
        SYNTAX              RowStatus
        MAX-ACCESS          read-create
        STATUS              current
        DESCRIPTION         "(U//FOUO) The status of the row by which new entries
                            may be created, existing entries modified or
                            deleted from this table."
        ::= { dpiNfCTExpClctrEntry 6 }

    --*****************
    --Rule Sets
    --*****************
    dpiRuleSets OBJECT IDENTIFIER ::= { dpiFeatureElements 2 }

    dpiRuleSetsPTInterface OBJECT IDENTIFIER ::= { dpiRuleSets 1 }

    dpiRSPTConfigurationScalarGroup OBJECT IDENTIFIER ::= { dpiRuleSetsPTInterface 1 }

    dpiRSPTClear OBJECT-TYPE
        SYNTAX              TruthValue
        MAX-ACCESS          read-write
        STATUS              current
        DESCRIPTION         "(U//FOUO) Setting this object to 'true' will clear
                            all PT rules, and return the ECU to default configuration.
                            When read this object should return its value.
                            If this object is set to the same value as the
                            current value, the device must not perform any
                            operation but should accept this as a valid SET
                            operation."
        ::= { dpiRSPTConfigurationScalarGroup 1 }

    dpiRSPTRuleSet OBJECT-TYPE
        SYNTAX              SnmpAdminString (SIZE(1..64))
        MAX-ACCESS          read-only
        STATUS              current
        DESCRIPTION         "(U//FOUO) The Rule Set installed for use with
                            the PT interface."
        ::= { dpiRSPTConfigurationScalarGroup 2 }

    dpiRuleSetsCTInterface OBJECT IDENTIFIER ::= { dpiRuleSets 2 }

    dpiRSCTConfigurationScalarGroup OBJECT IDENTIFIER ::= { dpiRuleSetsCTInterface 1 }

    dpiRSCTClear OBJECT-TYPE
        SYNTAX              TruthValue
        MAX-ACCESS          read-write
        STATUS              current
        DESCRIPTION         "(U//FOUO) Setting this object to 'true' will clear
                            all CT rules, and return the ECU to default configuration.
                            When read this object should return its value.
                            If this object is set to the same value as the
                            current value, the device must not perform any
                            operation but should accept this as a valid SET
                            operation."
        ::= { dpiRSCTConfigurationScalarGroup 1 }

    dpiRSCTRuleSet OBJECT-TYPE
        SYNTAX              SnmpAdminString (SIZE(1..64))
        MAX-ACCESS          read-only
        STATUS              current
        DESCRIPTION         "(U//FOUO) The Rule Set installed for use with
                            the CT interface."
        ::= { dpiRSCTConfigurationScalarGroup 2 }
        
	dpiRSInstallConfigurationScalarGroup OBJECT IDENTIFIER ::= { dpiRuleSets 3 }
		
    dpiRSInstallInterface OBJECT-TYPE
        SYNTAX              Unsigned32
        MAX-ACCESS          read-write
        STATUS              current
        DESCRIPTION         "(U//FOUO) The interface over which Rule Set data is to be 
							received. The interface, URI, and Authentication code must
							be set together. The install will be triggered by the set."
        ::= { dpiRSInstallConfigurationScalarGroup 1 }		

    dpiRSInstallURI OBJECT-TYPE
        SYNTAX              SnmpAdminString
        MAX-ACCESS          read-write
        STATUS              current
        DESCRIPTION         "(U//FOUO) The URI for the Rule Set to be installed.
							The interface, URI, and Authentication code must be set 
							together. The install will be triggered by the set."
        ::= { dpiRSInstallConfigurationScalarGroup 2 }
		
    dpiRSInstallAuthCode OBJECT-TYPE
        SYNTAX              SnmpAdminString (SIZE(12..32))
        MAX-ACCESS          read-write
        STATUS              current
        DESCRIPTION         "(U//FOUO) The authentication code for the Rule Set to be 
							installed. When read this object will always return an 
							empty string. The interface, URI, and Authentication code 
							must be set together. The install will be triggered by the set."
        ::= { dpiRSInstallConfigurationScalarGroup 3 }

    dpiRSInstallOperStatus OBJECT-TYPE
        SYNTAX INTEGER {
			inProgress( 1 ),
			success( 2 ),
			failure( 3 )
        }
        MAX-ACCESS          read-only
        STATUS              current
        DESCRIPTION         "(U//FOUO) The status of the Rule Set download and 
							installation."
        ::= { dpiRSInstallConfigurationScalarGroup 4 }		

    --*************************
    --Security Alert Reporting
    --*************************
    dpiAlerts OBJECT IDENTIFIER ::= { dpiFeatureElements 3 }

    dpiAlertsPTInterface OBJECT IDENTIFIER ::= { dpiAlerts 1 }

    dpiAlertsPTConfigurationScalarGroup
        OBJECT IDENTIFIER ::= { dpiAlertsPTInterface 1 }

    dpiAlertsPTEnable OBJECT-TYPE
        SYNTAX              TruthValue
        MAX-ACCESS          read-write
        STATUS              current
        DESCRIPTION         "(U//FOUO) Allows the manager to enable the security
                            alert reporting process on the PT Interface by
                            setting this value to 'true'."
        ::= { dpiAlertsPTConfigurationScalarGroup 1 }

    dpiAlertsPTServerConfiguration OBJECT IDENTIFIER ::= { dpiAlertsPTInterface 2 }

    dpiAlertPTServerConfigTableCount OBJECT-TYPE
        SYNTAX              Unsigned32
        MAX-ACCESS          read-only
        STATUS              current
        DESCRIPTION         "(U//FOUO) The number of rows in the dpiAlertPTServerTable."
        ::= { dpiAlertsPTServerConfiguration 1 }

    dpiAlertPTServerConfigTableLastChanged OBJECT-TYPE
        SYNTAX              TimeStamp
        MAX-ACCESS          read-only
        STATUS              current
        DESCRIPTION         "(U//FOUO) The value of hSysUpTime the last time
                            any entry in the dpiAlertPTServerTable was modified,created,
                            or deleted by either SNMP or other management
                            method (e.g via an HMI). (U//FOUO) Manager can
                            use this object to ensure that no changes to
                            configuration of this table have happened since
                            the last time it examined the table. (U//FOUO)
                            A value of 0 indicates that no entry has been
                            changed since the agent initialized."
        ::= { dpiAlertsPTServerConfiguration 2 }

    dpiAlertPTServerTable OBJECT-TYPE
        SYNTAX              SEQUENCE OF DpiAlertPTServerEntry
        MAX-ACCESS          not-accessible
        STATUS              current
        DESCRIPTION         "(U//FOUO) The table that configures and lists
                            the Security Alert Servers for the device's PT
                            Interface."
        ::= { dpiAlertsPTServerConfiguration 3 }

    dpiAlertPTServerEntry OBJECT-TYPE
        SYNTAX              DpiAlertPTServerEntry
        MAX-ACCESS          not-accessible
        STATUS              current
        DESCRIPTION         "(U//FOUO) A row describing the characteristics
                            of the Alert Server configurations."
        INDEX 				{
								dpiAlertPTServerAddressType,
								dpiAlertPTServerAddress
							}
        ::= { dpiAlertPTServerTable 1 }

    DpiAlertPTServerEntry ::= SEQUENCE {
        dpiAlertPTServerAddressType 	InetAddressType,
        dpiAlertPTServerAddress 		InetAddress,
        dpiAlertPTServerPortNumber 		InetPortNumber,
        dpiAlertPTServerIntf 			Unsigned32,
        dpiAlertPTServerFormat 			DpiAlertFormat,
        dpiAlertPTServerRowStatus 		RowStatus
    }

    dpiAlertPTServerAddressType OBJECT-TYPE
        SYNTAX              InetAddressType
        MAX-ACCESS          not-accessible
        STATUS              current
        DESCRIPTION         "(U//FOUO) The type of address of the server."
        ::= { dpiAlertPTServerEntry 1 }

    dpiAlertPTServerAddress OBJECT-TYPE
        SYNTAX              InetAddress
        MAX-ACCESS          not-accessible
        STATUS              current
        DESCRIPTION         "(U//FOUO) The IP address of the alert server.
                            (U//FOUO) This IP address must be consistent
                            to the IP address type in dpiAlertPTServerAddressType.
                            Attempts to set this object to a value inconsistent
                            with must fail with an inconsistentValue error."
        ::= { dpiAlertPTServerEntry 2 }

    dpiAlertPTServerPortNumber OBJECT-TYPE
        SYNTAX              InetPortNumber
        MAX-ACCESS          read-create
        STATUS              current
        DESCRIPTION         "(U//FOUO) The transport port number of the server
                            which the security alerts are exported to."
        DEFVAL              { 514 }
        ::= { dpiAlertPTServerEntry 3 }

    dpiAlertPTServerIntf OBJECT-TYPE
        SYNTAX              Unsigned32
        MAX-ACCESS          read-create
        STATUS              current
        DESCRIPTION         "(U//FOUO) The interface of the server where the
                            security alerts are reported."
        ::= { dpiAlertPTServerEntry 4 }

    dpiAlertPTServerFormat OBJECT-TYPE
        SYNTAX              DpiAlertFormat
        MAX-ACCESS          read-create
        STATUS              current
        DESCRIPTION         "(U//FOUO) The format in which the PT security
                            alerts will be sent to the server."
        ::= { dpiAlertPTServerEntry 5 }

    dpiAlertPTServerRowStatus OBJECT-TYPE
        SYNTAX              RowStatus
        MAX-ACCESS          read-create
        STATUS              current
        DESCRIPTION         "(U//FOUO) The status of the row by which new entries
                            may be created, existing entries modified or
                            deleted from this table."
        ::= { dpiAlertPTServerEntry 6 }

    dpiAlertsCTInterface OBJECT IDENTIFIER ::= { dpiAlerts 2 }

    dpiAlertsCTConfigurationScalarGroup
        OBJECT IDENTIFIER ::= { dpiAlertsCTInterface 1 }

    dpiAlertsCTEnable OBJECT-TYPE
        SYNTAX              TruthValue
        MAX-ACCESS          read-write
        STATUS              current
        DESCRIPTION         "(U//FOUO) Allows the manager to enable the security
                            alert reporting process on the CT Interface by
                            setting this value to 'true'."
        ::= { dpiAlertsCTConfigurationScalarGroup 1 }

    dpiAlertsCTServerConfiguration OBJECT IDENTIFIER ::= { dpiAlertsCTInterface 2 }

    dpiAlertCTServerConfigTableCount OBJECT-TYPE
        SYNTAX              Unsigned32
        MAX-ACCESS          read-only
        STATUS              current
        DESCRIPTION         "(U//FOUO) The number of rows in the dpiAlertCTServerTable."
        ::= { dpiAlertsCTServerConfiguration 1 }

    dpiAlertCTServerConfigTableLastChanged OBJECT-TYPE
        SYNTAX              TimeStamp
        MAX-ACCESS          read-only
        STATUS              current
        DESCRIPTION         "(U//FOUO) The value of hSysUpTime the last time
                            any entry in the dpiAlertCTServerTable was modified,created,
                            or deleted by either SNMP or other management
                            method (e.g via an HMI). (U//FOUO) Manager can
                            use this object to ensure that no changes to
                            configuration of this table have happened since
                            the last time it examined the table.
                            
                            (U//FOUO) A value of 0 indicates that no entry
                            has been changed since the agent initialized."
        ::= { dpiAlertsCTServerConfiguration 2 }

    dpiAlertCTServerTable OBJECT-TYPE
        SYNTAX              SEQUENCE OF DpiAlertCTServerEntry
        MAX-ACCESS          not-accessible
        STATUS              current
        DESCRIPTION         "(U//FOUO) The table that configures and lists
                            the Security Alert Servers for the device's CT
                            Interface."
        ::= { dpiAlertsCTServerConfiguration 3 }

    dpiAlertCTServerEntry OBJECT-TYPE
        SYNTAX              DpiAlertCTServerEntry
        MAX-ACCESS          not-accessible
        STATUS              current
        DESCRIPTION         "(U//FOUO) A row describing the characteristics
                            of the Alert Server configurations."
        INDEX 				{
								dpiAlertCTServerAddressType,
								dpiAlertCTServerAddress
							}
        ::= { dpiAlertCTServerTable 1 }

    DpiAlertCTServerEntry ::= SEQUENCE {
        dpiAlertCTServerAddressType 	InetAddressType,
        dpiAlertCTServerAddress 		InetAddress,
        dpiAlertCTServerPortNumber 		InetPortNumber,
        dpiAlertCTServerIntf 		 	Unsigned32,
        dpiAlertCTServerFormat 			DpiAlertFormat,
        dpiAlertCTServerRowStatus 		RowStatus
    }

    dpiAlertCTServerAddressType OBJECT-TYPE
        SYNTAX              InetAddressType
        MAX-ACCESS          not-accessible
        STATUS              current
        DESCRIPTION         "(U//FOUO) The type of address of the server."
        ::= { dpiAlertCTServerEntry 1 }

    dpiAlertCTServerAddress OBJECT-TYPE
        SYNTAX              InetAddress
        MAX-ACCESS          not-accessible
        STATUS              current
        DESCRIPTION         "(U//FOUO) The IP address of the alert server.
                            (U//FOUO) This IP address must be consistent
                            to the IP address type in dpiAlertCTServerAddressType.
                            Attempts to set this object to a value inconsistent
                            with must fail with an inconsistentValue error."
        ::= { dpiAlertCTServerEntry 2 }

    dpiAlertCTServerPortNumber OBJECT-TYPE
        SYNTAX              InetPortNumber
        MAX-ACCESS          read-create
        STATUS              current
        DESCRIPTION         "(U//FOUO) The transport port of the server which
                            the security alerts are exported to."
        DEFVAL              { 514 }
        ::= { dpiAlertCTServerEntry 3 }

    dpiAlertCTServerIntf OBJECT-TYPE
        SYNTAX              Unsigned32
        MAX-ACCESS          read-create
        STATUS              current
        DESCRIPTION         "(U//FOUO) The interface of the server where the
                            security alerts are reported."
        ::= { dpiAlertCTServerEntry 4 }

    dpiAlertCTServerFormat OBJECT-TYPE
        SYNTAX              DpiAlertFormat
        MAX-ACCESS          read-create
        STATUS              current
        DESCRIPTION         "(U//FOUO) The format in which the CT security
                            alerts will be sent to the server."
        ::= { dpiAlertCTServerEntry 5 }

    dpiAlertCTServerRowStatus OBJECT-TYPE
        SYNTAX              RowStatus
        MAX-ACCESS          read-create
        STATUS              current
        DESCRIPTION         "(U//FOUO) The status of the row by which new entries
                            may be created, existing entries modified or
                            deleted from this table."
        ::= { dpiAlertCTServerEntry 6 }

    --****
    --NTP
    --****
    dpiNTP OBJECT IDENTIFIER ::= { dpiFeatureElements 4 }

    dpiNtpPTInterface OBJECT IDENTIFIER ::= { dpiNTP 1 }

    dpiNtpPTConfigurationScalarGroup OBJECT IDENTIFIER ::= { dpiNtpPTInterface 1 }

    dpiNtpPTEnable OBJECT-TYPE
        SYNTAX              TruthValue
        MAX-ACCESS          read-write
        STATUS              current
        DESCRIPTION         "(U//FOUO) Allows the manager to enable the ECU
                            to receive time updates from the NTP server on
                            the PT interface by setting this value to 'true'."
        ::= { dpiNtpPTConfigurationScalarGroup 1 }

    dpiNtpPTDateTime OBJECT-TYPE
        SYNTAX              DateAndTime
        MAX-ACCESS          read-only
        STATUS              current
        DESCRIPTION         "(U//FOUO) The current NTP date/time on the device.
                            (U//FOUO) The date and time will be displayed
                            in UTC time. For example Tuesday May 26, 1992
                            2:30:15 PM UTC is displayed as: 1992-5-26,14:30:15.0"
        ::= { dpiNtpPTConfigurationScalarGroup 2 }

    dpiNtpPTServerConfiguration OBJECT IDENTIFIER ::= { dpiNtpPTInterface 2 }

    dpiNtpPTServerConfigTableCount OBJECT-TYPE
        SYNTAX              Unsigned32
        MAX-ACCESS          read-only
        STATUS              current
        DESCRIPTION         "(U//FOUO) The number of rows in the dpiNtpPTServerTable."
        ::= { dpiNtpPTServerConfiguration 1 }

    dpiNtpPTServerConfigTableLastChanged OBJECT-TYPE
        SYNTAX              TimeStamp
        MAX-ACCESS          read-only
        STATUS              current
        DESCRIPTION         "(U//FOUO) The value of hSysUpTime the last time
                            any entry in the dpiNtpPTServerTable was modified,created,
                            or deleted by either SNMP or other management
                            method (e.g via an HMI). (U//FOUO)Manager can
                            use this object to ensure that no changes to
                            configuration of this table have happened since
                            the last time it examined the table.
                            
                            (U//FOUO) A value of 0 indicates that no entry
                            has been changed since the agent initialized."
        ::= { dpiNtpPTServerConfiguration 2 }

    dpiNtpPTServerTable OBJECT-TYPE
        SYNTAX              SEQUENCE OF DpiNtpPTServerEntry
        MAX-ACCESS          not-accessible
        STATUS              current
        DESCRIPTION         "(U//FOUO) The table that configures and lists
                            the Simple Network Time Protocol Servers for
                            the PT interface."
        ::= { dpiNtpPTServerConfiguration 3 }

    dpiNtpPTServerEntry OBJECT-TYPE
        SYNTAX              DpiNtpPTServerEntry
        MAX-ACCESS          not-accessible
        STATUS              current
        DESCRIPTION         "(U//FOUO) A row describing characteristics of
                            the NTP Server."
        INDEX               {
                                dpiNtpPTServerAddressType,
                                dpiNtpPTServerAddress
                            }
        ::= { dpiNtpPTServerTable 1 }

    DpiNtpPTServerEntry ::= SEQUENCE {
        dpiNtpPTServerAddressType 		InetAddressType,
        dpiNtpPTServerAddress 			InetAddress,
        dpiNtpPTServerPortNumber		InetPortNumber,
        dpiNtpPTServerIntf 				Unsigned32,
        dpiNtpPTServerMinPollingRate 	DpiNtpPollingRate,
        dpiNtpPTServerMaxPollingRate 	DpiNtpPollingRate,
        dpiNtpPTServerOffset 			Unsigned32,
        dpiNtpPTServerDelay 			Unsigned32,
        dpiNtpPTServerStatus 			DpiNtpServerStatus,
        dpiNtpPTServerRowStatus 		RowStatus
    }

    dpiNtpPTServerAddressType OBJECT-TYPE
        SYNTAX              InetAddressType
        MAX-ACCESS          not-accessible
        STATUS              current
        DESCRIPTION         "(U//FOUO) The type of address of the server."
        ::= { dpiNtpPTServerEntry 1 }

    dpiNtpPTServerAddress OBJECT-TYPE
        SYNTAX              InetAddress
        MAX-ACCESS          not-accessible
        STATUS              current
        DESCRIPTION         "(U//FOUO) The IP address of the NTP server. (U//FOUO)
                            This IP address must be consistent to the IP
                            address type in dpiNtpPTServerAddressType. Attempts
                            to set this object to a value inconsistent with
                            must fail with an inconsistentValue error."
        ::= { dpiNtpPTServerEntry 2 }

    dpiNtpPTServerPortNumber OBJECT-TYPE
        SYNTAX              InetPortNumber
        MAX-ACCESS          read-create
        STATUS              current
        DESCRIPTION         "(U//FOUO) The port number of the NTP server."
        DEFVAL              { 123 }
        ::= { dpiNtpPTServerEntry 3 }

    dpiNtpPTServerIntf OBJECT-TYPE
        SYNTAX              Unsigned32
        MAX-ACCESS          read-create
        STATUS              current
        DESCRIPTION         "(U//FOUO) The interface off which to find the
                            NTP server."
        ::= { dpiNtpPTServerEntry 4 }

    dpiNtpPTServerMinPollingRate OBJECT-TYPE
        SYNTAX              DpiNtpPollingRate
        MAX-ACCESS          read-create
        STATUS              current
        DESCRIPTION         "(U//FOUO) The minimum polling rate of the NTP
                            server. (U//FOUO) If the device is being configured
                            for static polling, set this value to equal dpiNtpPTServerMaxPollingRate."
        DEFVAL              { 1024 }
        ::= { dpiNtpPTServerEntry 5 }

    dpiNtpPTServerMaxPollingRate OBJECT-TYPE
        SYNTAX              DpiNtpPollingRate
        MAX-ACCESS          read-create
        STATUS              current
        DESCRIPTION         "(U//FOUO) The maximum polling rate of the NTP
                            server. (U//FOUO) If the device is being configured
                            for static polling, set this value to equal dpiNtpPTServerMinPollingRate."
        DEFVAL              { 4096 }
        ::= { dpiNtpPTServerEntry 6 }

    dpiNtpPTServerOffset OBJECT-TYPE
        SYNTAX              Unsigned32
        MAX-ACCESS          read-only
        STATUS              current
        DESCRIPTION         "(U//FOUO) The time offset to the NTP server."
        ::= { dpiNtpPTServerEntry 7 }

    dpiNtpPTServerDelay OBJECT-TYPE
        SYNTAX              Unsigned32
        MAX-ACCESS          read-only
        STATUS              current
        DESCRIPTION         "(U//FOUO) The network delay of the NTP server."
        ::= { dpiNtpPTServerEntry 8 }

    dpiNtpPTServerStatus OBJECT-TYPE
        SYNTAX              DpiNtpServerStatus
        MAX-ACCESS          read-only
        STATUS              current
        DESCRIPTION         "(U//FOUO) The current status of the connection
                            to the time server. (U//FOUO) FUTURE: If the
                            status is fail, then an Event Notification will
                            be triggered."
        ::= { dpiNtpPTServerEntry 9 }

    dpiNtpPTServerRowStatus OBJECT-TYPE
        SYNTAX              RowStatus
        MAX-ACCESS          read-create
        STATUS              current
        DESCRIPTION         "(U//FOUO) The status of the row by which new entries
                            may be created, existing entries modified or
                            deleted from this table."
        ::= { dpiNtpPTServerEntry 10 }

    dpiNtpCTInterface OBJECT IDENTIFIER ::= { dpiNTP 2 }

    dpiNtpCTConfigurationScalarGroup OBJECT IDENTIFIER ::= { dpiNtpCTInterface 1 }

    dpiNtpCTEnable OBJECT-TYPE
        SYNTAX              TruthValue
        MAX-ACCESS          read-write
        STATUS              current
        DESCRIPTION         "(U//FOUO) Allows the manager to enable the ECU
                            to receive time updates from the NTP server on
                            the CT interface by setting this value to 'true'."
        ::= { dpiNtpCTConfigurationScalarGroup 1 }

    dpiNtpCTDateTime OBJECT-TYPE
        SYNTAX              DateAndTime
        MAX-ACCESS          read-only
        STATUS              current
        DESCRIPTION         "(U//FOUO) The current NTP date/time on the device.
                            (U//FOUO) The date and time will be displayed
                            in UTC time. For example Tuesday May 26, 1992
                            2:30:15 PM UTC is displayed as: 1992-5-26,14:30:15.0"
        ::= { dpiNtpCTConfigurationScalarGroup 2 }

    dpiNtpCTServerConfiguration OBJECT IDENTIFIER ::= { dpiNtpCTInterface 2 }

    dpiNtpCTServerConfigTableCount OBJECT-TYPE
        SYNTAX              Unsigned32
        MAX-ACCESS          read-only
        STATUS              current
        DESCRIPTION         "(U//FOUO) The number of rows in the dpiNtpCTServerTable."
        ::= { dpiNtpCTServerConfiguration 1 }

    dpiNtpCTServerConfigTableLastChanged OBJECT-TYPE
        SYNTAX              TimeStamp
        MAX-ACCESS          read-only
        STATUS              current
        DESCRIPTION         "(U//FOUO) The value of hSysUpTime the last time
                            any entry in the dpiNtpCTServerTable was modified,created,
                            or deleted by either SNMP or other management
                            method (e.g via an HMI). (U//FOUO)Manager can
                            use this object to ensure that no changes to
                            configuration of this table have happened since
                            the last time it examined the table.
                            
                            (U//FOUO) A value of 0 indicates that no entry
                            has been changed since the agent initialized."
        ::= { dpiNtpCTServerConfiguration 2 }

    dpiNtpCTServerTable OBJECT-TYPE
        SYNTAX              SEQUENCE OF DpiNtpCTServerEntry
        MAX-ACCESS          not-accessible
        STATUS              current
        DESCRIPTION         "(U//FOUO) The table that configures and lists
                            the Simple Network Time Protocol Servers for
                            the CT interface."
        ::= { dpiNtpCTServerConfiguration 3 }

    dpiNtpCTServerEntry OBJECT-TYPE
        SYNTAX              DpiNtpCTServerEntry
        MAX-ACCESS          not-accessible
        STATUS              current
        DESCRIPTION         "(U//FOUO) A row describing characteristics of
                            the NTP Server."
        INDEX               {
                                dpiNtpCTServerAddressType,
                                dpiNtpCTServerAddress
                            }
        ::= { dpiNtpCTServerTable 1 }

    DpiNtpCTServerEntry ::= SEQUENCE {
        dpiNtpCTServerAddressType		InetAddressType,
        dpiNtpCTServerAddress 			InetAddress,
        dpiNtpCTServerPortNumber 		InetPortNumber,
        dpiNtpCTServerIntf 				Unsigned32,
        dpiNtpCTServerMinPollingRate 	DpiNtpPollingRate,
        dpiNtpCTServerMaxPollingRate 	DpiNtpPollingRate,
        dpiNtpCTServerOffset	 		Unsigned32,
        dpiNtpCTServerDelay 			Unsigned32,
        dpiNtpCTServerStatus  			DpiNtpServerStatus,
        dpiNtpCTServerRowStatus  		RowStatus
    }

    dpiNtpCTServerAddressType OBJECT-TYPE
        SYNTAX              InetAddressType
        MAX-ACCESS          not-accessible
        STATUS              current
        DESCRIPTION         "(U//FOUO) The type of address of the server."
        ::= { dpiNtpCTServerEntry 1 }

    dpiNtpCTServerAddress OBJECT-TYPE
        SYNTAX              InetAddress
        MAX-ACCESS          not-accessible
        STATUS              current
        DESCRIPTION         "(U//FOUO) The IP address of the NTP server. (U//FOUO)
                            This IP address must be consistent to the IP
                            address type in dpiNtpCTServerAddressType. Attempts
                            to set this object to a value inconsistent with
                            must fail with an inconsistentValue error."
        ::= { dpiNtpCTServerEntry 2 }

    dpiNtpCTServerPortNumber OBJECT-TYPE
        SYNTAX              InetPortNumber
        MAX-ACCESS          read-create
        STATUS              current
        DESCRIPTION         "(U//FOUO) The port number of the NTP server."
        DEFVAL              { 123 }
        ::= { dpiNtpCTServerEntry 3 }

    dpiNtpCTServerIntf OBJECT-TYPE
        SYNTAX              Unsigned32
        MAX-ACCESS          read-create
        STATUS              current
        DESCRIPTION         "(U//FOUO) The interface off which to find the
                            NTP server."
        ::= { dpiNtpCTServerEntry 4 }

    dpiNtpCTServerMinPollingRate OBJECT-TYPE
        SYNTAX              DpiNtpPollingRate
        MAX-ACCESS          read-create
        STATUS              current
        DESCRIPTION         "(U//FOUO) The minimum polling rate of the NTP
                            server. (U//FOUO) If the device is being configured
                            for static polling, set this value to equal dpiNtpCTServerMaxPollingRate."
        DEFVAL              { 1024 }
        ::= { dpiNtpCTServerEntry 5 }

    dpiNtpCTServerMaxPollingRate OBJECT-TYPE
        SYNTAX              DpiNtpPollingRate
        MAX-ACCESS          read-create
        STATUS              current
        DESCRIPTION         "(U//FOUO) The maximum polling rate of the NTP
                            server. (U//FOUO) If the device is being configured
                            for static polling, set this value to equal dpiNtpCTServerMinPollingRate."
        DEFVAL              { 4096 }
        ::= { dpiNtpCTServerEntry 6 }

    dpiNtpCTServerOffset OBJECT-TYPE
        SYNTAX              Unsigned32
        MAX-ACCESS          read-only
        STATUS              current
        DESCRIPTION         "(U//FOUO) The time offset to the NTP server."
        ::= { dpiNtpCTServerEntry 7 }

    dpiNtpCTServerDelay OBJECT-TYPE
        SYNTAX              Unsigned32
        MAX-ACCESS          read-only
        STATUS              current
        DESCRIPTION         "(U//FOUO) The network delay of the NTP server."
        ::= { dpiNtpCTServerEntry 8 }

    dpiNtpCTServerStatus OBJECT-TYPE
        SYNTAX              DpiNtpServerStatus
        MAX-ACCESS          read-only
        STATUS              current
        DESCRIPTION         "(U//FOUO) The current status of the connection
                            to the time server. (U//FOUO) FUTURE: If the
                            status is fail, then an Event Notification will
                            be triggered."
        ::= { dpiNtpCTServerEntry 9 }

    dpiNtpCTServerRowStatus OBJECT-TYPE
        SYNTAX              RowStatus
        MAX-ACCESS          read-create
        STATUS              current
        DESCRIPTION         "(U//FOUO) The status of the row by which new entries
                            may be created, existing entries modified or
                            deleted from this table."
        ::= { dpiNtpCTServerEntry 10 }
        
    dpiNotifs OBJECT IDENTIFIER ::= { dpiFeature 3 }       
        
    dpiRuleSetNotifs OBJECT IDENTIFIER ::= { dpiNotifs 1 }

    dpiRuleSetNotifVariables OBJECT IDENTIFIER ::= { dpiRuleSetNotifs 1 }
    
    dpiNtpDateTime OBJECT-TYPE
        SYNTAX              DateAndTime
        MAX-ACCESS          accessible-for-notify
        STATUS              current
        DESCRIPTION         "(U//FOUO) The NTP time of the Rule Set 
						    installation."
        ::= { dpiRuleSetNotifVariables 1 }

    dpiRSRuleSetName OBJECT-TYPE
        SYNTAX              SnmpAdminString (SIZE(1..64))
        MAX-ACCESS          accessible-for-notify
        STATUS              current
        DESCRIPTION         "(U//FOUO) The name of the Rule Set that was 
							installed."
        ::= { dpiRuleSetNotifVariables 2 }
        
    dpiRuleSetInstallationFailureReason OBJECT-TYPE
        SYNTAX INTEGER {
			fileTransferFailure( 1 ),
			invalidHeaderCRC( 2 ),
			invalidHeaderFileType( 3 ),
			invalidHeaderFileSize( 4 ),
			invalidImageOrder( 5 ),
			downloadNotAllowed( 6 ),
			fileNotFound( 7 ),
			invalidAuthSignature( 8 ),
			ruleSetLoadFailed( 9 ),
			installAttemptFailed( 10 ),
			configTableNotFound( 11 ),
			graphAlreadyExists( 12 ),
			graphDoesNotExist( 13 ),
			cannotAllocateMemory( 14 ),
			cannotOpenGraphFile( 15 ),
			decryptionFailed( 16 )
		}
        MAX-ACCESS          accessible-for-notify
        STATUS              current
        DESCRIPTION         "(U//FOUO) This is the reason for the Rule Set 
							installation failure."
        ::= { dpiRuleSetNotifVariables 3 }

    -- unofficial definition (CHIMERA Team)
    dpiReason OBJECT-TYPE
        SYNTAX INTEGER {
			timeout( 1 )
		}
        MAX-ACCESS          accessible-for-notify
        STATUS              current
        DESCRIPTION         "(U//FOUO) The reason for a DPI operation."
        ::= { dpiRuleSetNotifVariables 4 }

    -- unofficial definition (CHIMERA Team)
    dpiCoreID OBJECT-TYPE
        SYNTAX              Unsigned32
        MAX-ACCESS          accessible-for-notify
        STATUS              current
        DESCRIPTION         "(U//FOUO) The DPI Core ID."
        ::= { dpiRuleSetNotifVariables 5 }

    dpiRuleSetNotifEvents OBJECT IDENTIFIER ::= { dpiRuleSetNotifs 2 }

    dpiRuleSetInstallationSucceeded NOTIFICATION-TYPE
        OBJECTS	{
			commonStationID,
			commonSystemDate,
			commonIfIndex,
			dpiNtpDateTime,
			dpiRSRuleSetName
		}
        STATUS				current
        DESCRIPTION         "(U//FOUO) This notification is sent when a Rule 
                            Set has been installed."
        ::= { dpiRuleSetNotifEvents 1 }

    dpiRuleSetInstallationFailed NOTIFICATION-TYPE
        OBJECTS	{
			commonStationID,
			commonSystemDate,
			commonIfIndex,
			dpiRuleSetInstallationFailureReason
		}
        STATUS		   	 	current
        DESCRIPTION         "(U//FOUO) This notification is sent when a Rule 
                            Set fails installation."
        ::= { dpiRuleSetNotifEvents 2 }

    -- unofficial definition (CHIMERA Team)
    dpiKnownAnswerTestFailed NOTIFICATION-TYPE
        OBJECTS	{
			commonStationID,
			commonSystemDate,
			commonIfIndex,
			dpiCoreID,
			dpiReason
		}
        STATUS		   	 	current
        DESCRIPTION         "(U//FOUO) This notification is sent when a known 
                            answer test fails."
        ::= { dpiRuleSetNotifEvents 3 }

    dpiFeatureConformance OBJECT IDENTIFIER ::= { dpiFeature 4 }

    dpiFeatureGroups OBJECT IDENTIFIER ::= { dpiFeatureConformance 1 }

    dpiFeatureGroup OBJECT-GROUP
        OBJECTS	{
			dpiEnable,
			dpiMode,
			dpiUnsupEthFramePrtclAction,
			dpiNfPTEnable,
			dpiNfPTFlowActiveTimeout,
			dpiNfPTFlowInactiveTimeout,
			dpiNfPTExportConfigTableCount,
			dpiNfPTExportConfigTableLastChanged,
			dpiNfPTExpClctrPortNumber,
			dpiNfPTExpClctrIntf,
			dpiNfPTExpClctrTemplateTimeout,
			dpiNfPTExpClctrRowStatus,
			dpiNfCTEnable,
			dpiNfCTFlowActiveTimeout,
			dpiNfCTFlowInactiveTimeout,
			dpiNfCTExportConfigTableCount,
			dpiNfCTExportConfigTableLastChanged,
			dpiNfCTExpClctrPortNumber,
			dpiNfCTExpClctrIntf,
			dpiNfCTExpClctrTemplateTimeout,
			dpiNfCTExpClctrRowStatus,
			dpiRSPTClear,
			dpiRSPTRuleSet,
			dpiRSCTClear,
			dpiRSCTRuleSet,
			dpiRSInstallInterface,
			dpiRSInstallURI,
			dpiRSInstallAuthCode,
			dpiRSInstallOperStatus,
			dpiAlertsPTEnable,
			dpiAlertPTServerConfigTableCount,
			dpiAlertPTServerConfigTableLastChanged,
			dpiAlertPTServerAddressType,
			dpiAlertPTServerAddress,
			dpiAlertPTServerPortNumber,
			dpiAlertPTServerIntf,
			dpiAlertPTServerFormat,
			dpiAlertPTServerRowStatus,
			dpiAlertsCTEnable,
			dpiAlertCTServerConfigTableCount,
			dpiAlertCTServerConfigTableLastChanged,
			dpiAlertCTServerAddressType,
			dpiAlertCTServerAddress,
			dpiAlertCTServerPortNumber,
			dpiAlertCTServerIntf,
			dpiAlertCTServerFormat,
			dpiAlertCTServerRowStatus,
			dpiNtpPTEnable,
			dpiNtpPTDateTime,
			dpiNtpPTServerConfigTableCount,
			dpiNtpPTServerConfigTableLastChanged,
			dpiNtpPTServerPortNumber,
			dpiNtpPTServerIntf,
			dpiNtpPTServerMinPollingRate,
			dpiNtpPTServerMaxPollingRate,
			dpiNtpPTServerOffset,
			dpiNtpPTServerDelay,
			dpiNtpPTServerStatus,
			dpiNtpPTServerRowStatus,
			dpiNtpCTEnable,
			dpiNtpCTDateTime,
			dpiNtpCTServerConfigTableCount,
			dpiNtpCTServerConfigTableLastChanged,
			dpiNtpCTServerPortNumber,
			dpiNtpCTServerIntf,
			dpiNtpCTServerMinPollingRate,
			dpiNtpCTServerMaxPollingRate,
			dpiNtpCTServerOffset,
			dpiNtpCTServerDelay,
			dpiNtpCTServerStatus,
			dpiNtpCTServerRowStatus
		}
        STATUS		    	current
        DESCRIPTION         "(U//FOUO) The objects related to the DPI Feature."
        ::= { dpiFeatureGroups 1 }

    dpiNotifVariablesGroup OBJECT-GROUP
        OBJECTS	{
			dpiNtpDateTime,
			dpiRSRuleSetName,
			dpiRuleSetInstallationFailureReason
		}
        STATUS		    	current
        DESCRIPTION         "(U//FOUO) The notification variables associated
                            with DPI."
        ::= { dpiFeatureGroups 2 }

    dpiNotifEventsGroup NOTIFICATION-GROUP
        NOTIFICATIONS {
			dpiRuleSetInstallationSucceeded,
			dpiRuleSetInstallationFailed
		}
        STATUS		    	current
        DESCRIPTION         "(U//FOUO) The notifications associated with DPI."
        ::= { dpiFeatureGroups 3 }
END
