--BEGIN Revision History
--
--20120508 - E. Clark - Original.
--
--END Revision History

GDC4S-PACKET-STATISTICS-MIB DEFINITIONS ::= BEGIN
    IMPORTS
    MODULE-IDENTITY, OBJECT-TYPE, Unsigned32,
    Counter64
        FROM SNMPv2-SMI
    OBJECT-GROUP
        FROM SNMPv2-CONF
    gdc4sFeatureHierarchy
        FROM GDC4S-FEATURE-MIB
    TruthValue, TimeStamp
        FROM SNMPv2-TC;

    pstatsFeature MODULE-IDENTITY
        LAST-UPDATED	    "201201300000Z"
        ORGANIZATION	    "General Dynamics C4 Systems"
        CONTACT-INFO        "Infosec Support                              
                            
                            
                            
                            General Dynamics C4
                            Systems Corporation
                            77 A Street
                            Needham Heights, MA
                            02494-2806
                            Telephone: 877-230-0236
                            email: INFOSECSUPPORT@GDC4S.COM"
        DESCRIPTION         "This MIB supports additional MIB features necessary 
                            to configure the devices developed by General
                            Dynamics C4 Systems."

        ::= { gdc4sFeatureHierarchy 2 }


    --**********************************************************************
    --PACKET-STATISTICS
    --**********************************************************************
    pstatsFeatureElements OBJECT IDENTIFIER ::= { pstatsFeature 1 }

    pstatsPacketStatistics OBJECT IDENTIFIER ::= { pstatsFeatureElements 1 }

    pstatsPacketStatisticsClear OBJECT-TYPE
        SYNTAX              TruthValue
        MAX-ACCESS          read-write
        STATUS              current
        DESCRIPTION         "(U//FOUO) Setting this object to 'true' will clear 
                            all packet statistics. When read this object
                            should return 'false'."
        ::= { pstatsPacketStatistics 1 }

    pstatsPacketStatisticsTable OBJECT-TYPE
        SYNTAX              SEQUENCE OF PstatsPacketStatisticsEntry
        MAX-ACCESS          not-accessible
        STATUS              current
        DESCRIPTION         "(U//FOUO) Contains packet statistics indexed by 
                            interface."
        ::= { pstatsPacketStatistics 2 }

    pstatsPacketStatisticsEntry OBJECT-TYPE
        SYNTAX              PstatsPacketStatisticsEntry
        MAX-ACCESS          not-accessible
        STATUS              current
        DESCRIPTION         "(U//FOUO) A row in the pstatsPacketStatisticsTable."
        INDEX               {
                                pstatsPacketStatisticsSide
                            }
        ::= { pstatsPacketStatisticsTable 1 }

    PstatsPacketStatisticsEntry ::= SEQUENCE {
        pstatsPacketStatisticsSide
            Unsigned32,
        pstatsPacketStatisticsRxDroppedPackets
            Counter64,
        pstatsPacketStatisticsRxTotalPackets
            Counter64,
        pstatsPacketStatisticsTxTotalPackets
            Counter64,
        pstatsPacketStatisticsPceRxDroppedPackets
            Counter64,
        pstatsPacketStatisticsPceRxTotalPackets
            Counter64,
        pstatsPacketStatisticsPceTxTotalPackets
            Counter64,
        pstatsPacketStatisticsNisRxTotalPackets
            Counter64,
        pstatsPacketStatisticsNisTxTotalPackets
            Counter64,
        pstatsPacketStatisticsNisRxPacketFragments
            Counter64,
        pstatsPacketStatisticsReassembleRxPackets
            Counter64
    }

    pstatsPacketStatisticsSide OBJECT-TYPE
        SYNTAX              Unsigned32
        MAX-ACCESS          not-accessible
        STATUS              current
        DESCRIPTION         "(U//FOUO) The device side (PT(1)/CT(2))."
        ::= { pstatsPacketStatisticsEntry 1 }

    pstatsPacketStatisticsRxDroppedPackets OBJECT-TYPE
        SYNTAX              Counter64
        MAX-ACCESS          read-only
        STATUS              current
        DESCRIPTION         "(U//FOUO) The number of received packets that 
                            have been dropped."
        ::= { pstatsPacketStatisticsEntry 2 }

    pstatsPacketStatisticsRxTotalPackets OBJECT-TYPE
        SYNTAX              Counter64
        MAX-ACCESS          read-only
        STATUS              current
        DESCRIPTION         "(U//FOUO) The total number of received packets."
        ::= { pstatsPacketStatisticsEntry 3 }

    pstatsPacketStatisticsTxTotalPackets OBJECT-TYPE
        SYNTAX              Counter64
        MAX-ACCESS          read-only
        STATUS              current
        DESCRIPTION         "(U//FOUO) Total number of transmitted packets."
        ::= { pstatsPacketStatisticsEntry 4 }

    pstatsPacketStatisticsPceRxDroppedPackets OBJECT-TYPE
        SYNTAX              Counter64
        MAX-ACCESS          read-only
        STATUS              current
        DESCRIPTION         "(U//FOUO) The number of packets received by the 
                            PCE that have been dropped."
        ::= { pstatsPacketStatisticsEntry 5 }

    pstatsPacketStatisticsPceRxTotalPackets OBJECT-TYPE
        SYNTAX              Counter64
        MAX-ACCESS          read-only
        STATUS              current
        DESCRIPTION         "(U//FOUO) The total number of packets received 
                            by the PCE."
        ::= { pstatsPacketStatisticsEntry 6 }

    pstatsPacketStatisticsPceTxTotalPackets OBJECT-TYPE
        SYNTAX              Counter64
        MAX-ACCESS          read-only
        STATUS              current
        DESCRIPTION         "(U//FOUO) The total number of packets transmitted 
                            by the PCE."
        ::= { pstatsPacketStatisticsEntry 7 }

    pstatsPacketStatisticsNisRxTotalPackets OBJECT-TYPE
        SYNTAX              Counter64
        MAX-ACCESS          read-only
        STATUS              current
        DESCRIPTION         "(U//FOUO) The total number of packets received 
                            by the NIS."
        ::= { pstatsPacketStatisticsEntry 8 }

    pstatsPacketStatisticsNisTxTotalPackets OBJECT-TYPE
        SYNTAX              Counter64
        MAX-ACCESS          read-only
        STATUS              current
        DESCRIPTION         "(U//FOUO) The total number of packets the Control 
                            Plane injected into the Fast Path."
        ::= { pstatsPacketStatisticsEntry 9 }

    pstatsPacketStatisticsNisRxPacketFragments OBJECT-TYPE
        SYNTAX              Counter64
        MAX-ACCESS          read-only
        STATUS              current
        DESCRIPTION         "(U//FOUO) The number of fragmented ESP packets 
                            that were received from the network interface
                            and were forwarded to IP reassembly processing.
                            Note, this statistic is only applicable for the
                            CT side."
        ::= { pstatsPacketStatisticsEntry 10 }

    pstatsPacketStatisticsReassembleRxPackets OBJECT-TYPE
        SYNTAX              Counter64
        MAX-ACCESS          read-only
        STATUS              current
        DESCRIPTION         "(U//FOUO) The number of reassembled ESP packets 
                            that were sent to the Fast Path to be decrypted.
                            Note, this statistic is only applicable for the
                            CT side."
        ::= { pstatsPacketStatisticsEntry 11 }

    pstatsPacketStatisticsCollectSAStats OBJECT-TYPE
        SYNTAX              TruthValue
        MAX-ACCESS          read-write
        STATUS              current
        DESCRIPTION         "(U//FOUO) Setting this object to 'true' will 
                            enable collection of per SA packet statistics. 
							When read this object should return its value. 
							If this object is set to the same value as the 
							current value, the device must not perform any 
							operation but should accept this as a valid SET 
							operation."
        ::= { pstatsPacketStatistics 3 }		
		
    pstatsFeatureConformance OBJECT IDENTIFIER ::= { pstatsFeature 2 }

    pstatsFeatureGroups OBJECT IDENTIFIER ::= { pstatsFeatureConformance 1 }

    pstatsFeatureGroup OBJECT-GROUP
        OBJECTS	{
        		pstatsPacketStatisticsRxDroppedPackets,
        		pstatsPacketStatisticsRxTotalPackets,
        		pstatsPacketStatisticsTxTotalPackets,
        		pstatsPacketStatisticsPceRxDroppedPackets,
        		pstatsPacketStatisticsPceRxTotalPackets,
        		pstatsPacketStatisticsPceTxTotalPackets,
        		pstatsPacketStatisticsNisRxTotalPackets,
        		pstatsPacketStatisticsNisTxTotalPackets,
        		pstatsPacketStatisticsNisRxPacketFragments,
        		pstatsPacketStatisticsReassembleRxPackets,
        		pstatsPacketStatisticsClear,
				pstatsPacketStatisticsCollectSAStats
        	}
        STATUS		    current
        DESCRIPTION         "(U//FOUO) The objects related to the Packet Statistics 
                            Feature."
        ::= { pstatsFeatureGroups 1 }


END
