TACLANE-PRODUCTS-REGISTRATION-MIB DEFINITIONS ::= BEGIN
    IMPORTS
    MODULE-IDENTITY, OBJECT-IDENTITY
        FROM SNMPv2-SMI
    taclaneProducts
        FROM GDC4S-ENCRYPTION-PRODUCTS-MIB;

    taclaneProductsRegistrationMIB MODULE-IDENTITY
        LAST-UPDATED	    "201011031745Z"
        ORGANIZATION	    "General Dynamics C4 Systems Corp."
        CONTACT-INFO        "Infosec Support General Dynamics C4 Systems Corporation
                            77 A Street
                            Needham Heights, MA
                            02494-2806
                            Telephone: 877-230-0236
                            email: INFOSECSUPPORT@GDC4S.COM"
        DESCRIPTION         "This MIB module provides the Object-Identity objects
                            referenced by sysObjectID to identify the platform
                            and software version of managed TACLANE Network
                            Encryptor."

        REVISION	    "200907301745Z"
        DESCRIPTION         "initial version of this module"
        ::= { taclaneProducts 3 }


    taclaneGigERegistrations OBJECT IDENTIFIER ::= { taclaneProductsRegistrationMIB 1 }

    taclaneGigER3 OBJECT IDENTIFIER ::= { taclaneGigERegistrations 3 }

    taclaneGigER35 OBJECT-IDENTITY
        STATUS		current
        DESCRIPTION         "(U//FOUO) The Object-Identity for the TACLANE-GigE
                            platform running an undefined version of Revision
                            3.5 of the software image."
        ::= { taclaneGigER3 5 }

    taclaneGigER35v1 OBJECT-IDENTITY
        STATUS		current
        DESCRIPTION         "(U//FOUO) The Object-Identity for the TACLANE-GigE
                            platform running Revision 3.5 version 1 of the
                            software image."
        ::= { taclaneGigER35 1 }

    taclaneGigER35v2 OBJECT-IDENTITY
        STATUS		current
        DESCRIPTION         "(U//FOUO) The Object-Identity for the TACLANE-GigE
                            platform running Revision 3.5 version 2 of the
                            software image."
        ::= { taclaneGigER35 2 }

    taclaneGigER35v3 OBJECT-IDENTITY
        STATUS		current
        DESCRIPTION         "(U//FOUO) The Object-Identity for the TACLANE-GigE
                            platform running Revision 3.5 version 3 of the
                            software image."
        ::= { taclaneGigER35 3 }

    taclaneGigER35v4 OBJECT-IDENTITY
        STATUS		current
        DESCRIPTION         "(U//FOUO) The Object-Identity for the TACLANE-GigE
                            platform running Revision 3.5 version 4 of the
                            software image."
        ::= { taclaneGigER35 4 }

    taclaneGigER35v5 OBJECT-IDENTITY
        STATUS		current
        DESCRIPTION         "(U//FOUO) The Object-Identity for the TACLANE-GigE
                            platform running Revision 3.5 version 5 of the
                            software image."
        ::= { taclaneGigER35 5 }

    taclaneGigER35v6 OBJECT-IDENTITY
        STATUS		current
        DESCRIPTION         "(U//FOUO) The Object-Identity for the TACLANE-GigE
                            platform running Revision 3.5 version 6 of the
                            software image."
        ::= { taclaneGigER35 6 }

    taclaneGigER35v7 OBJECT-IDENTITY
        STATUS		current
        DESCRIPTION         "(U//FOUO) The Object-Identity for the TACLANE-GigE
                            platform running Revision 3.5 version 7 of the
                            software image."
        ::= { taclaneGigER35 7 }

    taclaneGigER35v8 OBJECT-IDENTITY
        STATUS		current
        DESCRIPTION         "(U//FOUO) The Object-Identity for the TACLANE-GigE
                            platform running Revision 3.5 version 8 of the
                            software image."
        ::= { taclaneGigER35 8 }

    taclaneGigER35v9 OBJECT-IDENTITY
        STATUS		current
        DESCRIPTION         "(U//FOUO) The Object-Identity for the TACLANE-GigE
                            platform running Revision 3.5 version 9 of the
                            software image."
        ::= { taclaneGigER35 9 }

    taclaneGigER35v10 OBJECT-IDENTITY
        STATUS		current
        DESCRIPTION         "(U//FOUO) The Object-Identity for the TACLANE-GigE
                            platform running Revision 3.5 version 10 of the
                            software image."
        ::= { taclaneGigER35 10 }

    taclaneMiniRegistrations OBJECT IDENTIFIER ::= { taclaneProductsRegistrationMIB 2 }

    taclaneMiniR3 OBJECT IDENTIFIER ::= { taclaneMiniRegistrations 3 }

    taclaneMiniR35 OBJECT-IDENTITY
        STATUS		current
        DESCRIPTION         "(U//FOUO) The Object-Identity for the TACLANE-Mini
                            platform running an undefined version of Revision
                            3.5 of the software image."
        ::= { taclaneMiniR3 5 }

    taclaneMiniR35v1 OBJECT-IDENTITY
        STATUS		current
        DESCRIPTION         "(U//FOUO) The Object-Identity for the TACLANE-Mini
                            platform running Revision 3.5 version 1 of the
                            software image."
        ::= { taclaneMiniR35 1 }

    taclaneMiniR35v2 OBJECT-IDENTITY
        STATUS		current
        DESCRIPTION         "(U//FOUO) The Object-Identity for the TACLANE-Mini
                            platform running Revision 3.5 version 2 of the
                            software image."
        ::= { taclaneMiniR35 2 }

    taclaneMiniR35v3 OBJECT-IDENTITY
        STATUS		current
        DESCRIPTION         "(U//FOUO) The Object-Identity for the TACLANE-Mini
                            platform running Revision 3.5 version 3 of the
                            software image."
        ::= { taclaneMiniR35 3 }

    taclaneMiniR35v4 OBJECT-IDENTITY
        STATUS		current
        DESCRIPTION         "(U//FOUO) The Object-Identity for the TACLANE-Mini
                            platform running Revision 3.5 version 4 of the
                            software image."
        ::= { taclaneMiniR35 4 }

    taclaneMiniR35v5 OBJECT-IDENTITY
        STATUS		current
        DESCRIPTION         "(U//FOUO) The Object-Identity for the TACLANE-Mini
                            platform running Revision 3.5 version 5 of the
                            software image."
        ::= { taclaneMiniR35 5 }

    taclaneMiniR35v6 OBJECT-IDENTITY
        STATUS		current
        DESCRIPTION         "(U//FOUO) The Object-Identity for the TACLANE-Mini
                            platform running Revision 3.5 version 6 of the
                            software image."
        ::= { taclaneMiniR35 6 }

    taclaneMiniR35v7 OBJECT-IDENTITY
        STATUS		current
        DESCRIPTION         "(U//FOUO) The Object-Identity for the TACLANE-Mini
                            platform running Revision 3.5 version 7 of the
                            software image."
        ::= { taclaneMiniR35 7 }

    taclaneMiniR35v8 OBJECT-IDENTITY
        STATUS		current
        DESCRIPTION         "(U//FOUO) The Object-Identity for the TACLANE-Mini
                            platform running Revision 3.5 version 8 of the
                            software image."
        ::= { taclaneMiniR35 8 }

    taclaneMiniR35v9 OBJECT-IDENTITY
        STATUS		current
        DESCRIPTION         "(U//FOUO) The Object-Identity for the TACLANE-Mini
                            platform running Revision 3.5 version 9 of the
                            software image."
        ::= { taclaneMiniR35 9 }

    taclaneMiniR35v10 OBJECT-IDENTITY
        STATUS		current
        DESCRIPTION         "(U//FOUO) The Object-Identity for the TACLANE-Mini
                            platform running Revision 3.5 version 10 of the
                            software image."
        ::= { taclaneMiniR35 10 }

    taclaneMicroRegistrations OBJECT IDENTIFIER ::= { taclaneProductsRegistrationMIB 3 }

    taclaneMicroR3 OBJECT IDENTIFIER ::= { taclaneMicroRegistrations 3 }

    taclaneMicroR33 OBJECT-IDENTITY
        STATUS		current
        DESCRIPTION         "(U//FOUO) The Object-Identity for the TACLANE-Micro
                            platform running an undefined version of Revision
                            3.3 of the software image."
        ::= { taclaneMicroR3 3 }

    taclaneMicroR33v1 OBJECT-IDENTITY
        STATUS		current
        DESCRIPTION         "(U//FOUO) The Object-Identity for the TACLANE-Micro
                            platform running Revision 3.3 version 1 of the
                            software image."
        ::= { taclaneMicroR33 1 }

    taclaneMicroR33v2 OBJECT-IDENTITY
        STATUS		current
        DESCRIPTION         "(U//FOUO) The Object-Identity for the TACLANE-Micro
                            platform running Revision 3.3 version 2 of the
                            software image."
        ::= { taclaneMicroR33 2 }

    taclaneMicroR33v3 OBJECT-IDENTITY
        STATUS		current
        DESCRIPTION         "(U//FOUO) The Object-Identity for the TACLANE-Micro
                            platform running Revision 3.3 version 3 of the
                            software image."
        ::= { taclaneMicroR33 3 }

    taclaneMicroR33v4 OBJECT-IDENTITY
        STATUS		current
        DESCRIPTION         "(U//FOUO) The Object-Identity for the TACLANE-Micro
                            platform running Revision 3.3 version 4 of the
                            software image."
        ::= { taclaneMicroR33 4 }

    taclaneMicroR33v5 OBJECT-IDENTITY
        STATUS		current
        DESCRIPTION         "(U//FOUO) The Object-Identity for the TACLANE-Micro
                            platform running Revision 3.3 version 5 of the
                            software image."
        ::= { taclaneMicroR33 5 }

    taclaneMicroR33v6 OBJECT-IDENTITY
        STATUS		current
        DESCRIPTION         "(U//FOUO) The Object-Identity for the TACLANE-Micro
                            platform running Revision 3.3 version 6 of the
                            software image."
        ::= { taclaneMicroR33 6 }

    taclaneMicroR33v7 OBJECT-IDENTITY
        STATUS		current
        DESCRIPTION         "(U//FOUO) The Object-Identity for the TACLANE-Micro
                            platform running Revision 3.3 version 7 of the
                            software image."
        ::= { taclaneMicroR33 7 }

    taclaneMicroR33v8 OBJECT-IDENTITY
        STATUS		current
        DESCRIPTION         "(U//FOUO) The Object-Identity for the TACLANE-Micro
                            platform running Revision 3.3 version 8 of the
                            software image."
        ::= { taclaneMicroR33 8 }

    taclaneMicroR33v9 OBJECT-IDENTITY
        STATUS		current
        DESCRIPTION         "(U//FOUO) The Object-Identity for the TACLANE-Micro
                            platform running Revision 3.3 version 9 of the
                            software image."
        ::= { taclaneMicroR33 9 }

    taclaneMicroR33v10 OBJECT-IDENTITY
        STATUS		current
        DESCRIPTION         "(U//FOUO) The Object-Identity for the TACLANE-Micro
                            platform running Revision 3.3 version 10 of the
                            software image."
        ::= { taclaneMicroR33 10 }

    taclaneMicroR34 OBJECT-IDENTITY
        STATUS		current
        DESCRIPTION         "(U//FOUO) The Object-Identity for the TACLANE-Micro
                            platform running an undefined version of Revision
                            3.4 of the software image."
        ::= { taclaneMicroR3 4 }

    taclaneMicroR34v1 OBJECT-IDENTITY
        STATUS		current
        DESCRIPTION         "(U//FOUO) The Object-Identity for the TACLANE-Micro
                            platform running Revision 3.4 version 1 of the
                            software image."
        ::= { taclaneMicroR34 1 }

    taclaneMicroR34v2 OBJECT-IDENTITY
        STATUS		current
        DESCRIPTION         "(U//FOUO) The Object-Identity for the TACLANE-Micro
                            platform running Revision 3.4 version 2 of the
                            software image."
        ::= { taclaneMicroR34 2 }

    taclaneMicroR34v3 OBJECT-IDENTITY
        STATUS		current
        DESCRIPTION         "(U//FOUO) The Object-Identity for the TACLANE-Micro
                            platform running Revision 3.4 version 3 of the
                            software image."
        ::= { taclaneMicroR34 3 }

    taclaneMicroR34v4 OBJECT-IDENTITY
        STATUS		current
        DESCRIPTION         "(U//FOUO) The Object-Identity for the TACLANE-Micro
                            platform running Revision 3.4 version 4 of the
                            software image."
        ::= { taclaneMicroR34 4 }

    taclaneMicroR34v5 OBJECT-IDENTITY
        STATUS		current
        DESCRIPTION         "(U//FOUO) The Object-Identity for the TACLANE-Micro
                            platform running Revision 3.4 version 5 of the
                            software image."
        ::= { taclaneMicroR34 5 }

    taclaneMicroR34v6 OBJECT-IDENTITY
        STATUS		current
        DESCRIPTION         "(U//FOUO) The Object-Identity for the TACLANE-Micro
                            platform running Revision 3.4 version 6 of the
                            software image."
        ::= { taclaneMicroR34 6 }

    taclaneMicroR34v7 OBJECT-IDENTITY
        STATUS		current
        DESCRIPTION         "(U//FOUO) The Object-Identity for the TACLANE-Micro
                            platform running Revision 3.4 version 7 of the
                            software image."
        ::= { taclaneMicroR34 7 }

    taclaneMicroR34v8 OBJECT-IDENTITY
        STATUS		current
        DESCRIPTION         "(U//FOUO) The Object-Identity for the TACLANE-Micro
                            platform running Revision 3.4 version 8 of the
                            software image."
        ::= { taclaneMicroR34 8 }

    taclaneMicroR34v9 OBJECT-IDENTITY
        STATUS		current
        DESCRIPTION         "(U//FOUO) The Object-Identity for the TACLANE-Micro
                            platform running Revision 3.4 version 9 of the
                            software image."
        ::= { taclaneMicroR34 9 }

    taclaneMicroR34v10 OBJECT-IDENTITY
        STATUS		current
        DESCRIPTION         "(U//FOUO) The Object-Identity for the TACLANE-Micro
                            platform running Revision 3.4 version 10 of the
                            software image."
        ::= { taclaneMicroR34 10 }

    taclaneMicroR35 OBJECT-IDENTITY
        STATUS		current
        DESCRIPTION         "(U//FOUO) The Object-Identity for the TACLANE-Micro
                            platform running an undefined version of Revision
                            3.5 of the software image."
        ::= { taclaneMicroR3 5 }

    taclaneMicroR35v1 OBJECT-IDENTITY
        STATUS		current
        DESCRIPTION         "(U//FOUO) The Object-Identity for the TACLANE-Micro
                            platform running Revision 3.5 version 1 of the
                            software image."
        ::= { taclaneMicroR35 1 }

    taclaneMicroR35v2 OBJECT-IDENTITY
        STATUS		current
        DESCRIPTION         "(U//FOUO) The Object-Identity for the TACLANE-Micro
                            platform running Revision 3.5 version 2 of the
                            software image."
        ::= { taclaneMicroR35 2 }

    taclaneMicroR35v3 OBJECT-IDENTITY
        STATUS		current
        DESCRIPTION         "(U//FOUO) The Object-Identity for the TACLANE-Micro
                            platform running Revision 3.5 version 3 of the
                            software image."
        ::= { taclaneMicroR35 3 }

    taclaneMicroR35v4 OBJECT-IDENTITY
        STATUS		current
        DESCRIPTION         "(U//FOUO) The Object-Identity for the TACLANE-Micro
                            platform running Revision 3.5 version 4 of the
                            software image."
        ::= { taclaneMicroR35 4 }

    taclaneMicroR35v5 OBJECT-IDENTITY
        STATUS		current
        DESCRIPTION         "(U//FOUO) The Object-Identity for the TACLANE-Micro
                            platform running Revision 3.5 version 5 of the
                            software image."
        ::= { taclaneMicroR35 5 }

    taclaneMicroR35v6 OBJECT-IDENTITY
        STATUS		current
        DESCRIPTION         "(U//FOUO) The Object-Identity for the TACLANE-Micro
                            platform running Revision 3.5 version 6 of the
                            software image."
        ::= { taclaneMicroR35 6 }

    taclaneMicroR35v7 OBJECT-IDENTITY
        STATUS		current
        DESCRIPTION         "(U//FOUO) The Object-Identity for the TACLANE-Micro
                            platform running Revision 3.5 version 7 of the
                            software image."
        ::= { taclaneMicroR35 7 }

    taclaneMicroR35v8 OBJECT-IDENTITY
        STATUS		current
        DESCRIPTION         "(U//FOUO) The Object-Identity for the TACLANE-Micro
                            platform running Revision 3.5 version 8 of the
                            software image."
        ::= { taclaneMicroR35 8 }

    taclaneMicroR35v9 OBJECT-IDENTITY
        STATUS		current
        DESCRIPTION         "(U//FOUO) The Object-Identity for the TACLANE-Micro
                            platform running Revision 3.5 version 9 of the
                            software image."
        ::= { taclaneMicroR35 9 }

    taclaneMicroR35v10 OBJECT-IDENTITY
        STATUS		current
        DESCRIPTION         "(U//FOUO) The Object-Identity for the TACLANE-Micro
                            platform running Revision 3.5 version 10 of the
                            software image."
        ::= { taclaneMicroR35 10 }

    taclaneMicroR4 OBJECT IDENTIFIER ::= { taclaneMicroRegistrations 4 }

    taclaneMicroR41 OBJECT-IDENTITY
        STATUS		current
        DESCRIPTION         "(U//FOUO) The Object-Identity for the TACLANE-Micro
                            platform running an undefined version of Revision
                            4.1 of the software image."
        ::= { taclaneMicroR4 1 }

    taclaneMicroR41v1 OBJECT-IDENTITY
        STATUS		current
        DESCRIPTION         "(U//FOUO) The Object-Identity for the TACLANE-Micro
                            platform running Revision 4.1 version 1 of the
                            software image."
        ::= { taclaneMicroR41 1 }

    taclaneMicroR41v2 OBJECT-IDENTITY
        STATUS		current
        DESCRIPTION         "(U//FOUO) The Object-Identity for the TACLANE-Micro
                            platform running Revision 4.1 version 2 of the
                            software image."
        ::= { taclaneMicroR41 2 }

    taclaneMicroR41v3 OBJECT-IDENTITY
        STATUS		current
        DESCRIPTION         "(U//FOUO) The Object-Identity for the TACLANE-Micro
                            platform running Revision 4.1 version 3 of the
                            software image."
        ::= { taclaneMicroR41 3 }

    taclaneMicroR41v4 OBJECT-IDENTITY
        STATUS		current
        DESCRIPTION         "(U//FOUO) The Object-Identity for the TACLANE-Micro
                            platform running Revision 4.1 version 4 of the
                            software image."
        ::= { taclaneMicroR41 4 }

    taclaneMicroR41v5 OBJECT-IDENTITY
        STATUS		current
        DESCRIPTION         "(U//FOUO) The Object-Identity for the TACLANE-Micro
                            platform running Revision 4.1 version 5 of the
                            software image."
        ::= { taclaneMicroR41 5 }

    taclaneMicroR41v6 OBJECT-IDENTITY
        STATUS		current
        DESCRIPTION         "(U//FOUO) The Object-Identity for the TACLANE-Micro
                            platform running Revision 4.1 version 6 of the
                            software image."
        ::= { taclaneMicroR41 6 }

    taclaneMicroR41v7 OBJECT-IDENTITY
        STATUS		current
        DESCRIPTION         "(U//FOUO) The Object-Identity for the TACLANE-Micro
                            platform running Revision 4.1 version 7 of the
                            software image."
        ::= { taclaneMicroR41 7 }

    taclaneMicroR41v8 OBJECT-IDENTITY
        STATUS		current
        DESCRIPTION         "(U//FOUO) The Object-Identity for the TACLANE-Micro
                            platform running Revision 4.1 version 8 of the
                            software image."
        ::= { taclaneMicroR41 8 }

    taclaneMicroR41v9 OBJECT-IDENTITY
        STATUS		current
        DESCRIPTION         "(U//FOUO) The Object-Identity for the TACLANE-Micro
                            platform running Revision 4.1 version 9 of the
                            software image."
        ::= { taclaneMicroR41 9 }

    taclaneMicroR41v10 OBJECT-IDENTITY
        STATUS		current
        DESCRIPTION         "(U//FOUO) The Object-Identity for the TACLANE-Micro
                            platform running Revision 4.1 version 10 of the
                            software image."
        ::= { taclaneMicroR41 10 }

    taclaneVitaRegistrations OBJECT IDENTIFIER ::= { taclaneProductsRegistrationMIB 4 }

    taclaneVitaR3 OBJECT IDENTIFIER ::= { taclaneVitaRegistrations 3 }

    taclaneVitaR35 OBJECT-IDENTITY
        STATUS		current
        DESCRIPTION         "(U//FOUO) The Object-Identity for the TACLANE-Vita
                            platform running an undefined version of Revision
                            3.5 of the software image."
        ::= { taclaneVitaR3 5 }

    taclaneVitaR35v1 OBJECT-IDENTITY
        STATUS		current
        DESCRIPTION         "(U//FOUO) The Object-Identity for the TACLANE-Vita
                            platform running Revision 3.5 version 1 of the
                            software image."
        ::= { taclaneVitaR35 1 }

    taclaneVitaR35v2 OBJECT-IDENTITY
        STATUS		current
        DESCRIPTION         "(U//FOUO) The Object-Identity for the TACLANE-Vita
                            platform running Revision 3.5 version 2 of the
                            software image."
        ::= { taclaneVitaR35 2 }

    taclaneVitaR35v3 OBJECT-IDENTITY
        STATUS		current
        DESCRIPTION         "(U//FOUO) The Object-Identity for the TACLANE-Vita
                            platform running Revision 3.5 version 3 of the
                            software image."
        ::= { taclaneVitaR35 3 }

    taclaneVitaR35v4 OBJECT-IDENTITY
        STATUS		current
        DESCRIPTION         "(U//FOUO) The Object-Identity for the TACLANE-Vita
                            platform running Revision 3.5 version 4 of the
                            software image."
        ::= { taclaneVitaR35 4 }

    taclaneVitaR35v5 OBJECT-IDENTITY
        STATUS		current
        DESCRIPTION         "(U//FOUO) The Object-Identity for the TACLANE-Vita
                            platform running Revision 3.5 version 5 of the
                            software image."
        ::= { taclaneVitaR35 5 }

    taclaneVitaR35v6 OBJECT-IDENTITY
        STATUS		current
        DESCRIPTION         "(U//FOUO) The Object-Identity for the TACLANE-Vita
                            platform running Revision 3.5 version 6 of the
                            software image."
        ::= { taclaneVitaR35 6 }

    taclaneVitaR35v7 OBJECT-IDENTITY
        STATUS		current
        DESCRIPTION         "(U//FOUO) The Object-Identity for the TACLANE-Vita
                            platform running Revision 3.5 version 7 of the
                            software image."
        ::= { taclaneVitaR35 7 }

    taclaneVitaR35v8 OBJECT-IDENTITY
        STATUS		current
        DESCRIPTION         "(U//FOUO) The Object-Identity for the TACLANE-Vita
                            platform running Revision 3.5 version 8 of the
                            software image."
        ::= { taclaneVitaR35 8 }

    taclaneVitaR35v9 OBJECT-IDENTITY
        STATUS		current
        DESCRIPTION         "(U//FOUO) The Object-Identity for the TACLANE-Vita
                            platform running Revision 3.5 version 9 of the
                            software image."
        ::= { taclaneVitaR35 9 }

    taclaneVitaR35v10 OBJECT-IDENTITY
        STATUS		current
        DESCRIPTION         "(U//FOUO) The Object-Identity for the TACLANE-Vita
                            platform running Revision 3.5 version 10 of the
                            software image."
        ::= { taclaneVitaR35 10 }

    taclaneC100Registrations OBJECT IDENTIFIER ::= { taclaneProductsRegistrationMIB 5 }

    taclaneC100R3 OBJECT IDENTIFIER ::= { taclaneC100Registrations 3 }

    taclaneC100R35 OBJECT-IDENTITY
        STATUS		current
        DESCRIPTION         "(U//FOUO) The Object-Identity for the TACLANE-C100
                            platform running an undefined version of Revision
                            3.5 of the software image."
        ::= { taclaneC100R3 5 }

    taclaneC100R35v1 OBJECT-IDENTITY
        STATUS		current
        DESCRIPTION         "(U//FOUO) The Object-Identity for the TACLANE-C100
                            platform running Revision 3.5 version 1 of the
                            software image."
        ::= { taclaneC100R35 1 }

    taclaneC100R35v2 OBJECT-IDENTITY
        STATUS		current
        DESCRIPTION         "(U//FOUO) The Object-Identity for the TACLANE-C100
                            platform running Revision 3.5 version 2 of the
                            software image."
        ::= { taclaneC100R35 2 }

    taclaneC100R35v3 OBJECT-IDENTITY
        STATUS		current
        DESCRIPTION         "(U//FOUO) The Object-Identity for the TACLANE-C100
                            platform running Revision 3.5 version 3 of the
                            software image."
        ::= { taclaneC100R35 3 }

    taclaneC100R35v4 OBJECT-IDENTITY
        STATUS		current
        DESCRIPTION         "(U//FOUO) The Object-Identity for the TACLANE-C100
                            platform running Revision 3.5 version 4 of the
                            software image."
        ::= { taclaneC100R35 4 }

    taclaneC100R35v5 OBJECT-IDENTITY
        STATUS		current
        DESCRIPTION         "(U//FOUO) The Object-Identity for the TACLANE-C100
                            platform running Revision 3.5 version 5 of the
                            software image."
        ::= { taclaneC100R35 5 }

    taclaneC100R35v6 OBJECT-IDENTITY
        STATUS		current
        DESCRIPTION         "(U//FOUO) The Object-Identity for the TACLANE-C100
                            platform running Revision 3.5 version 6 of the
                            software image."
        ::= { taclaneC100R35 6 }

    taclaneC100R35v7 OBJECT-IDENTITY
        STATUS		current
        DESCRIPTION         "(U//FOUO) The Object-Identity for the TACLANE-C100
                            platform running Revision 3.5 version 7 of the
                            software image."
        ::= { taclaneC100R35 7 }

    taclaneC100R35v8 OBJECT-IDENTITY
        STATUS		current
        DESCRIPTION         "(U//FOUO) The Object-Identity for the TACLANE-C100
                            platform running Revision 3.5 version 8 of the
                            software image."
        ::= { taclaneC100R35 8 }

    taclaneC100R35v9 OBJECT-IDENTITY
        STATUS		current
        DESCRIPTION         "(U//FOUO) The Object-Identity for the TACLANE-C100
                            platform running Revision 3.5 version 9 of the
                            software image."
        ::= { taclaneC100R35 9 }

    taclaneC100R35v10 OBJECT-IDENTITY
        STATUS		current
        DESCRIPTION         "(U//FOUO) The Object-Identity for the TACLANE-C100
                            platform running Revision 3.5 version 10 of the
                            software image."
        ::= { taclaneC100R35 10 }

    taclaneC100R4 OBJECT IDENTIFIER ::= { taclaneC100Registrations 4 }

    taclaneC100R41 OBJECT-IDENTITY
        STATUS		current
        DESCRIPTION         "(U//FOUO) The Object-Identity for the TACLANE-C100
                            platform running an undefined version of Revision
                            4.1 of the software image."
        ::= { taclaneC100R4 1 }

    taclaneC100R41v1 OBJECT-IDENTITY
        STATUS		current
        DESCRIPTION         "(U//FOUO) The Object-Identity for the TACLANE-C100
                            platform running Revision 4.1 version 1 of the
                            software image."
        ::= { taclaneC100R41 1 }

    taclaneC100R41v2 OBJECT-IDENTITY
        STATUS		current
        DESCRIPTION         "(U//FOUO) The Object-Identity for the TACLANE-C100
                            platform running Revision 4.1 version 2 of the
                            software image."
        ::= { taclaneC100R41 2 }

    taclaneC100R41v3 OBJECT-IDENTITY
        STATUS		current
        DESCRIPTION         "(U//FOUO) The Object-Identity for the TACLANE-C100
                            platform running Revision 4.1 version 3 of the
                            software image."
        ::= { taclaneC100R41 3 }

    taclaneC100R41v4 OBJECT-IDENTITY
        STATUS		current
        DESCRIPTION         "(U//FOUO) The Object-Identity for the TACLANE-C100
                            platform running Revision 4.1 version 4 of the
                            software image."
        ::= { taclaneC100R41 4 }

    taclaneC100R41v5 OBJECT-IDENTITY
        STATUS		current
        DESCRIPTION         "(U//FOUO) The Object-Identity for the TACLANE-C100
                            platform running Revision 4.1 version 5 of the
                            software image."
        ::= { taclaneC100R41 5 }

    taclaneC100R41v6 OBJECT-IDENTITY
        STATUS		current
        DESCRIPTION         "(U//FOUO) The Object-Identity for the TACLANE-C100
                            platform running Revision 4.1 version 6 of the
                            software image."
        ::= { taclaneC100R41 6 }

    taclaneC100R41v7 OBJECT-IDENTITY
        STATUS		current
        DESCRIPTION         "(U//FOUO) The Object-Identity for the TACLANE-C100
                            platform running Revision 4.1 version 7 of the
                            software image."
        ::= { taclaneC100R41 7 }

    taclaneC100R41v8 OBJECT-IDENTITY
        STATUS		current
        DESCRIPTION         "(U//FOUO) The Object-Identity for the TACLANE-C100
                            platform running Revision 4.1 version 8 of the
                            software image."
        ::= { taclaneC100R41 8 }

    taclaneC100R41v9 OBJECT-IDENTITY
        STATUS		current
        DESCRIPTION         "(U//FOUO) The Object-Identity for the TACLANE-C100
                            platform running Revision 4.1 version 9 of the
                            software image."
        ::= { taclaneC100R41 9 }

    taclaneC100R41v10 OBJECT-IDENTITY
        STATUS		current
        DESCRIPTION         "(U//FOUO) The Object-Identity for the TACLANE-C100
                            platform running Revision 4.1 version 10 of the
                            software image."
        ::= { taclaneC100R41 10 }

    taclane1GRegistrations OBJECT IDENTIFIER ::= { taclaneProductsRegistrationMIB 6 }

    taclane1GR4 OBJECT IDENTIFIER ::= { taclane1GRegistrations 4 }

    taclane1GR41 OBJECT-IDENTITY
        STATUS		current
        DESCRIPTION         "(U//FOUO) The Object-Identity for the TACLANE-1G
                            platform running an undefined version of Revision
                            4.1 of the software image."
        ::= { taclane1GR4 1 }

    taclane1GR41v1 OBJECT-IDENTITY
        STATUS		current
        DESCRIPTION         "(U//FOUO) The Object-Identity for the TACLANE-1G
                            platform running Revision 4.1 version 1 of the
                            software image."
        ::= { taclane1GR41 1 }

    taclane1GR41v2 OBJECT-IDENTITY
        STATUS		current
        DESCRIPTION         "(U//FOUO) The Object-Identity for the TACLANE-1G
                            platform running Revision 4.1 version 2 of the
                            software image."
        ::= { taclane1GR41 2 }

    taclane1GR41v3 OBJECT-IDENTITY
        STATUS		current
        DESCRIPTION         "(U//FOUO) The Object-Identity for the TACLANE-1G
                            platform running Revision 4.1 version 3 of the
                            software image."
        ::= { taclane1GR41 3 }

    taclane1GR41v4 OBJECT-IDENTITY
        STATUS		current
        DESCRIPTION         "(U//FOUO) The Object-Identity for the TACLANE-1G
                            platform running Revision 4.1 version 4 of the
                            software image."
        ::= { taclane1GR41 4 }

    taclane1GR41v5 OBJECT-IDENTITY
        STATUS		current
        DESCRIPTION         "(U//FOUO) The Object-Identity for the TACLANE-1G
                            platform running Revision 4.1 version 5 of the
                            software image."
        ::= { taclane1GR41 5 }

    taclane1GR41v6 OBJECT-IDENTITY
        STATUS		current
        DESCRIPTION         "(U//FOUO) The Object-Identity for the TACLANE-1G
                            platform running Revision 4.1 version 6 of the
                            software image."
        ::= { taclane1GR41 6 }

    taclane1GR41v7 OBJECT-IDENTITY
        STATUS		current
        DESCRIPTION         "(U//FOUO) The Object-Identity for the TACLANE-1G
                            platform running Revision 4.1 version 7 of the
                            software image."
        ::= { taclane1GR41 7 }

    taclane1GR41v8 OBJECT-IDENTITY
        STATUS		current
        DESCRIPTION         "(U//FOUO) The Object-Identity for the TACLANE-1G
                            platform running Revision 4.1 version 8 of the
                            software image."
        ::= { taclane1GR41 8 }

    taclane1GR41v9 OBJECT-IDENTITY
        STATUS		current
        DESCRIPTION         "(U//FOUO) The Object-Identity for the TACLANE-1G
                            platform running Revision 4.1 version 9 of the
                            software image."
        ::= { taclane1GR41 9 }

    taclane1GR41v10 OBJECT-IDENTITY
        STATUS		current
        DESCRIPTION         "(U//FOUO) The Object-Identity for the TACLANE-1G
                            platform running Revision 4.1 version 10 of the
                            software image."
        ::= { taclane1GR41 10 }

    taclane10GRegistrations OBJECT IDENTIFIER ::= { taclaneProductsRegistrationMIB 7 }

    taclane10GR4 OBJECT IDENTIFIER ::= { taclane10GRegistrations 4 }

    taclane10GR41 OBJECT-IDENTITY
        STATUS		current
        DESCRIPTION         "(U//FOUO) The Object-Identity for the TACLANE-10G
                            platform running an undefined version of Revision
                            4.1 of the software image."
        ::= { taclane10GR4 1 }
        
    taclane10GR41v1 OBJECT-IDENTITY
        STATUS		current
        DESCRIPTION         "(U//FOUO) The Object-Identity for the TACLANE-10G
                            platform running Revision 4.1 version 1 of the
                            software image."
        ::= { taclane10GR41 1 }        
        
END
