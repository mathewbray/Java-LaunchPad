--BEGIN Revision History
--
--20110228 - M. DeVeau DRN MIB 195 - Add augments for PAC, FFVS, and TrustAnchor Hv4
--tables
--
--END Revision History

GDC4S-EXTENSION-MIB DEFINITIONS ::= BEGIN
    IMPORTS
    MODULE-IDENTITY, OBJECT-TYPE, Unsigned32
        FROM SNMPv2-SMI
    OBJECT-GROUP
        FROM SNMPv2-CONF
    SnmpAdminString
        FROM SNMP-FRAMEWORK-MIB
    hFireFlyTableEntry, hDPModuliTableEntry,
    hAPPKTATableEntry, hPrePlacedKeyTableEntry,
    hDGSharedKeyTableEntry
        FROM HAIPE-V4-KEY-INFORMATION-MIB
    hManualSADTableEntry, hIKEv1SADTableEntry,
    hIKEv2CHILDSADTableEntry
        FROM HAIPE-V4-TRAFFIC-PROTECTION-MIB
    TruthValue, DateAndTime
        FROM SNMPv2-TC
    FireflyKMID
        FROM HAIPE-V4-TEXTUAL-CONVENTIONS-MIB
    gdc4sEncryptionProductsMIB
        FROM GDC4S-ENCRYPTION-PRODUCTS-MIB
    hPEPTTableEntry, hRIPTableEntry
        FROM HAIPE-V4-DISCOVERY-MIB
    hIPv4IfaceTableEntry
        FROM HAIPE-V4-NETWORKING-MIB;

    gdc4sExtensions MODULE-IDENTITY
        LAST-UPDATED	    "201103070000Z"
        ORGANIZATION	    "General Dynamics C4 Systems"
        CONTACT-INFO        "Infosec Support                        
                            General Dynamics C4
                            Systems Corporation
                            77 A Street
                            Needham Heights, MA
                            02494-2806
                            Telephone: 877-230-0236
                            email: INFOSECSUPPORT@GDC4S.COM"
        DESCRIPTION         "This MIB supports extending IETF or other vendor
                            supplied MIB extensions (augments) necessary
                            to configure the devices developed by General
                            Dynamics C4 Systems."

        ::= { gdc4sEncryptionProductsMIB 5 }


    extensions OBJECT IDENTIFIER ::= { gdc4sExtensions 1 }

    extHaipe OBJECT IDENTIFIER ::= { extensions 1 }

    extHaipeV4 OBJECT IDENTIFIER ::= { extHaipe 1 }

    extTrafficProtection OBJECT IDENTIFIER ::= { extHaipeV4 1 }

    extManualSADTable OBJECT-TYPE
        SYNTAX              SEQUENCE OF ExtManualSADTableEntry
        MAX-ACCESS          not-accessible
        STATUS              current
        DESCRIPTION         "(U//FOUO) This table augments the hManualSADTable"
        ::= { extTrafficProtection 1 }

    extManualSADTableEntry OBJECT-TYPE
        SYNTAX              ExtManualSADTableEntry
        MAX-ACCESS          not-accessible
        STATUS              current
        DESCRIPTION         "(U//FOUO) An row containing additional information
                            applicable to Manual SAs."
        AUGMENTS            {                                 hManualSADTableEntry
                            }
        ::= { extManualSADTable 1 }

    ExtManualSADTableEntry ::= SEQUENCE {
        extManualSAAutocfgLclAddrs
            TruthValue,
        extManualSAAutocfgSpis
            TruthValue,
        extManualSAPMTU
            Unsigned32
    }

    extManualSAAutocfgLclAddrs OBJECT-TYPE
        SYNTAX              TruthValue
        MAX-ACCESS          read-create
        STATUS              current
        DESCRIPTION         "(U//FOUO) This object, when TRUE, causes the ECU
                            to Auto-Configure the local PT and CT addresses
                            (hManualSALocalCTAddress & hManualSALocalPTAddress)
                            for the Manually-Created, PPK SA represented
                            by this row in the hManualSADTable. If this truth-value
                            is true, then any value that is attempted to
                            be set to either or both local address objects
                            ( hManualSALocalCTAddress & hManualSALocalPTAddress)
                            is ignored. (U//FOUO) If the PT or CT local IP
                            address is left un-set by the manager during
                            the creation of a manual PPK SA, this object
                            will default to a value of TRUE and the local
                            IP addresses of this SA will be auto-configured.
                            (U//FOUO) When the hManualSADTable row is set,
                            it must have the same value for this object as
                            any associated SA's. (U//FOUO) When read, this
                            object is TRUE if the associated SA was configured
                            using Auto-Configuration to create the Local
                            CT and PT interface IP addresses. (U//FOUO) This
                            object is FALSE for all other rows in the hManualSADTable."
        DEFVAL              { false }
        ::= { extManualSADTableEntry 1 }

    extManualSAAutocfgSpis OBJECT-TYPE
        SYNTAX              TruthValue
        MAX-ACCESS          read-create
        STATUS              current
        DESCRIPTION         "(U//FOUO) This object, when TRUE, causes the ECU
                            to automatically calculate values for the SPI
                            chain group in the hManualSASPIChainTable. (U//FOUO)
                            When the hManualSADTable row is set, it must
                            have the same value for this object as any associated
                            SA's. (U//FOUO) When read, this object is TRUE
                            if the associated SA was configured using Auto-Calculation
                            to create the SPI value of the associated SA.
                            (U//FOUO) This object is FALSE for all other
                            rows in the hManualSADTable."
        DEFVAL              { false }
        ::= { extManualSADTableEntry 2 }

    extManualSAPMTU OBJECT-TYPE
        SYNTAX              Unsigned32
        MAX-ACCESS          read-only
        STATUS              current
        DESCRIPTION         "(U//FOUO) The PMTU value for the hManualSADTable
                            row."
        ::= { extManualSADTableEntry 3 }

    extIKEv1SADTable OBJECT-TYPE
        SYNTAX              SEQUENCE OF ExtIKEv1SADTableEntry
        MAX-ACCESS          not-accessible
        STATUS              current
        DESCRIPTION         "(U//FOUO) This table augments the hIKEv1SADTable"
        ::= { extTrafficProtection 2 }

    extIKEv1SADTableEntry OBJECT-TYPE
        SYNTAX              ExtIKEv1SADTableEntry
        MAX-ACCESS          not-accessible
        STATUS              current
        DESCRIPTION         "(U//FOUO) An row containing additional information
                            applicable to IKEv1 SAs."
        AUGMENTS            {                                 hIKEv1SADTableEntry
                            }
        ::= { extIKEv1SADTable 1 }

    ExtIKEv1SADTableEntry ::= SEQUENCE {
        extIKEv1SALocalCredentialID
            OCTET STRING,
        extIKEv1SARemoteCredentialID
            OCTET STRING,
        extIKEv1SAPMTU
            Unsigned32
    }

    extIKEv1SALocalCredentialID OBJECT-TYPE
        SYNTAX              OCTET STRING (SIZE(6))
        MAX-ACCESS          read-only
        STATUS              current
        DESCRIPTION         "(U//FOUO) The Certificate ID that was used to
                            authenticate the local side of the SA."
        ::= { extIKEv1SADTableEntry 1 }

    extIKEv1SARemoteCredentialID OBJECT-TYPE
        SYNTAX              OCTET STRING (SIZE(6))
        MAX-ACCESS          read-only
        STATUS              current
        DESCRIPTION         "(U//FOUO) The Certificate ID that was used to
                            authenticate the remote side of the SA."
        ::= { extIKEv1SADTableEntry 2 }

    extIKEv1SAPMTU OBJECT-TYPE
        SYNTAX              Unsigned32
        MAX-ACCESS          read-only
        STATUS              current
        DESCRIPTION         "(U//FOUO) The PMTU value for the hIKEv1SADTable
                            row."
        ::= { extIKEv1SADTableEntry 3 }

    extIKEv2CHILDSADTable OBJECT-TYPE
        SYNTAX              SEQUENCE OF ExtIKEv2CHILDSADTableEntry
        MAX-ACCESS          not-accessible
        STATUS              current
        DESCRIPTION         "(U//FOUO) This table augments the hIKEv2CHILDSADTable"
        ::= { extTrafficProtection 3 }

    extIKEv2CHILDSADTableEntry OBJECT-TYPE
        SYNTAX              ExtIKEv2CHILDSADTableEntry
        MAX-ACCESS          not-accessible
        STATUS              current
        DESCRIPTION         "(U//FOUO) An row containing additional information
                            applicable to IKEv2 Child SAs."
        AUGMENTS            {                                 hIKEv2CHILDSADTableEntry
                            }
        ::= { extIKEv2CHILDSADTable 1 }

    ExtIKEv2CHILDSADTableEntry ::= SEQUENCE {
        extIKEv2CHILDSAPMTU
            Unsigned32
    }

    extIKEv2CHILDSAPMTU OBJECT-TYPE
        SYNTAX              Unsigned32
        MAX-ACCESS          read-only
        STATUS              current
        DESCRIPTION         "(U//FOUO) The PMTU value for the hIKEv2CHILDSADTable
                            row."
        ::= { extIKEv2CHILDSADTableEntry 1 }

    extKeyInformation OBJECT IDENTIFIER ::= { extHaipeV4 2 }

    extFireFlyTable OBJECT-TYPE
        SYNTAX              SEQUENCE OF ExtFireFlyEntry
        MAX-ACCESS          not-accessible
        STATUS              current
        DESCRIPTION         "(U//FOUO) A table augmenting information about
                            the filled/loaded Firefly Vector Sets (FFVSs)
                            in the ECU. This table contains additional objects
                            for the hFireFlyTableEntry of the HAIPE-V4-KEY-INFORMATION-MIB."
        ::= { extKeyInformation 1 }

    extFireFlyEntry OBJECT-TYPE
        SYNTAX              ExtFireFlyEntry
        MAX-ACCESS          not-accessible
        STATUS              current
        DESCRIPTION         "(U//FOUO) An row containing additional information
                            applicable to a firefly vector set (FFVS)."
        AUGMENTS            {                                 hFireFlyTableEntry
                            }
        ::= { extFireFlyTable 1 }

    ExtFireFlyEntry ::= SEQUENCE {
        extFFPACModuliId
            OCTET STRING
    }

    extFFPACModuliId OBJECT-TYPE
        SYNTAX              OCTET STRING (SIZE(6))
        MAX-ACCESS          read-only
        STATUS              current
        DESCRIPTION         "(U//FOUO) The Moduli ID of the PAC Module used
                            to dePAC this Firefly VS."
        ::= { extFireFlyEntry 1 }

    extDPModuliTable OBJECT-TYPE
        SYNTAX              SEQUENCE OF ExtDPModuliEntry
        MAX-ACCESS          not-accessible
        STATUS              current
        DESCRIPTION         "(U//FOUO)Table augments hDPModuliTableEntry."
        ::= { extKeyInformation 2 }

    extDPModuliEntry OBJECT-TYPE
        SYNTAX              ExtDPModuliEntry
        MAX-ACCESS          not-accessible
        STATUS              current
        DESCRIPTION         "(U//FOUO) A row containing additional capabilities
                            for installed DePAC Moduli. It augments the hDPModuliTableEntry
                            in the HAIPE-V4-KEY-INFORMATION-MIB."
        AUGMENTS            {                                 hDPModuliTableEntry
                            }
        ::= { extDPModuliTable 1 }

    ExtDPModuliEntry ::= SEQUENCE {
        extDPModuliZeroizeCmd
            TruthValue
    }

    extDPModuliZeroizeCmd OBJECT-TYPE
        SYNTAX              TruthValue
        MAX-ACCESS          read-write
        STATUS              current
        DESCRIPTION         "(U//FOUO) This object is set to TRUE to zeroize
                            the corresponding DePAC Moduli and delete the
                            corresponding row of the hDPModuliTableEntry.
                            When set to FALSE, the set is accepted and no
                            action occurs. When read, it always returns FALSE."
        ::= { extDPModuliEntry 1 }

    extAPPKTATable OBJECT-TYPE
        SYNTAX              SEQUENCE OF ExtAPPTAEntry
        MAX-ACCESS          not-accessible
        STATUS              current
        DESCRIPTION         "(U//FOUO) This table augments the hAPPKTATableEntry."
        ::= { extKeyInformation 3 }

    extAPPKTATableEntry OBJECT-TYPE
        SYNTAX              ExtAPPTAEntry
        MAX-ACCESS          not-accessible
        STATUS              current
        DESCRIPTION         "(U//FOUO) An row containing additional information
                            applicable to the APPK trust anchors."
        AUGMENTS            {                                 hAPPKTATableEntry
                            }
        ::= { extAPPKTATable 1 }

    ExtAPPTAEntry ::= SEQUENCE {
        extAPPKTAZeroizeCMD
            TruthValue,
        extAPPKTAKMID
            FireflyKMID,
        extAPPKTAType
            INTEGER
    }

    extAPPKTAZeroizeCMD OBJECT-TYPE
        SYNTAX              TruthValue
        MAX-ACCESS          read-write
        STATUS              current
        DESCRIPTION         "(U//FOUO) This object is set to TRUE to zeroize
                            the corresponding trust anchor and delete the
                            corresponding row in hAPPKTATableEntry. When
                            set to FALSE, the set is accepted and no action
                            occurs. When read, it always returns FALSE."
        ::= { extAPPKTATableEntry 1 }

    extAPPKTAKMID OBJECT-TYPE
        SYNTAX              FireflyKMID
        MAX-ACCESS          read-only
        STATUS              current
        DESCRIPTION         "(U//FOUO) The Key Management Identifier for the
                            APPK trust anchor."
        ::= { extAPPKTATableEntry 2 }

    extAPPKTAType OBJECT-TYPE
        SYNTAX              INTEGER {
                                base( 1 ),
                                alternate( 2 )
                            }
        MAX-ACCESS          read-only
        STATUS              current
        DESCRIPTION         "(U//FOUO) Indicates whether this is a Base or
                            Alternate trust anchor."
        ::= { extAPPKTATableEntry 3 }

    extPrePlacedKeyTable OBJECT-TYPE
        SYNTAX              SEQUENCE OF ExtPrePlacedKeyTableEntry
        MAX-ACCESS          not-accessible
        STATUS              current
        DESCRIPTION         "(U//FOUO) This table augments the hPrePlacedKeyTable"
        ::= { extKeyInformation 4 }

    extPrePlacedKeyTableEntry OBJECT-TYPE
        SYNTAX              ExtPrePlacedKeyTableEntry
        MAX-ACCESS          not-accessible
        STATUS              current
        DESCRIPTION         "(U//FOUO) An row containing additional information
                            applicable to Pre-Placed keys."
        AUGMENTS            {                                 hPrePlacedKeyTableEntry
                            }
        ::= { extPrePlacedKeyTable 1 }

    ExtPrePlacedKeyTableEntry ::= SEQUENCE {
        extPrePlacedKeyTAPartialKeyData
            OCTET STRING,
        extPrePlacedKeyCaveat
            INTEGER,
        extPrePlacedKeyOwnership
            INTEGER,
        extPrePlacedKeyEffectiveDate
            DateAndTime,
        extPrePlacedKeyUpdateCount
            Unsigned32,
        extPrePlacedKeyAssignedToChain
            TruthValue
    }

    extPrePlacedKeyTAPartialKeyData OBJECT-TYPE
        SYNTAX              OCTET STRING (SIZE(8))
        MAX-ACCESS          read-only
        STATUS              current
        DESCRIPTION         "(U//FOUO) The low order 64 bits of the ECDSA Public
                            Key. This information is matched against the
                            Partial Key Data inherent in the APPK material."
        ::= { extPrePlacedKeyTableEntry 1 }

    extPrePlacedKeyCaveat OBJECT-TYPE
        SYNTAX              INTEGER {
                                notAvailable( 0 ),
                                crypto( 1 ),
                                nonCrypto( 2 ),
                                reserved( 3 )
                            }
        MAX-ACCESS          read-only
        STATUS              current
        DESCRIPTION         "(U//FOUO) The current caveat of this Pre-Placed
                            key."
        ::= { extPrePlacedKeyTableEntry 2 }

    extPrePlacedKeyOwnership OBJECT-TYPE
        SYNTAX              INTEGER {
                                notAvailable( 0 ),
                                nato( 1 ),
                                natoRel( 2 ),
                                cosmic( 3 ),
                                cosmicRel( 4 ),
                                reserved( 5 )
                            }
        MAX-ACCESS          read-only
        STATUS              current
        DESCRIPTION         "(U//FOUO) The current ownership of this Pre-Placed
                            key."
        ::= { extPrePlacedKeyTableEntry 3 }

    extPrePlacedKeyEffectiveDate OBJECT-TYPE
        SYNTAX              DateAndTime
        MAX-ACCESS          read-write
        STATUS              current
        DESCRIPTION         "(U//FOUO) The current effective date of this Pre-Placed
                            key."
        ::= { extPrePlacedKeyTableEntry 4 }

    extPrePlacedKeyUpdateCount OBJECT-TYPE
        SYNTAX              Unsigned32
        MAX-ACCESS          read-only
        STATUS              current
        DESCRIPTION         "(U//FOUO) The current update count of this Pre-Placed
                            key."
        ::= { extPrePlacedKeyTableEntry 5 }

    extPrePlacedKeyAssignedToChain OBJECT-TYPE
        SYNTAX              TruthValue
        MAX-ACCESS          read-only
        STATUS              current
        DESCRIPTION         "(U//FOUO) This current indication whether this
                            Pre-Placed key is assigned to a chain or not."
        ::= { extPrePlacedKeyTableEntry 6 }

    extDGSharedKeyTable OBJECT-TYPE
        SYNTAX              SEQUENCE OF ExtDGSharedKeyTableEntry
        MAX-ACCESS          not-accessible
        STATUS              current
        DESCRIPTION         "(U//FOUO) This table augments the hDGSharedKeyTable"
        ::= { extKeyInformation 5 }

    extDGSharedKeyTableEntry OBJECT-TYPE
        SYNTAX              ExtDGSharedKeyTableEntry
        MAX-ACCESS          not-accessible
        STATUS              current
        DESCRIPTION         "(U//FOUO) An row containing additional information
                            applicable to Device Generated Shared Keys."
        AUGMENTS            {                                 hDGSharedKeyTableEntry
                            }
        ::= { extDGSharedKeyTable 1 }

    ExtDGSharedKeyTableEntry ::= SEQUENCE {
        extDGSharedKeyMode
            INTEGER,
        extDGSharedKeySuite
            INTEGER
    }

    extDGSharedKeyMode OBJECT-TYPE
        SYNTAX              INTEGER {
                                unassigned( 0 ),
                                haipe( 1 ),
                                ipmeir( 2 )
                            }
        MAX-ACCESS          read-create
        STATUS              current
        DESCRIPTION         "(U//FOUO) The current mode of this Device Generated
                            Shared Key."
        ::= { extDGSharedKeyTableEntry 1 }

    extDGSharedKeySuite OBJECT-TYPE
        SYNTAX              INTEGER {
                                noSuite( 0 ),
                                suiteA( 1 ),
                                suiteB( 2 )
                            }
        MAX-ACCESS          read-create
        STATUS              current
        DESCRIPTION         "(U//FOUO) The current suite of this Device Generated
                            Shared Key."
        ::= { extDGSharedKeyTableEntry 2 }

    extDiscovery OBJECT IDENTIFIER ::= { extHaipeV4 3 }

    extRIPTable OBJECT-TYPE
        SYNTAX              SEQUENCE OF ExtRIPEntry
        MAX-ACCESS          not-accessible
        STATUS              current
        DESCRIPTION         "(U//FOUO) A table augmenting information about
                            the RIP entries. This table contains additional
                            objects for the hRIPTable of the HAIPE-V4-DISCOVERY-MIB."
        ::= { extDiscovery 1 }

    extRIPEntry OBJECT-TYPE
        SYNTAX              ExtRIPEntry
        MAX-ACCESS          not-accessible
        STATUS              current
        DESCRIPTION         "(U//FOUO) An row containing additional information
                            applicable to RIP."
        AUGMENTS            {                                 hRIPTableEntry
                            }
        ::= { extRIPTable 1 }

    ExtRIPEntry ::= SEQUENCE {
        extRIPLEPTLifetimeOffset
            Unsigned32
    }

    extRIPLEPTLifetimeOffset OBJECT-TYPE
        SYNTAX              Unsigned32
        UNITS               "seconds"
        MAX-ACCESS          read-create
        STATUS              current
        DESCRIPTION         "(U//FOUO) The number of seconds that will be added
                            to hSystemDate to populate an hLEPTTable entry's
                            hLEPTRowLifetime if configured via RIP."
        ::= { extRIPEntry 1 }

    extPEPTTable OBJECT-TYPE
        SYNTAX              SEQUENCE OF ExtPEPTEntry
        MAX-ACCESS          not-accessible
        STATUS              current
        DESCRIPTION         "(U//FOUO) A table augmenting information about
                            the peer HAIPE PT enclave topology entries. This
                            table contains additional objects for the hPEPTTable
                            of the HAIPE-V4-DISCOVERY-MIB."
        ::= { extDiscovery 2 }

    extPEPTEntry OBJECT-TYPE
        SYNTAX              ExtPEPTEntry
        MAX-ACCESS          not-accessible
        STATUS              current
        DESCRIPTION         "(U//FOUO) An row containing additional information
                            applicable to PEP."
        AUGMENTS            {                                 hPEPTTableEntry
                            }
        ::= { extPEPTTable 1 }

    ExtPEPTEntry ::= SEQUENCE {
        extPEPTLabel
            SnmpAdminString
    }

    extPEPTLabel OBJECT-TYPE
        SYNTAX              SnmpAdminString (SIZE(0..32))
        MAX-ACCESS          read-write
        STATUS              current
        DESCRIPTION         "(U//FOUO) This object is a free text field allowing
                            the user to tag PEP routes with helpful information."
        ::= { extPEPTEntry 1 }

    extNetworking OBJECT IDENTIFIER ::= { extHaipeV4 4 }

    extIPv4IfaceTable OBJECT-TYPE
        SYNTAX              SEQUENCE OF ExtIPv4IfaceEntry
        MAX-ACCESS          not-accessible
        STATUS              current
        DESCRIPTION         "(U//FOUO) A table augmenting information about
                            the IPv4 Interface entries. This table contains
                            additional objects for the hIPv4IfaceTable of
                            the HAIPE-V4-NETWORKING-MIB.your description."
        ::= { extNetworking 1 }

    extIPv4IfaceEntry OBJECT-TYPE
        SYNTAX              ExtIPv4IfaceEntry
        MAX-ACCESS          not-accessible
        STATUS              current
        DESCRIPTION         "(U//FOUO) An row containing additional information
                            applicable to IPv4Interfaces."
        AUGMENTS            {                                 hIPv4IfaceTableEntry
                            }
        ::= { extIPv4IfaceTable 1 }

    ExtIPv4IfaceEntry ::= SEQUENCE {
        extDHCPEnable
            TruthValue
    }

    extDHCPEnable OBJECT-TYPE
        SYNTAX              TruthValue
        MAX-ACCESS          read-write
        STATUS              current
        DESCRIPTION         "(U//FOUO) Setting the object to TRUE enables DHCP.
                            Setting the object to FALSE disables DHCP."
        ::= { extIPv4IfaceEntry 1 }

    gdc4sExtensionConformance OBJECT IDENTIFIER ::= { gdc4sExtensions 2 }

    gdc4sExtensionGroups OBJECT IDENTIFIER ::= { gdc4sExtensionConformance 1 }

    extFireFlyGroup OBJECT-GROUP
        OBJECTS	{
        		extFFPACModuliId
        	}
        STATUS		    current
        DESCRIPTION         "(U//FOUO) The objects related to Firefly Vector
                            Sets that extend the hFireFlyTableEntry"
        ::= { gdc4sExtensionGroups 1 }

    extDPModuliGroup OBJECT-GROUP
        OBJECTS	{
        		extDPModuliZeroizeCmd
        	}
        STATUS		    current
        DESCRIPTION         "(U//FOUO) The objects related to depac moduli
                            that extend the hDPModuliTable."
        ::= { gdc4sExtensionGroups 2 }

    extAPPKTAGroup OBJECT-GROUP
        OBJECTS	{
        		extAPPKTAZeroizeCMD,
        		extAPPKTAKMID,
        		extAPPKTAType
        	}
        STATUS		    current
        DESCRIPTION         "(U//FOUO) The objects related to Trust Anchors
                            that extend the hAPPKTATableEntry"
        ::= { gdc4sExtensionGroups 3 }

    extRIPGroup OBJECT-GROUP
        OBJECTS	{
        		extRIPLEPTLifetimeOffset
        	}
        STATUS		    current
        DESCRIPTION         "(U//FOUO) The objects related to RIP"
        ::= { gdc4sExtensionGroups 4 }

    extPrePlacedKeyGroup OBJECT-GROUP
        OBJECTS	{
        		extPrePlacedKeyTAPartialKeyData,
        		extPrePlacedKeyCaveat,
        		extPrePlacedKeyOwnership,
        		extPrePlacedKeyEffectiveDate,
        		extPrePlacedKeyUpdateCount,
        		extPrePlacedKeyAssignedToChain
        	}
        STATUS		    current
        DESCRIPTION         "(U//FOUO) The objects related to Pre-Placed keys
                            that extend the hPrePlacedKeyTableEntry"
        ::= { gdc4sExtensionGroups 5 }

    extDGSharedKeyGroup OBJECT-GROUP
        OBJECTS	{
        		extDGSharedKeyMode,
        		extDGSharedKeySuite
        	}
        STATUS		    current
        DESCRIPTION         "(U//FOUO) The objects related to Device Generated
                            Shared Keys that extend the hDGSharedKeyTableEntry"
        ::= { gdc4sExtensionGroups 6 }

    extManualSADGroup OBJECT-GROUP
        OBJECTS	{
        		extManualSAAutocfgLclAddrs,
        		extManualSAAutocfgSpis,
        		extManualSAPMTU
        	}
        STATUS		    current
        DESCRIPTION         "(U//FOUO) The objects related to Manual Sas that
                            extend the hManualSADTableEntry"
        ::= { gdc4sExtensionGroups 7 }

    extIKEv1SADGroup OBJECT-GROUP
        OBJECTS	{
        		extIKEv1SALocalCredentialID,
        		extIKEv1SARemoteCredentialID,
        		extIKEv1SAPMTU
        	}
        STATUS		    current
        DESCRIPTION         "(U//FOUO) The objects related to IKE v1 Sas that
                            extend the hIKEv1SADTableEntry"
        ::= { gdc4sExtensionGroups 8 }

    extIKEv2CHILDSADGroup OBJECT-GROUP
        OBJECTS	{
        		extIKEv2CHILDSAPMTU
        	}
        STATUS		    current
        DESCRIPTION         "(U//FOUO) The objects related to IKE v2 Child
                            Sas that extend the hIKEv2CHILDSADTableEntry"
        ::= { gdc4sExtensionGroups 9 }

    extPEPTGroup OBJECT-GROUP
        OBJECTS	{
        		extPEPTLabel
        	}
        STATUS		    current
        DESCRIPTION         "(U//FOUO) The objects related to PEP that extend
                            the hPEPTTableEntry"
        ::= { gdc4sExtensionGroups 10 }
        
    extIPv4IfaceGroup OBJECT-GROUP
        OBJECTS	{
        		extDHCPEnable
        	}
        STATUS		    current
        DESCRIPTION         "(U//FOUO) The objects related the IPV4 interfaces 
							that extend the hIPv4IfaceTableEntry"
        ::= { gdc4sExtensionGroups 11 }

END
