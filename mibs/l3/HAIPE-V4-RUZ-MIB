--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-RUZ-MIB  DEFINITIONS  ::= BEGIN

IMPORTS
    OBJECT-TYPE, Unsigned32, Integer32,
    MODULE-IDENTITY                     FROM SNMPv2-SMI                         
    SnmpAdminString                     FROM SNMP-FRAMEWORK-MIB
    RowPointer, RowStatus, TimeStamp,
    DateAndTime, TruthValue             FROM SNMPv2-TC
    IPAddress, IPAddressType            FROM HAIPE-V4-TEXTUAL-CONVENTIONS-MIB
    hv4RUZ                              FROM HAIPE-V4-FEATURE-HIERARCHY-MIB;

haipev4RUZMIB MODULE-IDENTITY
    LAST-UPDATED "201602190530Z"
    ORGANIZATION "HAIPE PO"
    CONTACT-INFO
        "(U//FOUO) Not Available"
    DESCRIPTION
        "(U//FOUO) This MIB defines the HAIPE RUZ MIB objects."
    REVISION     "201602190530Z"
    DESCRIPTION  "(U//FOUO) MIB 4.2.3 Final" 
    ::= { hv4RUZ 1 }

-- **********************************************************************
-- RUZ Information Segments
-- **********************************************************************
hRUZControlObjects               OBJECT IDENTIFIER ::= { haipev4RUZMIB 1 }
hRUZScalars                      OBJECT IDENTIFIER ::= { haipev4RUZMIB 2 }
hRUZNotifications                OBJECT IDENTIFIER ::= { haipev4RUZMIB 3 }
hRUZ                             OBJECT IDENTIFIER ::= { haipev4RUZMIB 4 }

hRUZNetController                OBJECT IDENTIFIER ::= { hRUZ 1 }
hRUZClient                       OBJECT IDENTIFIER ::= { hRUZ 2 }

hRUZNetControllerControlObjects  OBJECT IDENTIFIER ::= { hRUZNetController 1 }
hRUZNetControllerScalars         OBJECT IDENTIFIER ::= { hRUZNetController 2 }
hRUZNetControllerNotifications   OBJECT IDENTIFIER ::= { hRUZNetController 3 }
hRUZClients                      OBJECT IDENTIFIER ::= { hRUZNetController 4 }
hRUZClientTriggers               OBJECT IDENTIFIER ::= { hRUZNetController 5 }
hRUZClientHeartbeats             OBJECT IDENTIFIER ::= { hRUZNetController 6 }

hRUZClientControlObjects         OBJECT IDENTIFIER ::= { hRUZClient 1 }
hRUZClientScalars                OBJECT IDENTIFIER ::= { hRUZClient 2 }
hRUZClientNotifications          OBJECT IDENTIFIER ::= { hRUZClient 3 }
hRUZNetControllers               OBJECT IDENTIFIER ::= { hRUZClient 4 }
hRUZLocalTriggers                OBJECT IDENTIFIER ::= { hRUZClient 5 }
hRUZLocalHeartbeats              OBJECT IDENTIFIER ::= { hRUZClient 6 }



-- **********************************************************************
-- RUZ Net Controller
-- **********************************************************************

-- =========
-- RUZ Clients Table
-- =========
hRUZClientsTableCount OBJECT-TYPE
    SYNTAX     Unsigned32
    MAX-ACCESS read-only
    STATUS     current
    DESCRIPTION
        "(U//FOUO) The number of rows in the hRUZClientsTable."
    ::= { hRUZClients 1}

hRUZClientsTableLastChanged OBJECT-TYPE
    SYNTAX     TimeStamp
    MAX-ACCESS read-only
    STATUS     current
    DESCRIPTION
        "(U//FOUO) The value of hSystemUpTime the last time any entry in the
         hRUZClientsTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hRUZClients 2}

hRUZClientsTable OBJECT-TYPE
    SYNTAX     SEQUENCE OF HRUZClientsTableEntry
    MAX-ACCESS not-accessible
    STATUS     current
    DESCRIPTION
        "(U//FOUO) This table stores Render Useless Zeroization Client
         IP Address information.  This table is supported by RUZ Net
         Controllers.

         (U//FOUO) This table is used to control the transmission of RUZ
         messages to RUZ Clients."
    ::= { hRUZClients 3 }

hRUZClientsTableEntry OBJECT-TYPE
    SYNTAX     HRUZClientsTableEntry
    MAX-ACCESS not-accessible
    STATUS     current
    DESCRIPTION
        "(U//FOUO) A row in the hRUZClientsTable specifying a RUZ Client IP
        address information."
    INDEX  { hRUZClientIPAddressType, hRUZClientIPAddress }
    ::= { hRUZClientsTable 1 }

HRUZClientsTableEntry ::= SEQUENCE
{
   hRUZClientIPAddressType                IPAddressType,
   hRUZClientIPAddress	                  IPAddress,
   hRUZClientTransferTime                 DateAndTime,
   hRUZClientZeroize                      TruthValue,
   hRUZClientRetries                      Unsigned32,
   hRUZClientRetryPeriod                  Unsigned32,
   hRUZClientRowStatus	                  RowStatus
}

hRUZClientIPAddressType OBJECT-TYPE
    SYNTAX     IPAddressType
    MAX-ACCESS not-accessible
    STATUS     current
    DESCRIPTION
        "(U//FOUO) IP version of a RUZ Client's CT IP Address (IPv4/IPv6).
        Note, this value determines the size and format of the associated
        hRUZClientIPAddress value."
    ::= { hRUZClientsTableEntry 1 }

hRUZClientIPAddress OBJECT-TYPE
    SYNTAX     IPAddress
    MAX-ACCESS not-accessible
    STATUS     current
    DESCRIPTION
        "(U//FOUO) CT IP Address of a RUZ Client."
    ::= { hRUZClientsTableEntry 2 }

hRUZClientTransferTime OBJECT-TYPE
    SYNTAX     DateAndTime
    MAX-ACCESS read-create
    STATUS     current
    DESCRIPTION
        "(U//FOUO) This indicates the date and time that the trigger indicated
         by this row should be sent to the client indicated by this row."
    ::= { hRUZClientsTableEntry 3 }

hRUZClientZeroize OBJECT-TYPE
    SYNTAX     TruthValue
    MAX-ACCESS read-create
    STATUS     current
    DESCRIPTION
        "(U//FOUO) This object, when set to true, is used to initiate a RUZ
         Immediate Zeroize message to the indicated client.  Implementations
         will ignore setting it to false, and it will always return false when
         read.

         (U//FOUO) When this object is set to true and the hRUZClientsRetries
         counter has been exhausted or a GOODBYE message has been received from
         the client, the entire row is deleted by the agent."
    ::= { hRUZClientsTableEntry 4 }

hRUZClientRetries OBJECT-TYPE
    SYNTAX     Unsigned32
    MAX-ACCESS read-create
    STATUS     current
    DESCRIPTION
        "(U//FOUO) This indicates the number of times the message should be
         re-sent to the client. For example, a value of zero indicates that the
         key should be sent once. A value of 2 indicates the key should be sent
         three times (once for the initial send, and then two retries)."
    ::= { hRUZClientsTableEntry 5 }

hRUZClientRetryPeriod OBJECT-TYPE
    SYNTAX     Unsigned32
    MAX-ACCESS read-create
    STATUS     current
    DESCRIPTION
        "(U//FOUO) This indicates the number of seconds between each attempt to
         re-send the message to a client."
    ::= { hRUZClientsTableEntry 6 }

hRUZClientRowStatus OBJECT-TYPE
    SYNTAX     RowStatus
    MAX-ACCESS read-create
    STATUS     current
    DESCRIPTION
        "(U//FOUO) The status of the row, by which new entries may be created,
         or old entries deleted from this table.

         (U//FOUO) If values are not valid for the required columns, an
         inconsistentName error will be returned for this object.

         (U//FOUO) If any column is set to an invalid or unsupported value
         (during row creation or any other time), a wrongValue error will be
         returned for that object.

         (U//FOUO) An active row may not be changed to an inconsistent state.
         If such an attempt is made, an inconsistentValue error will be
         returned. In other words, any new values must be valid values for an
         active row.

         (U//FOUO) At a minimum, implementations must support createAndGo and
         destroy management functions. Support for createAndWait, active,
         notInService, and notReady management functions is optional."
    ::= { hRUZClientsTableEntry 7 }


-- =========
-- RUZ Client Triggers
-- =========
hRUZClientTrigTableCount OBJECT-TYPE
    SYNTAX     Unsigned32
    MAX-ACCESS read-only
    STATUS     current
    DESCRIPTION
        "(U//FOUO) The number of rows in the hRUZClientTrigTable."
    ::= { hRUZClientTriggers 1}

hRUZClientTrigTableLastChanged OBJECT-TYPE
    SYNTAX     TimeStamp
    MAX-ACCESS read-only
    STATUS     current
    DESCRIPTION
        "(U//FOUO) The value of hSystemUpTime the last time any entry in the
         hRUZClientTrigTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hRUZClientTriggers 2}

hRUZClientTrigTable OBJECT-TYPE
    SYNTAX     SEQUENCE OF HRUZClientTrigTableEntry
    MAX-ACCESS not-accessible
    STATUS     current
    DESCRIPTION
        "(U//FOUO) This table stores Render Useless Zeroization triggers to be,
         or that have been, established on the associated client. This table is
         supported by RUZ Net Controllers.

         (U//FOUO) This table is used to control the payload of RUZ messages
         sent to clients."
    ::= { hRUZClientTriggers 3 }

hRUZClientTrigTableEntry OBJECT-TYPE
    SYNTAX     HRUZClientTrigTableEntry
    MAX-ACCESS not-accessible
    STATUS     current
    DESCRIPTION
        "(U//FOUO) A row in the hRUZClientTrigTable specifying a RUZ Client
        trigger information."
    INDEX  { hRUZClientTriggerID }
    ::= { hRUZClientTrigTable 1 }

HRUZClientTrigTableEntry ::= SEQUENCE
{
   hRUZClientTriggerID                  OCTET STRING,
   hRUZClientTriggerRef                 RowPointer,
   hRUZClientTriggerType                INTEGER,
   hRUZClientTriggerData                OCTET STRING,
   hRUZClientTriggerRowStatus	          RowStatus
}

hRUZClientTriggerID OBJECT-TYPE
    SYNTAX OCTET STRING (SIZE(4))
    MAX-ACCESS not-accessible
    STATUS     current
    DESCRIPTION
        "(U//FOUO)The unique system identifier for this trigger. The Trigger-ID
        shall be the 32 LSB of the SHA2 HASH of the CT IP Address of the Net
        Controller concatenated with the 64-bit POSIX current time when the
        manager created the row."
    ::= { hRUZClientTrigTableEntry 1 }

hRUZClientTriggerRef OBJECT-TYPE
    SYNTAX RowPointer
    MAX-ACCESS read-create
    STATUS     current
    DESCRIPTION
        "(U//FOUO) The value contains the RowPointer that identifies
         the row in the hRUZClientsTable that is associated with the
         trigger specified by this row.

         (U//FOUO) Multiple rows in this table may point to the same client in
         the hRUZClientsTable."
    ::= { hRUZClientTrigTableEntry 2 }

hRUZClientTriggerType OBJECT-TYPE
    SYNTAX     INTEGER { absoluteTime(1), elapsedTime(2),
                         electronicSerialNumber(3), heartbeat(4) }
    MAX-ACCESS read-create
    STATUS     current
    DESCRIPTION
        "(U//FOUO) The type of trigger to be established on the client. This
         value is used to determine how to interpret the data in the
         hRUZTriggerData column.

         If this column is set to heartbeat the hRUZTriggerData column is set
         to all ZEROES and the row is extended by the hRUZClientHrtbtTable
         which defines the remainder of the Trigger."
    ::= { hRUZClientTrigTableEntry 3 }

hRUZClientTriggerData OBJECT-TYPE
    SYNTAX       OCTET STRING(SIZE (8 | 16))
    MAX-ACCESS read-create
    STATUS     current
    DESCRIPTION
        "(U//FOUO) The data associated with the type of trigger specified by the
         hRUZTriggerType column of this row.

         Absolute Time - this column value specifies date and time in 64-bit
                         POSIX time format.

         Elapsed Time - this column value specifies the unsigned 64-bit integer
                        number of seconds to allow to elapse after transmitting
                        the message before the client initiates the zeroization
                        process.

         Electronic Serial Number - this column specifies the 14 character ASCII
                                    encoded station identifier formatted as
                                    specified in 0N716929 and padded on the
                                    right with ASCII space characters."
    ::= { hRUZClientTrigTableEntry 4 }

hRUZClientTriggerRowStatus OBJECT-TYPE
    SYNTAX     RowStatus
    MAX-ACCESS read-create
    STATUS     current
    DESCRIPTION
        "(U//FOUO) The status of the row, by which new entries may be created,
         or old entries deleted from this table.

         (U//FOUO) If values are not valid for the required columns, an
         inconsistentName error will be returned for this object.

         (U//FOUO) If any column is set to an invalid or unsupported value
         (during row creation or any other time), a wrongValue error will be
         returned for that object.

         (U//FOUO) An active row may not be changed to an inconsistent state.
         If such an attempt is made, an inconsistentValue error will be
         returned. In other words, any new values must be valid values for an
         active row.

         (U//FOUO) At a minimum, implementations must support createAndGo and
         destroy management functions. Support for createAndWait, active,
         notInService, and notReady management functions is optional."
    ::= { hRUZClientTrigTableEntry 5 }

-- =========
-- RUZ Client Heartbeats
-- =========
hRUZClientHrtbtTableCount OBJECT-TYPE
    SYNTAX     Unsigned32
    MAX-ACCESS read-only
    STATUS     current
    DESCRIPTION
        "(U//FOUO) The number of rows in the hRUZClientHrtbtTable."
    ::= { hRUZClientHeartbeats 1}

hRUZClientHrtbtTableLastChanged OBJECT-TYPE
    SYNTAX     TimeStamp
    MAX-ACCESS read-only
    STATUS     current
    DESCRIPTION
        "(U//FOUO) The value of hSystemUpTime the last time any entry in the
         hRUZClientHrtbtTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hRUZClientHeartbeats 2}

hRUZClientHrtbtTable OBJECT-TYPE
    SYNTAX     SEQUENCE OF HRUZClientHrtbtTableEntry
    MAX-ACCESS not-accessible
    STATUS     current
    DESCRIPTION
        "(U//FOUO) This table stores Render Useless Zeroization Heartbeats to
         be, or that have been, established on the associated client. This
         table is supported by RUZ Net Controllers.

         (U//FOUO) This table is used to control the payload of RUZ messages
         sent to clients."
    ::= { hRUZClientHeartbeats 3 }

hRUZClientHrtbtTableEntry OBJECT-TYPE
    SYNTAX     HRUZClientHrtbtTableEntry
    MAX-ACCESS not-accessible
    STATUS     current
    DESCRIPTION
        "(U//FOUO) A row in the hRUZClientHrtbtTable specifying RUZ Heartbeat
         information."
    INDEX  { hRUZClientTriggerID }
    ::= { hRUZClientHrtbtTable 1 }

HRUZClientHrtbtTableEntry ::= SEQUENCE
{
   hRUZClientHrtbtPeerAddrType            IPAddressType,
   hRUZClientHrtbtPeerAddr                IPAddress,
   hRUZClientHrtbtInterval                Unsigned32,
   hRUZClientHrtbtMissedCount             INTEGER,
   hRUZClientHrtbtDirection               INTEGER
}

hRUZClientHrtbtPeerAddrType OBJECT-TYPE
    SYNTAX     IPAddressType
    MAX-ACCESS read-create
    STATUS     current
    DESCRIPTION
        "(U//FOUO) The Internet Protocol version, IPv4 or IPv6, of the CT
         address of the peer with which the heartbeat will occur. The value of
         this property determines the size and format of the
         hRUZClientHrtbtPeerAddr."
    ::= { hRUZClientHrtbtTableEntry 2 }

hRUZClientHrtbtPeerAddr OBJECT-TYPE
    SYNTAX     IPAddress
    MAX-ACCESS read-create
    STATUS     current
    DESCRIPTION
        "(U//FOUO) The Internet Protocol addressing information for the peer
         with which the heartbeat will occur. The size and format of this column
         is determined by the hRUZClientHrtbtPeerAddrType."
    ::= { hRUZClientHrtbtTableEntry 3 }

hRUZClientHrtbtInterval OBJECT-TYPE
    SYNTAX     Unsigned32
    MAX-ACCESS read-create
    STATUS     current
    DESCRIPTION
        "(U//FOUO) This indicates the number of seconds between each attempt to
         re-send the heartbeat."
    ::= { hRUZClientHrtbtTableEntry 4 }

hRUZClientHrtbtMissedCount OBJECT-TYPE
    SYNTAX     INTEGER(0..255)
    MAX-ACCESS read-create
    STATUS     current
    DESCRIPTION
        "(U//FOUO) Setting that determines the number of successive missed
         heartbeat requests/responses that will trigger the HAIPE to initiate
         the zeroization process."
    ::= { hRUZClientHrtbtTableEntry 5 }

hRUZClientHrtbtDirection OBJECT-TYPE
    SYNTAX     INTEGER{ receive(0), send(1) }
    MAX-ACCESS read-create
    STATUS     current
    DESCRIPTION
        "(U//FOUO) Setting that determines if the HAIPE sends the heartbeat
         requests to the peer or if it should expect to receive the requests.

         0 = Device receives heartbeat signal from peer.
         1 = Device sends heartbeat signal to peer."
    ::= { hRUZClientHrtbtTableEntry 6 }


-- **********************************************************************
-- RUZ Client
-- **********************************************************************

-- =========
-- RUZ Net Controller Table
-- =========
hRUZNetControllersTableCount OBJECT-TYPE
    SYNTAX     Unsigned32
    MAX-ACCESS read-only
    STATUS     current
    DESCRIPTION
        "(U//FOUO) The number of rows in the hRUZNetControllersTable."
    ::= { hRUZNetControllers 1}

hRUZNetConTableLastChanged OBJECT-TYPE
    SYNTAX     TimeStamp
    MAX-ACCESS read-only
    STATUS     current
    DESCRIPTION
        "(U//FOUO) The value of hSystemUpTime the last time any entry in the
         hRUZNetControllersTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hRUZNetControllers 2}

hRUZNetControllersTable OBJECT-TYPE
    SYNTAX     SEQUENCE OF HRUZNetControllersTableEntry
    MAX-ACCESS not-accessible
    STATUS     current
    DESCRIPTION
        "(U//FOUO) This table stores authorized Render Useless Zeroization
         Net Controller IP Address information.  This table is supported by
         RUZ Clients.

         (U//FOUO) This table is consulted when the local HAIPE receives RUZ
         messages through an established Security Association. RUZ Clients
         only process RUZ messages from authorized RUZ Net Controllers."
    ::= { hRUZNetControllers 3 }

hRUZNetControllersTableEntry OBJECT-TYPE
    SYNTAX     HRUZNetControllersTableEntry
    MAX-ACCESS not-accessible
    STATUS     current
    DESCRIPTION
        "(U//FOUO) A row in the hRUZNetControllersTable specifying an authorized
         RUZ Net Controller IP address information."
    INDEX  { hRUZNetControllerIPAddressType, hRUZNetControllerIPAddress }
    ::= { hRUZNetControllersTable 1 }

HRUZNetControllersTableEntry ::= SEQUENCE
{
   hRUZNetControllerIPAddressType   IPAddressType,
   hRUZNetControllerIPAddress	      IPAddress,
   hRUZNetControllerPIN             OCTET STRING,
   hRUZNetControllerRowStatus	      RowStatus
}

hRUZNetControllerIPAddressType OBJECT-TYPE
    SYNTAX     IPAddressType
    MAX-ACCESS not-accessible
    STATUS     current
    DESCRIPTION
        "(U//FOUO) IP version of an authorized RUZ Net Controller's CT IP
        Address (IPv4/IPv6).   Note, this value determines the size and format
        of the associated hRUZNetControllerIPAddress value."
    ::= { hRUZNetControllersTableEntry 1 }

hRUZNetControllerIPAddress OBJECT-TYPE
    SYNTAX     IPAddress
    MAX-ACCESS not-accessible
    STATUS     current
    DESCRIPTION
        "(U//FOUO) CT IP Address of an authorized RUZ Net Controller."
    ::= { hRUZNetControllersTableEntry 2 }

hRUZNetControllerPIN OBJECT-TYPE
    SYNTAX     OCTET STRING (SIZE(8))
    MAX-ACCESS read-create
    STATUS     current
    DESCRIPTION
        "(U//FOUO) 8 character ASCII PIN to limit read/edit access to this row."
    ::= { hRUZNetControllersTableEntry 3 }

hRUZNetControllerRowStatus OBJECT-TYPE
    SYNTAX     RowStatus
    MAX-ACCESS read-create
    STATUS     current
    DESCRIPTION
        "(U//FOUO) The status of the row, by which new entries may be created,
         or old entries deleted from this table.

         (U//FOUO) If values are not valid for the required columns, an
         inconsistentName error will be returned for this object.

         (U//FOUO) If any column is set to an invalid or unsupported value
         (during row creation or any other time), a wrongValue error will be
         returned for that object.

         (U//FOUO) An active row may not be changed to an inconsistent state.
         If such an attempt is made, an inconsistentValue error will be
         returned. In other words, any new values must be valid values for an
         active row.

         (U//FOUO) At a minimum, implementations must support createAndGo and
         destroy management functions. Support for createAndWait, active,
         notInService, and notReady management functions is optional."
    ::= { hRUZNetControllersTableEntry 4 }

-- =========
-- RUZ Local Triggers
-- =========
hRUZLocalTrigTableCount OBJECT-TYPE
    SYNTAX     Unsigned32
    MAX-ACCESS read-only
    STATUS     current
    DESCRIPTION
        "(U//FOUO) The number of rows in the hRUZLocalsTable."
    ::= { hRUZLocalTriggers 1}

hRUZLocalTrigTableLastChanged OBJECT-TYPE
    SYNTAX     TimeStamp
    MAX-ACCESS read-only
    STATUS     current
    DESCRIPTION
        "(U//FOUO) The value of hSystemUpTime the last time any entry in the
         hRUZLocalsTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hRUZLocalTriggers 2}

hRUZLocalTrigTable OBJECT-TYPE
    SYNTAX     SEQUENCE OF HRUZLocalTrigTableEntry
    MAX-ACCESS not-accessible
    STATUS     current
    DESCRIPTION
        "(U//FOUO) This table stores Render Useless Zeroization triggers that
         have been established on the Local HAIPE."
    ::= { hRUZLocalTriggers 3 }

hRUZLocalTrigTableEntry OBJECT-TYPE
    SYNTAX     HRUZLocalTrigTableEntry
    MAX-ACCESS not-accessible
    STATUS     current
    DESCRIPTION
        "(U//FOUO) A row in the hRUZLocalTrigTable specifying a RUZ trigger
         information."
    INDEX  { hRUZLocalTriggerID }
    ::= { hRUZLocalTrigTable 1 }

HRUZLocalTrigTableEntry ::= SEQUENCE
{
   hRUZLocalTriggerID                  OCTET STRING,
   hRUZLocalTriggerType                INTEGER,
   hRUZLocalTriggerData                OCTET STRING,
   hRUZLocalTriggerMsgTime             DateAndTime,
   hRUZLocalTriggerPIN                 OCTET STRING,
   hRUZLocalTriggerRowStatus	         RowStatus
}

hRUZLocalTriggerID OBJECT-TYPE
    SYNTAX OCTET STRING (SIZE(4))
    MAX-ACCESS not-accessible
    STATUS     current
    DESCRIPTION
        "(U//FOUO)The unique system identifier for this trigger. If created
         using SNMP of RUZ protocol this value will be set by the manager or
         Net Controller. If created via HMI this value shall be the 32 LSB of
         the SHA2 HASH of the CT IP Address of the local HAIPE concatenated
         with the 64-bit POSIX current time when the row was created."
    ::= { hRUZLocalTrigTableEntry 1 }

hRUZLocalTriggerType OBJECT-TYPE
    SYNTAX     INTEGER { absoluteTime(1), elapsedTime(2),
                         electronicSerialNumber(3), heartbeat(4) }
    MAX-ACCESS read-create
    STATUS     current
    DESCRIPTION
        "(U//FOUO) The type of established trigger. This value is used to
         determine how to interpret the data in the hRUZLocalTriggerData column.

         If this column is set to heartbeat the hRUZTriggerData column is set
         to all ZEROES and the row is extended by the hRUZLocalHeartbeats
         table which defines the remainder of the Trigger."
    ::= { hRUZLocalTrigTableEntry 2 }

hRUZLocalTriggerData OBJECT-TYPE
    SYNTAX       OCTET STRING(SIZE (8 | 16))
    MAX-ACCESS read-create
    STATUS     current
    DESCRIPTION
        "(U//FOUO) The data associated with the type of trigger specified by the
         hRUZTriggerType column of this row. If the Trigger is a heartbeat
         the data for it is stored in the hRUZLocalHrtbtTable.

         Absolute Time - this column value specifies date and time in 64-bit
                         POSIX time format.

         Elapsed Time - this column value specifies the unsigned 64-bit integer
                        number of seconds to allow to elapse after receiving
                        the message before the client initiates the zeroization
                        process.

         Electronic Serial Number - this column specifies the 14 character ASCII
                                    encoded station identifier formatted as
                                    specified in 0N716929 and padded on the
                                    right with ASCII space characters."
    ::= { hRUZLocalTrigTableEntry 3 }

hRUZLocalTriggerMsgTime OBJECT-TYPE
    SYNTAX     DateAndTime
    MAX-ACCESS read-create
    STATUS     current
    DESCRIPTION
        "(U//FOUO) This indicates the date and time that the trigger indicated
         by this row was received."
    ::= { hRUZLocalTrigTableEntry 4 }

hRUZLocalTriggerPIN OBJECT-TYPE
    SYNTAX     OCTET STRING (SIZE(8))
    MAX-ACCESS read-create
    STATUS     current
    DESCRIPTION
        "(U//FOUO) 8 character ASCII PIN to limit read/edit access to this row."
    ::= { hRUZLocalTrigTableEntry 5 }

hRUZLocalTriggerRowStatus OBJECT-TYPE
    SYNTAX     RowStatus
    MAX-ACCESS read-create
    STATUS     current
    DESCRIPTION
        "(U//FOUO) The status of the row, by which new entries may be created,
         or old entries deleted from this table.

         (U//FOUO) If values are not valid for the required columns, an
         inconsistentName error will be returned for this object.

         (U//FOUO) If any column is set to an invalid or unsupported value
         (during row creation or any other time), a wrongValue error will be
         returned for that object.

         (U//FOUO) An active row may not be changed to an inconsistent state.
         If such an attempt is made, an inconsistentValue error will be
         returned. In other words, any new values must be valid values for an
         active row.

         (U//FOUO) At a minimum, implementations must support createAndGo and
         destroy management functions. Support for createAndWait, active,
         notInService, and notReady management functions is optional."
    ::= { hRUZLocalTrigTableEntry 6 }


-- =========
-- RUZ Local Heartbeats
-- =========
hRUZLocalHrtbtTableCount OBJECT-TYPE
    SYNTAX     Unsigned32
    MAX-ACCESS read-only
    STATUS     current
    DESCRIPTION
        "(U//FOUO) The number of rows in the hRUZLocalHrtbtTable."
    ::= { hRUZLocalHeartbeats 1}

hRUZLocalHrtbtTableLastChanged OBJECT-TYPE
    SYNTAX     TimeStamp
    MAX-ACCESS read-only
    STATUS     current
    DESCRIPTION
        "(U//FOUO) The value of hSystemUpTime the last time any entry in the
         hRUZLocalHrtbtTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hRUZLocalHeartbeats 2}

hRUZLocalHrtbtTable OBJECT-TYPE
    SYNTAX     SEQUENCE OF HRUZLocalHrtbtTableEntry
    MAX-ACCESS not-accessible
    STATUS     current
    DESCRIPTION
        "(U//FOUO) This table stores Render Useless Zeroization Heartbeats that
         have been established on the local HAIPE."
    ::= { hRUZLocalHeartbeats 3 }

hRUZLocalHrtbtTableEntry OBJECT-TYPE
    SYNTAX     HRUZLocalHrtbtTableEntry
    MAX-ACCESS not-accessible
    STATUS     current
    DESCRIPTION
        "(U//FOUO) A row in the hRUZLocalHrtbtTable specifying RUZ Heartbeat
         information."
    INDEX  { hRUZLocalTriggerID }
    ::= { hRUZLocalHrtbtTable 1 }

HRUZLocalHrtbtTableEntry ::= SEQUENCE
{
   hRUZLocalHrtbtPeerAddrType            IPAddressType,
   hRUZLocalHrtbtPeerAddr                IPAddress,
   hRUZLocalHrtbtInterval                Unsigned32,
   hRUZLocalHrtbtMissedCount             INTEGER,
   hRUZLocalHrtbtDirection               INTEGER
}

hRUZLocalHrtbtPeerAddrType OBJECT-TYPE
    SYNTAX     IPAddressType
    MAX-ACCESS read-create
    STATUS     current
    DESCRIPTION
        "(U//FOUO) The Internet Protocol version, IPv4 or IPv6, of the CT
         address of the peer with which the heartbeat will occur. The value of
         this property determines the size and format of the
         hRUZLocalHrtbtPeerAddr."
    ::= { hRUZLocalHrtbtTableEntry 2 }

hRUZLocalHrtbtPeerAddr OBJECT-TYPE
    SYNTAX     IPAddress
    MAX-ACCESS read-create
    STATUS     current
    DESCRIPTION
        "(U//FOUO) The Internet Protocol addressing information for the peer
         with which the heartbeat will occur. The size and format of this column
         is determined by the hRUZLocalHrtbtPeerAddrType."
    ::= { hRUZLocalHrtbtTableEntry 3 }

hRUZLocalHrtbtInterval OBJECT-TYPE
    SYNTAX     Unsigned32
    MAX-ACCESS read-create
    STATUS     current
    DESCRIPTION
        "(U//FOUO) This indicates the number of seconds between each attempt to
         re-send the heartbeat."
    ::= { hRUZLocalHrtbtTableEntry 4 }

hRUZLocalHrtbtMissedCount OBJECT-TYPE
    SYNTAX     INTEGER(0..255)
    MAX-ACCESS read-create
    STATUS     current
    DESCRIPTION
        "(U//FOUO) Setting that determines the number of successive missed
         heartbeat requests/responses that will trigger the HAIPE to initiate
         the zeroization process."
    ::= { hRUZLocalHrtbtTableEntry 5 }

hRUZLocalHrtbtDirection OBJECT-TYPE
    SYNTAX     INTEGER{ receive(0), send(1) }
    MAX-ACCESS read-create
    STATUS     current
    DESCRIPTION
        "(U//FOUO) Setting that determines if the HAIPE sends the heartbeat
         requests to the peer or if it should expect to receive the requests.

         0 = Device receives heartbeat signal from peer.
         1 = Device sends heartbeat signal to peer."
    ::= { hRUZLocalHrtbtTableEntry 6 }

END
