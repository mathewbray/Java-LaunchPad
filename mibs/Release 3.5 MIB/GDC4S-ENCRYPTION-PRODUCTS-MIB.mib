--BEGIN Revision History
--
--20091215 - MIB00184 - Acdc sonetEncryptors branch to Products and SonetEncryptor
    -- branch to Apps.
--
--20091027 - DRN00180 - Add Key Distribution branch  and keyDistributionApp branch.
--
--20091027 - Added taclaneProductsRegistrationMIB OBJECT IDENTIFIER to show
--connection between this MIB and the lower level taclaneProductsRegistrationMIB.
--
--20060726  Added comment that 'name' of MIB module in the
--GDC4S-ASSIGNMENTS-MIB.mib file changed, so the IMPORTS statement
--in this in this module is now completely correct.
--
--20060721
--a. Added comment identifying in which MIB module the descriptor/OID
--for {gdc4sEncryptionProductsMIB 2 } is currently defined
--b. Added comment about potential problem with IMPORTS clause.
--
--END Revision history

GDC4S-ENCRYPTION-PRODUCTS-MIB DEFINITIONS ::= BEGIN
    IMPORTS
    MODULE-IDENTITY
        FROM SNMPv2-SMI
    gdc4sAssignmentsMIB
        FROM GDC4S-ASSIGNMENTS-MIB;

    gdc4sEncryptionProductsMIB MODULE-IDENTITY
        LAST-UPDATED	    "200602031028Z"
        ORGANIZATION	    "General Dynamics C4 Systems"
        CONTACT-INFO        "Infosec Support General Dynamics C4 Systems    
                            
                            
                            
                            
                            
                            Corporation
                            
                            
                            
                            
                            
                            
                            
                            
                            77 A Street
                            Needham Heights, MA
                            02494-2806
                            Telephone: 877-230-0236
                            email: INFOSECSUPPORT@GDC4S.COM"
        DESCRIPTION         "(U//FOUO) This MIB supports the family of Encryption 
                            Products designed and developed by General  Dynamics
                            Corporation."

        REVISION	    "200602031028Z"
        DESCRIPTION         "Initial version of this module"
        ::= { gdc4sAssignmentsMIB 24 }


    products OBJECT IDENTIFIER ::= { gdc4sEncryptionProductsMIB 1 }

    networkEncryptors OBJECT IDENTIFIER ::= { products 1 }

    taclaneProducts OBJECT IDENTIFIER ::= { networkEncryptors 1 }

    taclaneMicroProducts OBJECT IDENTIFIER ::= { taclaneProducts 1 }

    taclaneGigEMiniProducts OBJECT IDENTIFIER ::= { taclaneProducts 2 }

    --
    --20091027 - Added taclaneProductsRegistrationMIB OBJECT IDENTIFIER to show
    --connection between this MIB and the lower level taclaneProductsRegistrationMIB.
    --
    taclaneProductsRegistrationMIB OBJECT IDENTIFIER ::= { taclaneProducts 3 }

    mediaEncryptors OBJECT IDENTIFIER ::= { products 2 }

    fibreChannelEncryptor OBJECT IDENTIFIER ::= { mediaEncryptors 1 }

    --20091027 - DRN00180 - Add Key Distribution branch
    --
    keyDistributors OBJECT IDENTIFIER ::= { products 3 }

    --20091215 - MIB00184 - New OID for KG-530 (sonet Encryptors)
    --
    sonetEncryptors OBJECT IDENTIFIER ::= { products 4 }

    --20091027 - Added common branch to show link to
    --GDC4S-Encryption-Products-Common-MIB
    common OBJECT IDENTIFIER ::= { gdc4sEncryptionProductsMIB 2 }

    applications OBJECT IDENTIFIER ::= { gdc4sEncryptionProductsMIB 3 }

    networkEncryptor OBJECT IDENTIFIER ::= { applications 1 }

    mediaEncryptor OBJECT IDENTIFIER ::= { applications 2 }

    --20091027 - DRN MIB00180 - Added keyDistributionApp
    keyDistributionApp OBJECT IDENTIFIER ::= { applications 3 }

    --20091215 - MIB00184 - New OID for KG-530 (sonet Encryptors)
    --
    sonetEncryptor OBJECT IDENTIFIER ::= { applications 4 }

    experimental OBJECT IDENTIFIER ::= { gdc4sEncryptionProductsMIB 4 }

    expNetworkEncryptor OBJECT IDENTIFIER ::= { experimental 1 }


END
