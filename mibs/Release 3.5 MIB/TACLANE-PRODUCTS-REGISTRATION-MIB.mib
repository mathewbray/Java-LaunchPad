TACLANE-PRODUCTS-REGISTRATION-MIB DEFINITIONS ::= BEGIN
    IMPORTS
    MODULE-IDENTITY, OBJECT-IDENTITY
        FROM SNMPv2-SMI
    taclaneProducts
        FROM GDC4S-ENCRYPTION-PRODUCTS-MIB;

    taclaneProductsRegistrationMIB MODULE-IDENTITY
        LAST-UPDATED	    "200907301745Z"
        ORGANIZATION	    "General Dynamics C4 Systems Corp."
        CONTACT-INFO        "Infosec Support General Dynamics C4 Systems Corporation  
                            
                            
                            
                            
                            
                            77 A Street
                            Needham Heights, MA
                            02494-2806
                            Telephone: 877-230-0236
                            email: INFOSECSUPPORT@GDC4S.COM"
        DESCRIPTION         "This MIB module provides the Object-Identity objects
                            referenced by sysObjectID to identify the platform
                            and software version of managed TACLANE Network
                            Encryptor."

        REVISION	    "200907301745Z"
        DESCRIPTION         "initial version of this module"
        ::= { taclaneProducts 3 }


    taclaneGigERegistrations OBJECT IDENTIFIER ::= { taclaneProductsRegistrationMIB 1 }

    taclaneGigER3 OBJECT IDENTIFIER ::= { taclaneGigERegistrations 3 }

    taclaneGigER35 OBJECT-IDENTITY
        STATUS		current
        DESCRIPTION         "(U//FOUO) The Object-Identity for the TACLANE-GigE 
                            platform running an undefined version of Revision
                            3.5 of the software image."
        ::= { taclaneGigER3 5 }

    taclaneGigER35v1 OBJECT-IDENTITY
        STATUS		current
        DESCRIPTION         "(U//FOUO) The Object-Identity for the TACLANE-GigE 
                            platform running Revision 3.5 version 1 of  the
                            software image."
        ::= { taclaneGigER35 1 }

    taclaneGigER35v2 OBJECT-IDENTITY
        STATUS		current
        DESCRIPTION         "(U//FOUO) The Object-Identity for the TACLANE-GigE 
                            platform running Revision 3.5 version 2 of  the
                            software image."
        ::= { taclaneGigER35 2 }

    taclaneGigER35v3 OBJECT-IDENTITY
        STATUS		current
        DESCRIPTION         "(U//FOUO) The Object-Identity for the TACLANE-GigE 
                            platform running Revision 3.5 version 3 of  the
                            software image."
        ::= { taclaneGigER35 3 }

    taclaneGigER35v4 OBJECT-IDENTITY
        STATUS		current
        DESCRIPTION         "(U//FOUO) The Object-Identity for the TACLANE-GigE 
                            platform running Revision 3.5 version 4 of  the
                            software image."
        ::= { taclaneGigER35 4 }

    taclaneGigER35v5 OBJECT-IDENTITY
        STATUS		current
        DESCRIPTION         "(U//FOUO) The Object-Identity for the TACLANE-GigE 
                            platform running Revision 3.5 version 5 of  the
                            software image."
        ::= { taclaneGigER35 5 }

    taclaneGigER35v6 OBJECT-IDENTITY
        STATUS		current
        DESCRIPTION         "(U//FOUO) The Object-Identity for the TACLANE-GigE 
                            platform running Revision 3.5 version 6 of  the
                            software image."
        ::= { taclaneGigER35 6 }

    taclaneGigER35v7 OBJECT-IDENTITY
        STATUS		current
        DESCRIPTION         "(U//FOUO) The Object-Identity for the TACLANE-GigE 
                            platform running Revision 3.5 version 7 of  the
                            software image."
        ::= { taclaneGigER35 7 }

    taclaneGigER35v8 OBJECT-IDENTITY
        STATUS		current
        DESCRIPTION         "(U//FOUO) The Object-Identity for the TACLANE-GigE 
                            platform running Revision 3.5 version 8 of  the
                            software image."
        ::= { taclaneGigER35 8 }

    taclaneGigER35v9 OBJECT-IDENTITY
        STATUS		current
        DESCRIPTION         "(U//FOUO) The Object-Identity for the TACLANE-GigE 
                            platform running Revision 3.5 version 9 of  the
                            software image."
        ::= { taclaneGigER35 9 }

    taclaneGigER35v10 OBJECT-IDENTITY
        STATUS		current
        DESCRIPTION         "(U//FOUO) The Object-Identity for the TACLANE-GigE 
                            platform running Revision 3.5 version 10 of
                            the software image."
        ::= { taclaneGigER35 10 }

    taclaneMiniRegistrations OBJECT IDENTIFIER ::= { taclaneProductsRegistrationMIB 2 }

    taclaneMiniR3 OBJECT IDENTIFIER ::= { taclaneMiniRegistrations 3 }

    taclaneMiniR35 OBJECT-IDENTITY
        STATUS		current
        DESCRIPTION         "(U//FOUO) The Object-Identity for the TACLANE-Mini 
                            platform running an undefined version of Revision
                            3.5 of the software image."
        ::= { taclaneMiniR3 5 }

    taclaneMiniR35v1 OBJECT-IDENTITY
        STATUS		current
        DESCRIPTION         "(U//FOUO) The Object-Identity for the TACLANE-Mini 
                            platform running Revision 3.5 version 1 of  the
                            software image."
        ::= { taclaneMiniR35 1 }

    taclaneMiniR35v2 OBJECT-IDENTITY
        STATUS		current
        DESCRIPTION         "(U//FOUO) The Object-Identity for the TACLANE-Mini 
                            platform running Revision 3.5 version 2 of  the
                            software image."
        ::= { taclaneMiniR35 2 }

    taclaneMiniR35v3 OBJECT-IDENTITY
        STATUS		current
        DESCRIPTION         "(U//FOUO) The Object-Identity for the TACLANE-Mini 
                            platform running Revision 3.5 version 3 of  the
                            software image."
        ::= { taclaneMiniR35 3 }

    taclaneMiniR35v4 OBJECT-IDENTITY
        STATUS		current
        DESCRIPTION         "(U//FOUO) The Object-Identity for the TACLANE-Mini 
                            platform running Revision 3.5 version 4 of  the
                            software image."
        ::= { taclaneMiniR35 4 }

    taclaneMiniR35v5 OBJECT-IDENTITY
        STATUS		current
        DESCRIPTION         "(U//FOUO) The Object-Identity for the TACLANE-Mini 
                            platform running Revision 3.5 version 5 of  the
                            software image."
        ::= { taclaneMiniR35 5 }

    taclaneMiniR35v6 OBJECT-IDENTITY
        STATUS		current
        DESCRIPTION         "(U//FOUO) The Object-Identity for the TACLANE-Mini 
                            platform running Revision 3.5 version 6 of  the
                            software image."
        ::= { taclaneMiniR35 6 }

    taclaneMiniR35v7 OBJECT-IDENTITY
        STATUS		current
        DESCRIPTION         "(U//FOUO) The Object-Identity for the TACLANE-Mini 
                            platform running Revision 3.5 version 7 of  the
                            software image."
        ::= { taclaneMiniR35 7 }

    taclaneMiniR35v8 OBJECT-IDENTITY
        STATUS		current
        DESCRIPTION         "(U//FOUO) The Object-Identity for the TACLANE-Mini 
                            platform running Revision 3.5 version 8 of  the
                            software image."
        ::= { taclaneMiniR35 8 }

    taclaneMiniR35v9 OBJECT-IDENTITY
        STATUS		current
        DESCRIPTION         "(U//FOUO) The Object-Identity for the TACLANE-Mini 
                            platform running Revision 3.5 version 9 of  the
                            software image."
        ::= { taclaneMiniR35 9 }

    taclaneMiniR35v10 OBJECT-IDENTITY
        STATUS		current
        DESCRIPTION         "(U//FOUO) The Object-Identity for the TACLANE-Mini 
                            platform running Revision 3.5 version 10 of
                            the software image."
        ::= { taclaneMiniR35 10 }

    taclaneMicroRegistrations OBJECT IDENTIFIER ::= { taclaneProductsRegistrationMIB 3 }

    taclaneMicroR3 OBJECT IDENTIFIER ::= { taclaneMicroRegistrations 3 }

    taclaneMicroR33 OBJECT-IDENTITY
        STATUS		current
        DESCRIPTION         "(U//FOUO) The Object-Identity for the TACLANE-Micro 
                            platform running an undefined version of Revision
                            3.3 of the software image."
        ::= { taclaneMicroR3 3 }

    taclaneMicroR33v1 OBJECT-IDENTITY
        STATUS		current
        DESCRIPTION         "(U//FOUO) The Object-Identity for the TACLANE-Micro 
                            platform running Revision 3.3 version 1 of  the
                            software image."
        ::= { taclaneMicroR33 1 }

    taclaneMicroR33v2 OBJECT-IDENTITY
        STATUS		current
        DESCRIPTION         "(U//FOUO) The Object-Identity for the TACLANE-Micro 
                            platform running Revision 3.3 version 2 of  the
                            software image."
        ::= { taclaneMicroR33 2 }

    taclaneMicroR33v3 OBJECT-IDENTITY
        STATUS		current
        DESCRIPTION         "(U//FOUO) The Object-Identity for the TACLANE-Micro 
                            platform running Revision 3.3 version 3 of  the
                            software image."
        ::= { taclaneMicroR33 3 }

    taclaneMicroR33v4 OBJECT-IDENTITY
        STATUS		current
        DESCRIPTION         "(U//FOUO) The Object-Identity for the TACLANE-Micro 
                            platform running Revision 3.3 version 4 of  the
                            software image."
        ::= { taclaneMicroR33 4 }

    taclaneMicroR33v5 OBJECT-IDENTITY
        STATUS		current
        DESCRIPTION         "(U//FOUO) The Object-Identity for the TACLANE-Micro 
                            platform running Revision 3.3 version 5 of  the
                            software image."
        ::= { taclaneMicroR33 5 }

    taclaneMicroR33v6 OBJECT-IDENTITY
        STATUS		current
        DESCRIPTION         "(U//FOUO) The Object-Identity for the TACLANE-Micro 
                            platform running Revision 3.3 version 6 of  the
                            software image."
        ::= { taclaneMicroR33 6 }

    taclaneMicroR33v7 OBJECT-IDENTITY
        STATUS		current
        DESCRIPTION         "(U//FOUO) The Object-Identity for the TACLANE-Micro 
                            platform running Revision 3.3 version 7 of  the
                            software image."
        ::= { taclaneMicroR33 7 }

    taclaneMicroR33v8 OBJECT-IDENTITY
        STATUS		current
        DESCRIPTION         "(U//FOUO) The Object-Identity for the TACLANE-Micro 
                            platform running Revision 3.3 version 8 of  the
                            software image."
        ::= { taclaneMicroR33 8 }

    taclaneMicroR33v9 OBJECT-IDENTITY
        STATUS		current
        DESCRIPTION         "(U//FOUO) The Object-Identity for the TACLANE-Micro 
                            platform running Revision 3.3 version 9 of  the
                            software image."
        ::= { taclaneMicroR33 9 }

    taclaneMicroR33v10 OBJECT-IDENTITY
        STATUS		current
        DESCRIPTION         "(U//FOUO) The Object-Identity for the TACLANE-Micro 
                            platform running Revision 3.3 version 10 of
                            the software image."
        ::= { taclaneMicroR33 10 }

    taclaneMicroR34 OBJECT-IDENTITY
        STATUS		current
        DESCRIPTION         "(U//FOUO) The Object-Identity for the TACLANE-Micro 
                            platform running an undefined version of Revision
                            3.4 of the software image."
        ::= { taclaneMicroR3 4 }

    taclaneMicroR34v1 OBJECT-IDENTITY
        STATUS		current
        DESCRIPTION         "(U//FOUO) The Object-Identity for the TACLANE-Micro 
                            platform running Revision 3.4 version 1 of  the
                            software image."
        ::= { taclaneMicroR34 1 }

    taclaneMicroR34v2 OBJECT-IDENTITY
        STATUS		current
        DESCRIPTION         "(U//FOUO) The Object-Identity for the TACLANE-Micro 
                            platform running Revision 3.4 version 2 of  the
                            software image."
        ::= { taclaneMicroR34 2 }

    taclaneMicroR34v3 OBJECT-IDENTITY
        STATUS		current
        DESCRIPTION         "(U//FOUO) The Object-Identity for the TACLANE-Micro 
                            platform running Revision 3.4 version 3 of  the
                            software image."
        ::= { taclaneMicroR34 3 }

    taclaneMicroR34v4 OBJECT-IDENTITY
        STATUS		current
        DESCRIPTION         "(U//FOUO) The Object-Identity for the TACLANE-Micro 
                            platform running Revision 3.4 version 4 of  the
                            software image."
        ::= { taclaneMicroR34 4 }

    taclaneMicroR34v5 OBJECT-IDENTITY
        STATUS		current
        DESCRIPTION         "(U//FOUO) The Object-Identity for the TACLANE-Micro 
                            platform running Revision 3.4 version 5 of  the
                            software image."
        ::= { taclaneMicroR34 5 }

    taclaneMicroR34v6 OBJECT-IDENTITY
        STATUS		current
        DESCRIPTION         "(U//FOUO) The Object-Identity for the TACLANE-Micro 
                            platform running Revision 3.4 version 6 of  the
                            software image."
        ::= { taclaneMicroR34 6 }

    taclaneMicroR34v7 OBJECT-IDENTITY
        STATUS		current
        DESCRIPTION         "(U//FOUO) The Object-Identity for the TACLANE-Micro 
                            platform running Revision 3.4 version 7 of  the
                            software image."
        ::= { taclaneMicroR34 7 }

    taclaneMicroR34v8 OBJECT-IDENTITY
        STATUS		current
        DESCRIPTION         "(U//FOUO) The Object-Identity for the TACLANE-Micro 
                            platform running Revision 3.4 version 8 of  the
                            software image."
        ::= { taclaneMicroR34 8 }

    taclaneMicroR34v9 OBJECT-IDENTITY
        STATUS		current
        DESCRIPTION         "(U//FOUO) The Object-Identity for the TACLANE-Micro 
                            platform running Revision 3.4 version 9 of  the
                            software image."
        ::= { taclaneMicroR34 9 }

    taclaneMicroR34v10 OBJECT-IDENTITY
        STATUS		current
        DESCRIPTION         "(U//FOUO) The Object-Identity for the TACLANE-Micro 
                            platform running Revision 3.4 version 10 of
                            the software image."
        ::= { taclaneMicroR34 10 }

    taclaneMicroR35 OBJECT-IDENTITY
        STATUS		current
        DESCRIPTION         "(U//FOUO) The Object-Identity for the TACLANE-Micro 
                            platform running an undefined version of Revision
                            3.5 of the software image."
        ::= { taclaneMicroR3 5 }

    taclaneMicroR35v1 OBJECT-IDENTITY
        STATUS		current
        DESCRIPTION         "(U//FOUO) The Object-Identity for the TACLANE-Micro 
                            platform running Revision 3.5 version 1 of  the
                            software image."
        ::= { taclaneMicroR35 1 }

    taclaneMicroR35v2 OBJECT-IDENTITY
        STATUS		current
        DESCRIPTION         "(U//FOUO) The Object-Identity for the TACLANE-Micro 
                            platform running Revision 3.5 version 2 of  the
                            software image."
        ::= { taclaneMicroR35 2 }

    taclaneMicroR35v3 OBJECT-IDENTITY
        STATUS		current
        DESCRIPTION         "(U//FOUO) The Object-Identity for the TACLANE-Micro 
                            platform running Revision 3.5 version 3 of  the
                            software image."
        ::= { taclaneMicroR35 3 }

    taclaneMicroR35v4 OBJECT-IDENTITY
        STATUS		current
        DESCRIPTION         "(U//FOUO) The Object-Identity for the TACLANE-Micro 
                            platform running Revision 3.5 version 4 of  the
                            software image."
        ::= { taclaneMicroR35 4 }

    taclaneMicroR35v5 OBJECT-IDENTITY
        STATUS		current
        DESCRIPTION         "(U//FOUO) The Object-Identity for the TACLANE-Micro 
                            platform running Revision 3.5 version 5 of  the
                            software image."
        ::= { taclaneMicroR35 5 }

    taclaneMicroR35v6 OBJECT-IDENTITY
        STATUS		current
        DESCRIPTION         "(U//FOUO) The Object-Identity for the TACLANE-Micro 
                            platform running Revision 3.5 version 6 of  the
                            software image."
        ::= { taclaneMicroR35 6 }

    taclaneMicroR35v7 OBJECT-IDENTITY
        STATUS		current
        DESCRIPTION         "(U//FOUO) The Object-Identity for the TACLANE-Micro 
                            platform running Revision 3.5 version 7 of  the
                            software image."
        ::= { taclaneMicroR35 7 }

    taclaneMicroR35v8 OBJECT-IDENTITY
        STATUS		current
        DESCRIPTION         "(U//FOUO) The Object-Identity for the TACLANE-Micro 
                            platform running Revision 3.5 version 8 of  the
                            software image."
        ::= { taclaneMicroR35 8 }

    taclaneMicroR35v9 OBJECT-IDENTITY
        STATUS		current
        DESCRIPTION         "(U//FOUO) The Object-Identity for the TACLANE-Micro 
                            platform running Revision 3.5 version 9 of  the
                            software image."
        ::= { taclaneMicroR35 9 }

    taclaneMicroR35v10 OBJECT-IDENTITY
        STATUS		current
        DESCRIPTION         "(U//FOUO) The Object-Identity for the TACLANE-Micro 
                            platform running Revision 3.5 version 10 of
                            the software image."
        ::= { taclaneMicroR35 10 }

    taclaneVitaRegistrations OBJECT IDENTIFIER ::= { taclaneProductsRegistrationMIB 4 }

    taclaneVitaR3 OBJECT IDENTIFIER ::= { taclaneVitaRegistrations 3 }

    taclaneVitaR35 OBJECT-IDENTITY
        STATUS		current
        DESCRIPTION         "(U//FOUO) The Object-Identity for the TACLANE-Vita 
                            platform running an undefined version of Revision
                            3.5 of the software image."
        ::= { taclaneVitaR3 5 }

    taclaneVitaR35v1 OBJECT-IDENTITY
        STATUS		current
        DESCRIPTION         "(U//FOUO) The Object-Identity for the TACLANE-Vita 
                            platform running Revision 3.5 version 1 of  the
                            software image."
        ::= { taclaneVitaR35 1 }

    taclaneVitaR35v2 OBJECT-IDENTITY
        STATUS		current
        DESCRIPTION         "(U//FOUO) The Object-Identity for the TACLANE-Vita 
                            platform running Revision 3.5 version 2 of  the
                            software image."
        ::= { taclaneVitaR35 2 }

    taclaneVitaR35v3 OBJECT-IDENTITY
        STATUS		current
        DESCRIPTION         "(U//FOUO) The Object-Identity for the TACLANE-Vita 
                            platform running Revision 3.5 version 3 of  the
                            software image."
        ::= { taclaneVitaR35 3 }

    taclaneVitaR35v4 OBJECT-IDENTITY
        STATUS		current
        DESCRIPTION         "(U//FOUO) The Object-Identity for the TACLANE-Vita 
                            platform running Revision 3.5 version 4 of  the
                            software image."
        ::= { taclaneVitaR35 4 }

    taclaneVitaR35v5 OBJECT-IDENTITY
        STATUS		current
        DESCRIPTION         "(U//FOUO) The Object-Identity for the TACLANE-Vita 
                            platform running Revision 3.5 version 5 of  the
                            software image."
        ::= { taclaneVitaR35 5 }

    taclaneVitaR35v6 OBJECT-IDENTITY
        STATUS		current
        DESCRIPTION         "(U//FOUO) The Object-Identity for the TACLANE-Vita 
                            platform running Revision 3.5 version 6 of  the
                            software image."
        ::= { taclaneVitaR35 6 }

    taclaneVitaR35v7 OBJECT-IDENTITY
        STATUS		current
        DESCRIPTION         "(U//FOUO) The Object-Identity for the TACLANE-Vita 
                            platform running Revision 3.5 version 7 of  the
                            software image."
        ::= { taclaneVitaR35 7 }

    taclaneVitaR35v8 OBJECT-IDENTITY
        STATUS		current
        DESCRIPTION         "(U//FOUO) The Object-Identity for the TACLANE-Vita 
                            platform running Revision 3.5 version 8 of  the
                            software image."
        ::= { taclaneVitaR35 8 }

    taclaneVitaR35v9 OBJECT-IDENTITY
        STATUS		current
        DESCRIPTION         "(U//FOUO) The Object-Identity for the TACLANE-Vita 
                            platform running Revision 3.5 version 9 of  the
                            software image."
        ::= { taclaneVitaR35 9 }

    taclaneVitaR35v10 OBJECT-IDENTITY
        STATUS		current
        DESCRIPTION         "(U//FOUO) The Object-Identity for the TACLANE-Vita 
                            platform running Revision 3.5 version 10 of
                            the software image."
        ::= { taclaneVitaR35 10 }


END
