--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-KMI-MIB  DEFINITIONS  ::= BEGIN

IMPORTS
    OBJECT-TYPE, Unsigned32,
    MODULE-IDENTITY                    FROM SNMPv2-SMI
    SnmpAdminString                    FROM SNMP-FRAMEWORK-MIB
    RowStatus, TimeStamp               FROM SNMPv2-TC
    hv4KMI                             FROM HAIPE-V4-FEATURE-HIERARCHY-MIB
    IPAddress, IPAddressType           FROM HAIPE-V4-TEXTUAL-CONVENTIONS-MIB;

haipeKMIMIB MODULE-IDENTITY
    LAST-UPDATED "201006231600Z"
    ORGANIZATION "HAIPE PO"
    CONTACT-INFO
         "(U//FOUO) Not Available"
    DESCRIPTION
        "(U//FOUO) This MIB defines KMI MIB objects necessary
         for a HAIPE to interface with KMI."
    REVISION     "201006231600Z"
    DESCRIPTION  "(U//FOUO) MIB 4.1.0 FINAL Release"		 
    ::= { hv4KMI 1 }

-- **********************************************************************
-- Key Management Infrastructure [KMI] Information Segments
-- **********************************************************************

-- Define Product Delivery Enclave [PDE] information
hPDEInformation           OBJECT IDENTIFIER ::= { haipeKMIMIB 1 }


-- **********************************************************************
-- Product Delivery Enclave [PDE] Scalars
-- **********************************************************************

hPDERetryDelay OBJECT-TYPE
    SYNTAX     Unsigned32
    MAX-ACCESS read-write
    STATUS     current
    DESCRIPTION
        "(U//FOUO) The amount of time to wait after a Key Management 
         Infrastructure [KMI] product download fails before attempting to retry
         the operation.  Failures in these cases do not include Transport Layer
         Security [TLS].  When a failure occurs due to the TLS protocol, then
         the hTLSEstablishmentRetryDelay applies and not this hPDERetryDelay."
    ::= { hPDEInformation 1 }

hPDERetryMaxAttempts OBJECT-TYPE
    SYNTAX     Unsigned32
    MAX-ACCESS read-write
    STATUS     current
    DESCRIPTION
        "(U//FOUO) The amount of retries attempted before giving up on this 
         Product Delivery Enclave [PDE] or Over-the-Network Keying [OTNK] 
         Intermediary due to consecutive download failures.  Failures in these
         cases do not include TLS.  When a failure occurs due to the TLS 
         protocol, then the hTLSEstablishmentMaxAttempts applies and not this
         hPDERetryMaxAttempts."
    ::= { hPDEInformation 2 }

hPDETLSEstablishmentRetryDelay OBJECT-TYPE
    SYNTAX     Unsigned32
    MAX-ACCESS read-write
    STATUS     current
    DESCRIPTION
        "(U//FOUO) The amount of time to wait before attempting to 
         establish a TLS connection with a PDE or OTNK Intermediary that 
         supports TLS."
    ::= { hPDEInformation 3 }

hPDETLSEstablishmentMaxAttempts OBJECT-TYPE
    SYNTAX     Unsigned32
    MAX-ACCESS read-write
    STATUS     current
    DESCRIPTION
        "(U//FOUO) The amount of retries attempted before giving up on this PDE
         or OTNK Intermediary due to consecutive failing attempts to try and 
         establish a TLS connection."
    ::= { hPDEInformation 4 }

-- **********************************************************************
-- PDE Table
-- **********************************************************************
    
hPDETableCount OBJECT-TYPE
    SYNTAX     Unsigned32
    MAX-ACCESS read-only
    STATUS     current
    DESCRIPTION
        "(U//FOUO) The number of rows in the hPDETable."
    ::= { hPDEInformation 5 }

hPDETableLastChanged OBJECT-TYPE
    SYNTAX     TimeStamp
    MAX-ACCESS read-only
    STATUS     current
    DESCRIPTION
        "(U//FOUO) The value of sysUpTime the last time any entry in the
         hPDETable was modified, created, or deleted by either SNMP or other
         management method (e.g. via an HMI).

         (U//FOUO) Managers can use this object to ensure that no changes to
         configuration of this table have happened since the last time it
         examined the table.

         (U//FOUO) A value of 0 indicates that no entry has been changed since
         the agent initialized."
    ::= { hPDEInformation 6 }

hPDETable OBJECT-TYPE
    SYNTAX     SEQUENCE OF HPDETableEntry
    MAX-ACCESS not-accessible
    STATUS     current
    DESCRIPTION
        "(U//FOUO)  This table allows the manager to configure Product 
         Delivery Enclaves [PDEs] or Over-the-Network Keying [OTNK] 
         Intermediaries that the HAIPE will interface with in order to obtain
         Product Availability Lists [PALs] or other Key Management 
         Infrastructure [KMI] product.

         (U//FOUO)  Entries from downloaded PALs are used to dynamically 
         populate this table.  The manager will have the capability to choose
         which KMI product to download from the automatically populated rows
         in this table.

         (U//FOUO)  Once product is downloaded it will populate the appropriate
         MIB table.  If the hPDERequest column is configured for 
         'downloadAndInstall' then the destination is a MIB table that allows 
         local consumption of the KMI product.

         (U//FOUO)  When multiple PDEs or OTNK Intermediaries are available,
         the  Manager will determine priority by initiating the request with the
         PDE or OTNK Intermediary which it feels should have the highest
         priority.  If the Hypertext Transfer Protocol [HTTP] request fails 
         after it reaches the hPDERetryMaxAttempts, then the Manager will
         attempt an alternate PDE or OTNK Intermediary which it feels has the
         next highest priority."
    ::= { hPDEInformation 7 }

hPDETableEntry OBJECT-TYPE
    SYNTAX     HPDETableEntry
    MAX-ACCESS not-accessible
    STATUS     current
    DESCRIPTION
        "(U//FOUO)  A row in the hPDETable that provides access to download a 
	 KMI product."
    INDEX  { hPDEIndex }
    ::= { hPDETable 1 }

HPDETableEntry ::= SEQUENCE
{
       hPDEIndex                       Unsigned32,
       hPDEFromPAL                     Unsigned32,
       hPDEType                        INTEGER,
       hPDERequest                     INTEGER,
       hPDERequestStatus               INTEGER,
       hPDEURI                         OCTET STRING,
       hPDERowStatus                   RowStatus
}


hPDEIndex OBJECT-TYPE
    SYNTAX     Unsigned32
    MAX-ACCESS not-accessible
    STATUS     current
    DESCRIPTION
        "(U//FOUO) A unique numeric index that identifies a potential request to
         obtain KMI Product from a Product Delivery Enclave [PDE] or 
         Over-the-Network Keying [OTNK] Intermediary.  This column is the sole 
         index to the hPDETable."
    ::= { hPDETableEntry 1 }

hPDEFromPAL OBJECT-TYPE
    SYNTAX     Unsigned32
    MAX-ACCESS read-only
    STATUS     current
    DESCRIPTION
        "(U//FOUO)  The hPDEIndex of the PAL which referenced the URI from
        which this row was created.  This allows tracking which entries in the
        hPDETable were dynamically created, and which PAL entry initiated the
        creation of the row.  For rows that are created by the manager, this
        column must not exist."
    ::= { hPDETableEntry 2 }

hPDEType OBJECT-TYPE
    SYNTAX     INTEGER { pal(1), ppk(2), appk(3), firefly(4), crl(5), pkc(6) }
    MAX-ACCESS read-create
    STATUS     current
    DESCRIPTION
        "(U//FOUO) The type of KMI product to be downloaded.  The type allows
         determination of the destination MIB table for the KMI product based 
         on the configured value of hPDERequest."
    ::= { hPDETableEntry 3 }

hPDERequest OBJECT-TYPE
    SYNTAX     INTEGER { downloadAndInstall(1), downloadAndStore(2), 
                         discardDownload(3) }
    MAX-ACCESS read-create
    STATUS     current
    DESCRIPTION
        "(U//FOUO)  This object signals the HAIPE to perform actions on the KMI
         product from the Product Delivery Enclave [PDE] or Over-the-Network 
	 Keying [OTNK] Intermediary. The following types of actions are 
	 supported:

         (U//FOUO) [downloadAndInstall] = Initiates an HTTP request to download
         the KMI product. After a successful download, the KMI product will be
         installed for local consumption and an entry is to be configured in the
         appropriate MIB table based on hPDEType:

         hPDEType   |  MIB Table Destination
         -------------------------------------
         (1) PAL    |  hPDETable  (this table)
         (2) PPK    |  hPrePlacedKeyTable          
         (3) APPK   |  hhPrePlacedKeyTable 
         (4) FF     |  hFFTable          
         (5) CRL    |  hCRLTable
         (6) PKC    |  hPKCTable


         (U//FOUO) [downloadAndStore] = Initiates an HTTP request to download
         the KMI product. After a successful download, an entry is to be
         created in the hLoadedKeyTable. Note this enumeration value only
         applies if hPDEType is 'ppk', 'appk' or 'firefly'.

         (U//FOUO) [discardDownload] = Discards the downloaded or downloading
         KMI product depending on the value of hPDERequestStatus. If
         hPDERequestStatus is currently set at 'inProgress' and hPDERequest is
         set to 'discardDownload', the KMI product will be discarded when
         possible. A 'discardDownload' while hPDERequestStatus is set  to 
         'controlError', 'downloadFailed', or 'installFailed' will cause 
         (1) the KMI product to be discarded if potentially downloaded and 
         (2) the hPDERequestStatus to revert to 'completeReady4Next'."
    ::= { hPDETableEntry 4 }

hPDERequestStatus OBJECT-TYPE
    SYNTAX     INTEGER { completeReady4Next(1), controlError(2), inProgress(3), 
	                 downloadFailed(4), installFailed(5), storeFailed(6) }
    MAX-ACCESS read-only
    STATUS     current
    DESCRIPTION
        "(U//FOUO) The status of the HTTP request operation. The following 
	 status values are supported:

         (U//FOUO) [completeReady4Next] = This is the default state where the 
	 HAIPE is ready to start a request for the KMI product. Between requests 
	 this state can only be reached after successful operations or if 
	 hPDERequest is set to 'discardDownload' during an operation.

         (U//FOUO) [controlError] - This state is reached when hPDERequest is 
	 set to an invalid value. The *2 in the table below show the cases when 
	 this state is reached based on the current hPDERequest and 
	 hPDERequestStatus values.  To exit this state, hPDERequest would need 
	 to be configured to 'discardDownload' to guarantee that any ambiguous 
	 download is discarded that could have occurred.

         (U//FOUO) [inProgress] - This state is reached when the device is 
	 either currently performing an HTTP download of a KMI product or 
	 configuring appropriate MIB tables conveying installation or storage 
	 (for key transfer) of key material.

         (U//FOUO) [downloadFailed] - This state is reached after a failure 
	 occurs during an HTTP download of a KMI product when hPDERequest was 
	 configured to either 'downloadAndStore' or 'downloadAndInstall'.

         (U//FOUO) [installFailed] - This state is reached after a failure 
	 occurs during the install of the downloaded KMI product when
	 hPDERequest was configured to 'downloadAndInstall'.

         (U//FOUO) [storeFailed] - This state is reached after a failure occurs 
	 during the store (for key transfer) of the downloaded KMI product when 
	 hPDERequest was configured to 'downloadAndStore'.

         (U//FOUO)  The table below shows the possible next state for the 
         hPDERequestStatus column based on its current state and the 
	 configuration of the hPDERequest column.


                                 |==========================|
                                 |         hPDERequest:     |
                                 |==========================|
                                 |download|download|        |
          ====================   |  And   |  And   |discard |
          |hPDERequestStatus:  \ |Install | Store  |Download|
          =======================+--------+--------+--------+
                                 | 3 -> 1 | 3 -> 1 |        |
          (1)completeReady4Next  | 3 -> 4 | 3 -> 4 | *2     |
                                 | 3 -> 5 | 3 -> 6 |        |
          -----------------------+--------+--------+--------+
          (2)controlError        | *2     | *2     |  1     |
          -----------------------+--------+--------+--------+
          (3)inProgress          | *2     | *2     |  1     |
          -----------------------+--------+--------+--------+
          (4)downloadFailed      | *2     | *2     |  1     |
          -----------------------+--------+--------+--------+
          (5)installFailed       | *2     | *2     |  1     |
          -----------------------+--------+--------+--------+
          (6)storeFailed         | *2     | *2     |  1     |
          -----------------------+--------+--------+--------+

          Note1:  *2 are transitions that happen only under incorrect 
          hPDERequest configurations.  To exit the 'controlError' state,
          it is necessary for hPDERequest to be configured to
          'discardDownload' in order to guarantee that any ambiguous download
          is discarded. The *2 transitions should not occur under normal 
          conditions.

          Note2: Normal uninterrupted transitions after configuration 
          of the hPDERequest are shown with the following notation:
          'a -> b'.  Where 'a' is the next state transition followed
          by state 'b'.  When multiple rows are shown such as:
          'a -> b'
          'a -> c'
          this implies that the next state is 'a' but the state after
          'a' can be either 'b' or 'c'."
    ::= { hPDETableEntry 5 }

hPDEURI OBJECT-TYPE
    SYNTAX     OCTET STRING (SIZE(1..384))
    MAX-ACCESS read-create
    STATUS     current
    DESCRIPTION
        "(U//FOUO)  The URI that defines where to obtain KMI product
         from the Product Delivery Enclave [PDE] or Over-the-Network Keying 
	 [OTNK] Intermediary.  For PAL entries that contain a PKC rekey 
         or issuance notification, this is the fixed URI defined for certificate
         notification retrieval.

         (U//FOUO)  The hostname in the hPDEURI is matched with the 
         hPDEMappingHostname (of hPDEMappingTable) to provide a link to its
         associated PT IP address located in the hPDEMappingPTIPAddress 
         (of hPDEMappingTable).

         Note:  'https' implies TLS, while 'http' implies no TLS."
    ::= { hPDETableEntry 6 }

hPDERowStatus OBJECT-TYPE
    SYNTAX     RowStatus
    MAX-ACCESS read-create
    STATUS     current
    DESCRIPTION
        "(U//FOUO) The status of the row, by which new entries may be created,
         or old entries deleted from this table.

         (U//FOUO) Entries created within this table may not become active
         unless all read-create columns in this table have valid values,
         as detailed by each individual column's description.

         (U//FOUO) At a minimum, implementations must support createAndGo,
         active, and destroy management functions. Support for createAndWait,
         notInService, and notReady management functions is optional."
    ::= { hPDETableEntry 7 }

-- **********************************************************************
-- PDE Mapping Table
-- **********************************************************************
    
hPDEMappingTableCount OBJECT-TYPE
    SYNTAX     Unsigned32
    MAX-ACCESS read-only
    STATUS     current
    DESCRIPTION
        "(U//FOUO) The number of rows in the hPDEMappingTable."
    ::= { hPDEInformation 8 }

hPDEMappingTableLastChanged OBJECT-TYPE
    SYNTAX     TimeStamp
    MAX-ACCESS read-only
    STATUS     current
    DESCRIPTION
        "(U//FOUO) The value of sysUpTime the last time any entry in the
         hPDEMappingTable was modified, created, or deleted by either SNMP or other
         management method (e.g. via an HMI).

         (U//FOUO) Managers can use this object to ensure that no changes to
         configuration of this table have happened since the last time it
         examined the table.

         (U//FOUO) A value of 0 indicates that no entry has been changed since
         the agent initialized."
    ::= { hPDEInformation 9 }

hPDEMappingTable OBJECT-TYPE
    SYNTAX     SEQUENCE OF HPDEMappingTableEntry
    MAX-ACCESS not-accessible
    STATUS     current
    DESCRIPTION
        "(U//FOUO)  This table allows configuration of Product 
         Delivery Enclaves [PDEs] or Over-the-Network Keying [OTNK] 
         Intermediaries that the HAIPE will interface with in order to obtain
         Product Availability Lists [PALs] or other Key Management 
         Infrastructure [KMI] product.

        (U//FOUO)   This table provides the mapping between the hostname and
         PT IP address of the configured PDE or Over-the-Network Keying [OTNK] 
         Intermediary.  A row in the hPDEMappingTable links the PT IP address 
         from this table based on the hostname in the hPDEURI."
    ::= { hPDEInformation 10 }

hPDEMappingTableEntry OBJECT-TYPE
    SYNTAX     HPDEMappingTableEntry
    MAX-ACCESS not-accessible
    STATUS     current
    DESCRIPTION
        "(U//FOUO)  A row in the hPDEMappingTable that provides mapping of 
         hostname to PT IP address."
    INDEX  { hPDEMappingIndex }
    ::= { hPDEMappingTable 1 }

HPDEMappingTableEntry ::= SEQUENCE
{
       hPDEMappingIndex               Unsigned32,
       hPDEMappingPTIPAddressType     IPAddressType,
       hPDEMappingPTIPAddress         IPAddress,
       hPDEMappingHostname            SnmpAdminString,
       hPDEMappingRowStatus           RowStatus
}


hPDEMappingIndex OBJECT-TYPE
    SYNTAX     Unsigned32
    MAX-ACCESS not-accessible
    STATUS     current
    DESCRIPTION
        "(U//FOUO) A unique numeric index that identifies hostname to PT IP
         address mapping for a Product Delivery Enclave [PDE] or 
         Over-the-Network Keying [OTNK] Intermediary.  This column is the sole
         index to the hPDEMappingTable."
    ::= { hPDEMappingTableEntry 1 }

hPDEMappingPTIPAddressType OBJECT-TYPE
    SYNTAX     IPAddressType
    MAX-ACCESS read-create
    STATUS     current
    DESCRIPTION
        "(U//FOUO) The Internet Protocol Version, IPv4 or IPv6, of the PT IP
	 address associated with the Product Delivery Enclave [PDE].
	 Specifically, the value of this property determines the size and format
	 of hPDEMappingPTIPAddress."
    ::= { hPDEMappingTableEntry 2 }    

hPDEMappingPTIPAddress OBJECT-TYPE
    SYNTAX     IPAddress
    MAX-ACCESS read-create
    STATUS     current
    DESCRIPTION
        "(U//FOUO)  The PT IP address associated with the Product Delivery 
	 Enclave [PDE] or Over-the-Network Keying [OTNK] Intermediary configured
	 in the hPDEMappingHostname column."
    ::= { hPDEMappingTableEntry 3 }

hPDEMappingHostname OBJECT-TYPE
    SYNTAX     SnmpAdminString
    MAX-ACCESS read-create
    STATUS     current
    DESCRIPTION
        "(U//FOUO)  The registered hostname of the Product Delivery  
         Enclave [PDE] or Over-the-Network Keying [OTNK] Intermediary where
         KMI product is requested."
    ::= { hPDEMappingTableEntry 4 }

hPDEMappingRowStatus OBJECT-TYPE
    SYNTAX     RowStatus
    MAX-ACCESS read-create
    STATUS     current
    DESCRIPTION
        "(U//FOUO) The status of the row, by which new entries may be created,
         or old entries deleted from this table.

         (U//FOUO) At a minimum, implementations must support createAndGo
         and destroy management functions. Support for createAndWait,
         notInService, and notReady management functions is optional."
    ::= { hPDEMappingTableEntry 5 }


END
