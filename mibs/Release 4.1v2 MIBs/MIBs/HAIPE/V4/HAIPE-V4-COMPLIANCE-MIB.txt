HAIPE-V4-COMPLIANCE-MIB DEFINITIONS ::= BEGIN
IMPORTS
    MODULE-IDENTITY                 FROM SNMPv2-SMI
    haipe                           FROM HAIPE-ASSIGNMENTS-MIB
    haipev4FeatureHierarchyMIB      FROM HAIPE-V4-FEATURE-HIERARCHY-MIB;

haipev4ComplianceMIB MODULE-IDENTITY
    LAST-UPDATED "201006231600Z"
    ORGANIZATION "HAIPE PO"
    CONTACT-INFO
         "(U//FOUO) Not Available"
    DESCRIPTION
        "(U//FOUO) This MIB defines compliance statements which
        define the levels of conformance required by the various HAIPE
        IS documents.  Each HAIPE IS v4.x version will contain a
        sub-mib-module to this tree structure to document MIB
        requirements imposed by each HAIPE IS v4.x version. This module
	is merely a top-level node for all sub-mib-modules."
    REVISION     "201006231600Z"
    DESCRIPTION  "(U//FOUO) MIB 4.1.0 FINAL Release"		
    ::= { haipev4FeatureHierarchyMIB 2 }    

END
