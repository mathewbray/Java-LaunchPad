--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-TRAFFIC-PROTECTION-MIB  DEFINITIONS  ::= BEGIN

IMPORTS
    OBJECT-TYPE, Unsigned32,
    NOTIFICATION-TYPE,
    MODULE-IDENTITY                     FROM SNMPv2-SMI
    SnmpAdminString                     FROM SNMP-FRAMEWORK-MIB
    RowPointer, RowStatus, DateAndTime,
    TruthValue,
    TEXTUAL-CONVENTION, TimeStamp       FROM SNMPv2-TC
    HaipeManualSATransformSuites,
    HaipeIKEv1SATransformSuites,
    HaipeIKEv2IKESATransformSuites,
    HaipeIKEv2CHILDSATransformSuites,
    IPAddress, IPAddressType,
    PortNumber                          FROM HAIPE-V4-TEXTUAL-CONVENTIONS-MIB
    hv4TrafficProtection                FROM HAIPE-V4-FEATURE-HIERARCHY-MIB;

haipev4TrafficProtectionMIB MODULE-IDENTITY
    LAST-UPDATED "201006231600Z"
    ORGANIZATION "HAIPE PO"
    CONTACT-INFO
         "(U//FOUO) Not Available"
    DESCRIPTION
        "(U//FOUO) This MIB defines the HAIPE traffic protection MIB objects."
    REVISION     "201006231600Z"
    DESCRIPTION  "(U//FOUO) MIB 4.1.0 FINAL Release"
    
    ::= { hv4TrafficProtection 1 }

-- **********************************************************************
-- Traffic Protection Information Segments
-- **********************************************************************

-- Defines the traffic protection control objects that trigger some action
-- when set to some value
hTPControlObjects               OBJECT IDENTIFIER ::= { haipev4TrafficProtectionMIB 1 }

-- Defines the traffic protection global scalars
hTPGlobalScalars                OBJECT IDENTIFIER ::= { haipev4TrafficProtectionMIB 2 }

-- Defines all branches under the SPD and SAD
hTPPolicyEnforcement            OBJECT IDENTIFIER ::= { haipev4TrafficProtectionMIB 3 }
hSecurityPolicyDatabase         OBJECT IDENTIFIER ::= { hTPPolicyEnforcement 1 }
hSecurityAssociationDatabase    OBJECT IDENTIFIER ::= { hTPPolicyEnforcement 2 }

-- SPD branches under hSecurityPolicyDatabase branch
hPolicyTrafficSelectors         OBJECT IDENTIFIER ::= { hSecurityPolicyDatabase 1 }
hPolicyLocalTrafficSelectors    OBJECT IDENTIFIER ::= { hPolicyTrafficSelectors 1 }
hPolicyRemoteTrafficSelectors   OBJECT IDENTIFIER ::= { hPolicyTrafficSelectors 2 }

hPolicyRules                    OBJECT IDENTIFIER ::= { hSecurityPolicyDatabase 2}

hSecurityAssociationProfiles    OBJECT IDENTIFIER ::= { hSecurityPolicyDatabase 3 }
hManualSAProfiles               OBJECT IDENTIFIER ::= { hSecurityAssociationProfiles 1 }
hManualSASecAttrProfiles        OBJECT IDENTIFIER ::= { hManualSAProfiles 1 }
hIKEv1SAProfiles                OBJECT IDENTIFIER ::= { hSecurityAssociationProfiles 2 }
hIKEv1SASecAttrProfiles         OBJECT IDENTIFIER ::= { hIKEv1SAProfiles 1 }
hIKEv1SANtwkParamsProfiles      OBJECT IDENTIFIER ::= { hIKEv1SAProfiles 2 }
hIKEv2IKESAProfiles             OBJECT IDENTIFIER ::= { hSecurityAssociationProfiles 3 }
hIKEv2CHILDSASecAttrProfiles    OBJECT IDENTIFIER ::= { hIKEv2IKESAProfiles 1 }
hIKEv2CHILDSANtwkParamsProfiles OBJECT IDENTIFIER ::= { hIKEv2IKESAProfiles 2 }
hIKEv2IKESANtwkParamsProfiles   OBJECT IDENTIFIER ::= { hIKEv2IKESAProfiles 3 }

hTFCConfig                      OBJECT IDENTIFIER ::= { hSecurityPolicyDatabase 4}

-- SAD branches under hSecurityAssociationDatabase branch
hEstablishedTrafficSelectors    OBJECT IDENTIFIER ::= { hSecurityAssociationDatabase 1 }
hEstablishedLocalTS             OBJECT IDENTIFIER ::= { hEstablishedTrafficSelectors 1 }
hEstablishedRemoteTS            OBJECT IDENTIFIER ::= { hEstablishedTrafficSelectors 2 }
hManualSAD                      OBJECT IDENTIFIER ::= { hSecurityAssociationDatabase 2 }
hIKEv1SAD                       OBJECT IDENTIFIER ::= { hSecurityAssociationDatabase 3 }
hIKEv2SAD                       OBJECT IDENTIFIER ::= { hSecurityAssociationDatabase 4 }
hIKEv2CHILDSAD                  OBJECT IDENTIFIER ::= { hIKEv2SAD 1 }
hIKEv2IKESAD                    OBJECT IDENTIFIER ::= { hIKEv2SAD 2 }

-- Defines all traffic protection notifications
hTPNotifications                OBJECT IDENTIFIER ::= { haipev4TrafficProtectionMIB 4 }


-- **********************************************************************
-- Traffic Protection Control Objects
-- **********************************************************************

useIKEVersion OBJECT-TYPE
    SYNTAX     INTEGER { ikev1FollowedByikev2(1), ikev2FollowedByikev1(2),
                         ikev1Andikev2(3), ikev1Only(4), ikev2Only(5),
			 disabled(6) }
    MAX-ACCESS read-write
    STATUS     current
    DESCRIPTION
        "(U//FOUO) A global switch indicating the HAIPE's IKE version preference
         when initiating an IKE Exchange for the creation of an Automated SA.
	 
         (U//FOUO) [ikev1FollowedByikev2] If this object is set to
         'ikev1FollowedByikev2', the HAIPE will initiate an IKEv1 Exchange.
         If a subsequent IKEv1 response is never recieved, the HAIPE will
         initiate an IKEv2 Exchange.

         (U//FOUO) [ikev2FollowedByikev1] If this object is set to
         'ikev2FollowedByikev1', the HAIPE will initiate an IKEv2 Exchange.
         If a subsequent IKEv2 response is never recieved, the HAIPE will
         initiate an IKEv1 Exchange.

         (U//FOUO) [ikev1Andikev2] If this object is set to 'ikev1Andikev2',
         the HAIPE will initiate both an IKEv1 Exchange and IKEv2 Exchange
         in parallel.
	 
	 (U//FOUO) [ikev1Only] If this object is set to 'ikev1Only', the HAIPE
	 will only initiate an IKEv1 Exchange.
	 
	 (U//FOUO) [ikev2Only] If this object is set to 'ikev2Only', the HAIPE
	 will only initiate an IKEv2 Exchange.

	 (U//FOUO) [disabled] If this object is set to 'disabled', the HAIPE
	 will not initiate an IKEv1 or IKEv2 Exchange.
	 
	 (U//FOUO) Note, this scalar only exists if a HAIPE supports the 
	 Automated SA Extension (IKEv1) and/or the Automated SA-IKEv2 Extension 
	 (IKEv2). If a HAIPE supports the Automated SA Extension (IKEv1) then
	 only the 'ikev1Only' and 'disabled' enumeration values apply. If the 
	 HAIPE supports the Automated SA-IKEv2 Extension (IKEv2), then only the
	 'ikev2Only' and 'disabled' enumeration values apply. All enumeration
	 values apply if the HAIPE supports both the Automated SA
         Extension (IKEv1) and the Automated SA-IKEv2 Extension (IKEv2)."
    ::= { hTPControlObjects 1 }

-- **********************************************************************
-- Traffic Protection Global Scalars
-- **********************************************************************


-- **********************************************************************
-- SPD Traffic Selectors
-- **********************************************************************

-- =========
-- Policy Local Traffic Selector Table
-- =========

hPolicyLocalTSTableCount OBJECT-TYPE
    SYNTAX     Unsigned32
    MAX-ACCESS read-only
    STATUS     current
    DESCRIPTION
        "(U//FOUO) The number of rows in the hPolicyLocalTSTable."
    ::= { hPolicyLocalTrafficSelectors 1 }

hPolicyLocalTSTableLastChanged OBJECT-TYPE
    SYNTAX     TimeStamp
    MAX-ACCESS read-only
    STATUS     current
    DESCRIPTION
        "(U//FOUO) The value of hSystemUpTime the last time any entry in the
         hPolicyLocalTSTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hPolicyLocalTrafficSelectors 2 }

hPolicyLocalTSTable OBJECT-TYPE
    SYNTAX     SEQUENCE OF HPolicyLocalTSTableEntry
    MAX-ACCESS not-accessible
    STATUS     current
    DESCRIPTION
        "(U//FOUO) The table containing a list of local traffic selectors that
         IP packets are checked against when they arrive on the HAIPE's
         interface. IP packets are also checked against selectors in the
         hPolicyRemoteTSTable. Note the two indices to this table:
         (1) hPolicyLocalTSName and (2) hPolicyLocalTSIndex. This table allows
         multiple traffic selectors to be grouped under the same
         hPolicyLocalTSName with each set of traffic selectors distinguished by
         hPolicyLocalTSIndex.

         (U//FOUO) This table is part of the Security Policy Database, and is
         only used in this context. It is distinct from the Established Traffic
         Selector Tables, which form part of the Security Association Database.

         (U//FOUO) An implementation is not required to support multiple traffic
         selectors. Single traffic selectors may be supported with one entry
         identified by a unique hPolicyLocalTSName and any hPolicyLocalTSIndex
         value. If single traffic selectors are only desired, the implementation
         should prevent configuration of multiple entries with the same
         hPolicyLocalTSName.

         (U//FOUO) A complete selector (Local and Remote) is constructed by
         using both this table and the hPolicyRemoteTSTable. The
         hPolicyRemoteTSTable must contain at least one selector of the same
         name (i.e. there must be at least one row in the hPolicyRemoteTSTable
         with a value in hPolicyRemoteTSName equal to hPolicyLocalTSName).
         Configured multiple traffic selectors abide by RFC 4306's
         'mix-and-match' semantics. Hence, any combination of local and remote
         PT address and port ranges with the same hPolicyLocalTSName and
         hPolicyRemoteTSName are handled under the same rule.

         (U//FOUO) As an example, suppose two hPolicyLocalTSTable entries exist
         with the following:(1) local PT address and port range of A, (2) local
         PT address and port range of B, and two hPolicyRemoteTSTable entries
         exist with the following: (1) remote PT address and port range of C,
         (2) remote PT address and port range of D. This means that traffic is
         allowed to flow between every possible combination (A-C, A-D, B-C,
         B-D). If every possible combination of traffic selectors violates the
         security policy (for example, traffic cannot flow between B and C),
         single entries with unique hPolicyRemoteTSName (in turn, multiple rule
         entries) would need to be configured (in this example, the traffic
         selector pairs would consist of two groups: A-C, A-D; and B-D).

         (U//FOUO) Note, for IKEv2, the address ranges and ports under one value
         in the hPolicyLocalTSName column constitute the TSi payload, while the
         remote PT address ranges and port under the same value in the
         hPolicyRemoteTSName column (hPolicyRemoteTSTable) constitute the TSr
         payload.

         (U//FOUO) A row in this table defines a set of traffic selectors to
         which the IP packet is checked against."
    ::= { hPolicyLocalTrafficSelectors 3 }

hPolicyLocalTSTableEntry OBJECT-TYPE
    SYNTAX    HPolicyLocalTSTableEntry
    MAX-ACCESS not-accessible
    STATUS     current
    DESCRIPTION
        "(U//FOUO) An entry in the hPolicyLocalTSTable, defining one set of
        local traffic selectors that an IP packet is checked against."
    INDEX  { hPolicyLocalTSName, hPolicyLocalTSIndex }
    ::= { hPolicyLocalTSTable 1 }

HPolicyLocalTSTableEntry ::= SEQUENCE
{
   hPolicyLocalTSName                    SnmpAdminString,
   hPolicyLocalTSIndex                   Unsigned32,
   hPolicyLocalTSPTAddrType              IPAddressType,
   hPolicyLocalTSPTAddrBegin             IPAddress,
   hPolicyLocalTSPTAddrEnd               IPAddress,
   hPolicyLocalTSProtocol                Unsigned32,
   hPolicyLocalTSPortBegin               PortNumber,
   hPolicyLocalTSPortEnd                 PortNumber,
   hPolicyLocalTSRowStatus               RowStatus
}

hPolicyLocalTSName OBJECT-TYPE
    SYNTAX     SnmpAdminString (SIZE(1..32))
    MAX-ACCESS not-accessible
    STATUS     current
    DESCRIPTION
        "(U//FOUO) The administrative name defining the set of local traffic
         selectors that an IP packet may match. Multiple traffic selectors may
         use the same administrative name, implying a group. It is the combination
         of hPolicyLocalTSName and hPolicyLocalTSIndex that uniquely identifies
         each row or set of traffic selectors."
    ::= { hPolicyLocalTSTableEntry 1 }

hPolicyLocalTSIndex OBJECT-TYPE
    SYNTAX     Unsigned32
    MAX-ACCESS not-accessible
    STATUS     current
    DESCRIPTION
        "(U//FOUO) A unique numeric index for rows, or sets of traffic
         selectors, with the same hPolicyLocalTSName. This value, in combination
         with hPolicyLocalTSName, uniquely identifies each row, or set of
         traffic selectors."
    ::= { hPolicyLocalTSTableEntry 2 }

hPolicyLocalTSPTAddrType OBJECT-TYPE
    SYNTAX     IPAddressType
    MAX-ACCESS read-create
    STATUS     current
    DESCRIPTION
        "(U//FOUO) The Internet Protocol Version, IPv4 or IPv6, of the local PT
         address range. Specifically, the value of this property determines the
         size and format of the hPolicyLocalTSPTAddrBegin and
         hPolicyLocalTSPTAddrEnd."
    ::= { hPolicyLocalTSTableEntry 3 }

hPolicyLocalTSPTAddrBegin OBJECT-TYPE
    SYNTAX     IPAddress
    MAX-ACCESS read-create
    STATUS     current
    DESCRIPTION
        "(U//FOUO) The starting address of a local address range that an IP
         packet must match in order for the row, or set of traffic selectors, to
         be considered a match.

    (U//FOUO) The address type value set (IPv4 address value,
         IPv6 address value) in this column should be consistent with the
         hPolicyLocalTSPTAddrType column.

         (U//FOUO) If the SPD rule that refers to this traffic selector is
         bidirectional, the value in this column will be compared against the
         packet's source address for outgoing data traffic and the packet's
         desination address for incoming data traffic. If the rule is
         unidirectional inbound, the value in this column will be compared
         against the packet's destination address. If the rule is undirectional
         outbound, the value in this column will be compared with the packet's
         source address.

         (U//FOUO) To have the local PT address range set to the ANY value (i.e.
         packet will not be checked against this selector), this object must be
         set to 0.0.0.0 for IPv4, or to ::0 for IPv6, while
         hPolicyLocalTSPTAddrEnd is set to 255.255.255.255 for IPv4, or to
         FFFF:FFFF:FFFF:FFFF:FFFF:FFFF:FFFF:FFFF for IPv6.

         (U//FOUO) Note, for all outgoing multicast SAs, the local PT address
         range should represent either a specific host range or the ANY value
         (0.0.0.0 to 255.255.255.255 for IPv4, or ::0 to
         FFFF:FFFF:FFFF:FFFF:FFFF:FFFF:FFFF:FFFF for IPv6). For all incoming
         multicast SAs, the local PT address range should represent one or
         possibly multiple PT multicast addresses to which the local HAIPE
         listens on. "
    ::= { hPolicyLocalTSTableEntry 4 }

hPolicyLocalTSPTAddrEnd OBJECT-TYPE
    SYNTAX     IPAddress
    MAX-ACCESS read-create
    STATUS     current
    DESCRIPTION
        "(U//FOUO) The ending address of a local address range that an IP packet
         must match in order for the row, or set of traffic selectors, to be
         considered a match. If this column is set to the same value as the
         hPolicyLocalTSPTAddrBegin, the local PT address range indicates an
         exact single address match.

    (U//FOUO) The address type value set (IPv4 address value,
         IPv6 address value) in this column should be consistent with the
         hPolicyLocalTSPTAddrType column.

         (U//FOUO) If the SPD rule that refers to this traffic selector is
         bidirectional, the value in this column will be compared against the
         packet's source address for outgoing data traffic and the packet's
         desination address for incoming data traffic. If the rule is
         unidirectional inbound, the value in this column will be compared
         against the packet's destination address. If the rule is undirectional
         outbound, the value in this column will be compared with the packet's
         source address.

         (U//FOUO) To set this selector to a single host, this column's value
         should be the same as hPolicyLocalTSPTAddrBegin.

         (U//FOUO) To have the local PT address range set to the ANY value (i.e.
         packet will not be checked against this selector), this object must be
         set to 255.255.255.255 for IPv4, or to
         FFFF:FFFF:FFFF:FFFF:FFFF:FFFF:FFFF:FFFF for IPv6, while
         hPolicyLocalTSPTAddrBegin is set to 0.0.0.0 for IPv4, or to ::0 for
         IPv6.

         (U//FOUO) Note, for all outgoing multicast SAs, the local PT address
         range should represent either a specific host range or the ANY value
         (0.0.0.0 to 255.255.255.255 for IPv4, or ::0 to
         FFFF:FFFF:FFFF:FFFF:FFFF:FFFF:FFFF:FFFF for IPv6). For all incoming
         multicast SAs, the local PT address range should represent one or
         possibly multiple PT multicast addresses to which the local HAIPE
         listens on. "
    ::= { hPolicyLocalTSTableEntry 5 }

hPolicyLocalTSProtocol OBJECT-TYPE
    SYNTAX     Unsigned32 (0..255)
    MAX-ACCESS read-create
    STATUS     current
    DESCRIPTION
        "(U//FOUO) The protocol selector value for this set of traffic
         selectors. If this column is set to 0, the packet's protocol value will
         not be checked."
    ::= { hPolicyLocalTSTableEntry 6 }

hPolicyLocalTSPortBegin OBJECT-TYPE
    SYNTAX     PortNumber
    MAX-ACCESS read-create
    STATUS     current
    DESCRIPTION
        "(U//FOUO) The starting port of a local port range that an IP packet
         must match in order for the row, or set of traffic selectors, to be
         considered a match.

         (U//FOUO) If the SPD rule that refers to this traffic selector is
         bidirectional, the value in this column will be compared against the
         packet's source port for outgoing data traffic and the packet's
         desination port for incoming data traffic. If the rule is
         unidirectional inbound, the value in this column will be compared
         against the packet's destination port. If the rule is undirectional
         outbound, the value in this column will be compared with the packet's
         source port.

         (U//FOUO) To have the local port range set to the ANY value, this
         object must be set to 0, while hPolicyLocalTSPortEnd is set to 65535.

         (U//FOUO) To have the local port range set to the OPAQUE value, this
         object must be set to 65535, while hPolicyLocalTSPortEnd is set to 0.

         (U//FOUO) For SAs intended for discovery, the local port range should
         include port 3623."
    ::= { hPolicyLocalTSTableEntry 7 }

hPolicyLocalTSPortEnd OBJECT-TYPE
    SYNTAX     PortNumber
    MAX-ACCESS read-create
    STATUS     current
    DESCRIPTION
        "(U//FOUO) The ending port of a local port range that an IP packet must
         match in order for the row, or set of traffic selectors, to be
         considered a match. If this column is set to the same value as the
         hPolicyLocalTSPortBegin, the local port range indicates an exact single
         port match.

         (U//FOUO) If the SPD rule that refers to this traffic selector is
         bidirectional, the value in this column will be compared against the
         packet's source port for outgoing data traffic and the packet's
         desination port for incoming data traffic. If the rule is
         unidirectional inbound, the value in this column will be compared
         against the packet's destination port. If the rule is undirectional
         outbound, the value in this column will be compared with the packet's
         source port.

         (U//FOUO) To set this selector to a single port, this column's value
         should be the same as hPolicyLocalTSPortBegin.

         (U//FOUO) To have the local port range set to the ANY value, this
         object must be set to 65535, while hPolicyLocalTSPortBegin is set to 0.

         (U//FOUO) To have the local port range set to the OPAQUE value, this
         object must be set to 0, while hPolicyLocalTSPortBegin is set to 65535.

         (U//FOUO) For SAs intended for discovery, the local port range should
         include port 3623."
    ::= { hPolicyLocalTSTableEntry 8 }

hPolicyLocalTSRowStatus OBJECT-TYPE
    SYNTAX     RowStatus
    MAX-ACCESS read-create
    STATUS     current
    DESCRIPTION
        "(U//FOUO) The status of the row, by which new entries may be created,
         or existing entries modified or deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

         (U//FOUO) If an active row is deleted, and it is the only row with a
         particular hPolicyLocalTSName, the rule pointing to this selector (if
         any) must be changed to notInService."
    ::= { hPolicyLocalTSTableEntry 9 }

-- =========
-- Policy Remote Traffic Selector Table
-- =========

hPolicyRemoteTSTableCount OBJECT-TYPE
    SYNTAX     Unsigned32
    MAX-ACCESS read-only
    STATUS     current
    DESCRIPTION
        "(U//FOUO) The number of rows in the hPolicyRemoteTSTable."
    ::= { hPolicyRemoteTrafficSelectors 1 }

hPolicyRemoteTSTableLastChanged OBJECT-TYPE
    SYNTAX     TimeStamp
    MAX-ACCESS read-only
    STATUS     current
    DESCRIPTION
        "(U//FOUO) The value of hSystemUpTime the last time any entry in the
         hPolicyRemoteTSTable was modified, created, or deleted by either SNMP
         or other management method (e.g. via an HMI).

         (U//FOUO) Managers can use this object to ensure that no changes to
         configuration of this table have happened since the last time it
         examined the table.

         (U//FOUO) A value of 0 indicates that no entry has been changed since
         the agent initialized."
    ::= { hPolicyRemoteTrafficSelectors 2 }

hPolicyRemoteTSTable OBJECT-TYPE
    SYNTAX     SEQUENCE OF HPolicyRemoteTSTableEntry
    MAX-ACCESS not-accessible
    STATUS     current
    DESCRIPTION
        "(U//FOUO) The table containing a list of remote traffic selectors that
         IP packets are checked against when they arrive on the HAIPE's
         interface. IP packets are also checked against selectors in the
         hPolicyLocalTSTable. Note the two indices to this table:
         (1) hPolicyRemoteTSName and (2) hPolicyRemoteTSIndex. This table allows
         multiple traffic selectors to be grouped under the same
         hPolicyRemoteTSName with each set of traffic selectors distinguished by
         hPolicyRemoteTSIndex.

         (U//FOUO) This table is part of the Security Policy Database, and is
         only used in this context. It is distinct from the Established Traffic
         Selector Tables, which form part of the Security Association Database.

         (U//FOUO) An implementation is not required to support multiple traffic
         selectors. Single traffic selectors may be supported with one entry
         identified by a unique hPolicyRemoteTSName and any hPolicyRemoteTSIndex
         value. If single traffic selectors are only desired, the implementation
         should prevent configuration of multiple entries with the same
         hPolicyRemoteTSName.

         (U//FOUO) A complete selector (Local and Remote) is constructed by
         using both this table and the hPolicyLocalTSTable. The
         hPolicyLocalTSTable must contain at least one selector of the same name
         (i.e. there must be at least one row in the hPolicyLocalTSTable with a
         value in hPolicyLocalTSName equal to hPolicyRemoteTSName). Configured
         multiple traffic selectors abide by RFC 4306's 'mix-and-match'
         semantics. Hence, any combination of local and remote PT address and
         port ranges with the same hPolicyLocalTSName and hPolicyRemoteTSName
         are handled under the same rule.

         (U//FOUO) As an example, suppose two hPolicyLocalTSTable entries exist
         with the following:(1) local PT address and port range of A, (2) local
         PT address and port range of B, and two hPolicyRemoteTSTable entries
         exist with the following: (1) remote PT address and port range of C,
         (2) remote PT address and port range of D. This means that traffic is
         allowed to flow between every possible combination (A-C, A-D, B-C,
         B-D). If every possible combination of traffic selectors violates the
         security policy (for example, traffic cannot flow between B and C),
         single entries with unique hPolicyRemoteTSName (in turn, multiple rule
         entries) would need to be configured (in this example, the traffic
         selector pairs would consist of two groups: A-C, A-D; and B-D).

         (U//FOUO) Note, for IKEv2, the address ranges and ports under one value
         in the hPolicyRemoteTSName column constitute the TSr payload, while the
         local PT address ranges and port under the same value in the
         hPolicyLocalTSName column (hPolicyLocalTSTable) constitute the TSi
         payload.

         (U//FOUO) A row in this table defines a set of traffic selectors to
         which the IP packet is checked against."
    ::= { hPolicyRemoteTrafficSelectors 3 }

hPolicyRemoteTSTableEntry OBJECT-TYPE
    SYNTAX     HPolicyRemoteTSTableEntry
    MAX-ACCESS not-accessible
    STATUS     current
    DESCRIPTION
        "(U//FOUO) An entry in the hPolicyRemoteTSTable, defining one set of
        remote traffic selectors that an IP packet is checked against."
    INDEX  { hPolicyRemoteTSName, hPolicyRemoteTSIndex }
    ::= { hPolicyRemoteTSTable 1 }

HPolicyRemoteTSTableEntry ::= SEQUENCE
{
   hPolicyRemoteTSName                   SnmpAdminString,
   hPolicyRemoteTSIndex                  Unsigned32,
   hPolicyRemoteTSPTAddrType             IPAddressType,
   hPolicyRemoteTSPTAddrBegin            IPAddress,
   hPolicyRemoteTSPTAddrEnd              IPAddress,
   hPolicyRemoteTSProtocol               Unsigned32,
   hPolicyRemoteTSPortBegin              PortNumber,
   hPolicyRemoteTSPortEnd                PortNumber,
   hPolicyRemoteTSRowStatus              RowStatus
}

hPolicyRemoteTSName OBJECT-TYPE
    SYNTAX     SnmpAdminString (SIZE(1..32))
    MAX-ACCESS not-accessible
    STATUS     current
    DESCRIPTION
        "(U//FOUO) The administrative name defining the set of remote traffic
         selectors that an IP packet may match. Multiple traffic selectors may
         use the same administrative name, implying a group. It is the combination
         of hPolicyRemoteTSName and hPolicyRemoteTSIndex that uniquely
         identifies each row or set of traffic selectors."
    ::= { hPolicyRemoteTSTableEntry 1 }

hPolicyRemoteTSIndex OBJECT-TYPE
    SYNTAX     Unsigned32
    MAX-ACCESS not-accessible
    STATUS     current
    DESCRIPTION
        "(U//FOUO) A unique numeric index for rows, or sets of traffic
         selectors, with the same hPolicyRemoteTSName. This value, in combination
         with hPolicyRemoteTSName, uniquely identifies each row, or set of
         traffic selectors."
    ::= { hPolicyRemoteTSTableEntry 2 }

hPolicyRemoteTSPTAddrType OBJECT-TYPE
    SYNTAX     IPAddressType
    MAX-ACCESS read-create
    STATUS     current
    DESCRIPTION
        "(U//FOUO) The Internet Protocol Version, IPv4 or IPv6, of the remote PT
         address range. Specifically, the value of this property determines the
         size and format of the hPolicyRemoteTSPTAddrBegin and
         hPolicyRemoteTSPTAddrEnd."
    ::= { hPolicyRemoteTSTableEntry 3 }

hPolicyRemoteTSPTAddrBegin OBJECT-TYPE
    SYNTAX     IPAddress
    MAX-ACCESS read-create
    STATUS     current
    DESCRIPTION
        "(U//FOUO) The starting address of a remote address range that an IP
         packet must match in order for the row, or set of traffic selectors, to
         be considered a match.

    (U//FOUO) The address type value set (IPv4 address value,
         IPv6 address value) in this column should be consistent with the
         hPolicyRemoteTSPTAddrType column.

         (U//FOUO) If the SPD rule that refers to this traffic selector is
         bidirectional, the value in this column will be compared against the
         packet's destination address for outgoing data traffic and the packet's
         source address for incoming data traffic. If the rule is unidirectional
         inbound, the value in this column will be compared against the packet's
         source address. If the rule is undirectional outbound, the value
         in this column will be compared with the packet's destination address.

         (U//FOUO) To have the remote PT address range set to the ANY value
         (i.e. packet will not be checked against this selector), this object
         must be set to 0.0.0.0 for IPv4 or to ::0 for IPv6, while
         hPolicyRemoteTSPTAddrEnd is set to 255.255.255.255 for IPv4, or to
         FFFF:FFFF:FFFF:FFFF:FFFF:FFFF:FFFF:FFFF for IPv6.

         (U//FOUO) Note, for all outgoing multicast SAs, the remote PT address
         range should represent one or possibly multiple PT multicast addresses
         to which the remote HAIPE listens on. For all incoming multicast SAs,
         the remote PT address range should represent either a specific host
         range or the ANY value (0.0.0.0-255.255.255.255 for IPv4, or ::0 to
         FFFF:FFFF:FFFF:FFFF:FFFF:FFFF:FFFF:FFFF for IPv6)."
    ::= { hPolicyRemoteTSTableEntry 4 }

hPolicyRemoteTSPTAddrEnd OBJECT-TYPE
    SYNTAX     IPAddress
    MAX-ACCESS read-create
    STATUS     current
    DESCRIPTION
        "(U//FOUO) The ending address of a remote address range that an IP
         packet must match in order for the row, or set of traffic selectors, to
         be considered a match. If this column is set to the same value as the
         hPolicyRemoteTSPTAddrBegin, the local PT address range indicates an
         exact single address match.

    (U//FOUO) The address type value set (IPv4 address value,
         IPv6 address value) in this column should be consistent with the
         hPolicyRemoteTSPTAddrType column.

         (U//FOUO) If the SPD rule that refers to this traffic selector is
         bidirectional, the value in this column will be compared against the
         packet's destination address for outgoing data traffic and the packet's
         source address for incoming data traffic. If the rule is unidirectional
         inbound, the value in this column will be compared against the packet's
         source address. If the rule is undirectional outbound, the value
         in this column will be compared with the packet's destination address.

         (U//FOUO) To set this selector to a single host, this column's value
         should be the same as hPolicyRemoteTSPTAddrBegin.

         (U//FOUO) To have the remote PT address range set to the ANY value
         (i.e. packet will not be checked against this selector), this object
         must be set to 255.255.255.255 for IPv4 or to
         FFFF:FFFF:FFFF:FFFF:FFFF:FFFF:FFFF:FFFF for IPv6, while
         hPolicyRemoteTSPTAddrBegin is set to 0.0.0.0 for IPv4, or to ::0 for
         IPv6.

         (U//FOUO) Note, for all outgoing multicast SAs, the remote PT address
         range should represent one or possibly multiple PT multicast addresses
         to which the remote HAIPE listens on. For all incoming multicast SAs,
         the remote PT address range should represent either a specific host
         range or the ANY value (0.0.0.0-255.255.255.255 for IPv4, or ::0 to
         FFFF:FFFF:FFFF:FFFF:FFFF:FFFF:FFFF:FFFF for IPv6)."
    ::= { hPolicyRemoteTSTableEntry 5 }

hPolicyRemoteTSProtocol OBJECT-TYPE
    SYNTAX     Unsigned32 (0..255)
    MAX-ACCESS read-create
    STATUS     current
    DESCRIPTION
        "(U//FOUO) The protocol selector value for this set of traffic
         selectors. If this column is set to 0, the packet's protocol value will
         not be checked."
    ::= { hPolicyRemoteTSTableEntry 6 }

hPolicyRemoteTSPortBegin OBJECT-TYPE
    SYNTAX     PortNumber
    MAX-ACCESS read-create
    STATUS     current
    DESCRIPTION
        "(U//FOUO) The starting port of a remote port range that an IP packet
         must match in order for the row, or set of traffic selectors, to be
         considered a match.

         (U//FOUO) If the SPD rule that refers to this traffic selector is
         bidirectional, the value in this column will be compared against the
         packet's destination port for outgoing data traffic and the packet's
         source port for incoming data traffic. If the rule is unidirectional
         inbound, the value in this column will be compared against the packet's
         source port. If the rule is undirectional outbound, the value
         in this column will be compared with the packet's destination port.

         (U//FOUO) To have the local port range set to the ANY value, this
         object must be set to 0, while hPolicyRemoteTSPortEnd is set to 65535.

         (U//FOUO) To have the local port range set to the OPAQUE value, this
         object must be set to 65535, while hPolicyRemoteTSPortEnd is set to 0.

         (U//FOUO) For SAs intended for discovery, the remote port range should
         include port 3623."
    ::= { hPolicyRemoteTSTableEntry 7 }

hPolicyRemoteTSPortEnd OBJECT-TYPE
    SYNTAX     PortNumber
    MAX-ACCESS read-create
    STATUS     current
    DESCRIPTION
        "(U//FOUO) The ending port of a remote port range that an IP packet must
         match in order for the row, or set of traffic selectors, to be
         considered a match. If this column is set to the same value as the
         hPolicyRemoteTSPortBegin, the remote port range indicates an exact
         single port match.

         (U//FOUO) If the SPD rule that refers to this traffic selector is
         bidirectional, the value in this column will be compared against the
         packet's destination port for outgoing data traffic and the packet's
         source port for incoming data traffic. If the rule is unidirectional
         inbound, the value in this column will be compared against the packet's
         source port. If the rule is undirectional outbound, the value
         in this column will be compared with the packet's destination port.

         (U//FOUO) To set this selector to a single port, this column's value
         should be the same as hPolicyRemoteTSPortBegin.

         (U//FOUO) To have the remote port range set to the ANY value, this
         object must be set to 65535, while hPolicyRemoteTSPortBegin is set to
         0.

         (U//FOUO) To have the remote port range set to the OPAQUE value, this
         object must be set to 0, while hPolicyRemoteTSPortBegin is set to
         65535.

         (U//FOUO) For SAs intended for discovery, the remote port range should
         include port 3623."
    ::= { hPolicyRemoteTSTableEntry 8 }

hPolicyRemoteTSRowStatus OBJECT-TYPE
    SYNTAX     RowStatus
    MAX-ACCESS read-create
    STATUS     current
    DESCRIPTION
        "(U//FOUO) The status of the row, by which new entries may be created,
         or existing entries modified or deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

         (U//FOUO) If an active row is deleted, and it is the only row with a
         particular hPolicyRemoteTSName, the rule pointing to this selector (if
         any) must be changed to notInService."
    ::= { hPolicyRemoteTSTableEntry 9 }

-- **********************************************************************
-- SPD Rule Table
-- **********************************************************************

hPolicyRuleTableCount OBJECT-TYPE
    SYNTAX     Unsigned32
    MAX-ACCESS read-only
    STATUS     current
    DESCRIPTION
        "(U//FOUO) The number of rows in the hPolicyRuleTable."
    ::= { hPolicyRules 1 }

hPolicyRuleTableLastChanged OBJECT-TYPE
    SYNTAX     TimeStamp
    MAX-ACCESS read-only
    STATUS     current
    DESCRIPTION
        "(U//FOUO) The value of hSystemUpTime the last time any entry in the
         hPolicyRuleTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hPolicyRules 2 }

hPolicyRuleTable OBJECT-TYPE
    SYNTAX     SEQUENCE OF HPolicyRuleTableEntry
    MAX-ACCESS not-accessible
    STATUS     current
    DESCRIPTION
        "(U//FOUO) The table containing an ordered list of SPD rules describing
         how to handle PT IP packets. Each SPD rule specifies one of four
    actions: (1) 'protect', (2) 'discardIn', (3) 'discardOut', and (4)
    'discardInAndOut'.

         (U//FOUO) SPD rules with a protect(1) or discardInAndOut(4) rule action
    are bidirectional, while rules with a discardIn(2) or discardOut(3)
    rule action are unidirectional."
    ::= { hPolicyRules 3 }

hPolicyRuleTableEntry OBJECT-TYPE
    SYNTAX     HPolicyRuleTableEntry
    MAX-ACCESS not-accessible
    STATUS     current
    DESCRIPTION
        "(U//FOUO) A row which describes the handling of PT IP packets."
    INDEX  { hPolicyRuleName, hPolicyRulePriority }
    ::= { hPolicyRuleTable 1 }

HPolicyRuleTableEntry ::= SEQUENCE
{
   hPolicyRuleName                       SnmpAdminString,
   hPolicyRulePriority                   Unsigned32,
   hPolicyRuleTrafficSelectorName        SnmpAdminString,
   hPolicyRuleSecAttrsProfileName        SnmpAdminString,
   hPolicyRuleAction                     INTEGER,
   hPolicyRuleDSCPClassifier             OCTET STRING,
   hPolicyRuleUseROHC                    INTEGER,
   hPolicyRuleUseBM                      SnmpAdminString,
   hPolicyRuleRowStatus                  RowStatus
}

hPolicyRuleName OBJECT-TYPE
    SYNTAX     SnmpAdminString (SIZE(1..32))
    MAX-ACCESS not-accessible
    STATUS     current
    DESCRIPTION
        "(U//FOUO) The unique administrative name identifying the rule. It is
         the combination of the hPolicyRuleName and hPolicyRulePriority that
         uniquely identifies each row or policy rule."
    ::= { hPolicyRuleTableEntry 1 }

hPolicyRulePriority OBJECT-TYPE
    SYNTAX     Unsigned32
    MAX-ACCESS not-accessible
    STATUS     current
    DESCRIPTION
        "(U//FOUO) The priority at which this rule is applied. Lower values have
         a higher priority (e.g. a value of 1 will be processed before a value
         of 2). It is the combination of the hPolicyRuleName and
         hPolicyRulePriority that uniquely identifies each row or policy rule. 
         Note, an entry's hPolicyRulePriority value must be unique - in other 
         words, no two entries may have the same hPolicyRulePriority value."
    ::= { hPolicyRuleTableEntry 2 }

hPolicyRuleTrafficSelectorName OBJECT-TYPE
    SYNTAX     SnmpAdminString (SIZE(1..32))
    MAX-ACCESS read-create
    STATUS     current
    DESCRIPTION
        "(U//FOUO) A reference string pointing to both the hPolicyLocalTSTable
         and hPolicyRemoteTSTable, determining the respective local and remote
         traffic selectors that should be compared against PT IP packets.

         (U//FOUO) A valid reference string must be specified in order for
         hPolicyRuleRowStatus to be 'active'."
    ::= { hPolicyRuleTableEntry 3 }

hPolicyRuleSecAttrsProfileName OBJECT-TYPE
    SYNTAX     SnmpAdminString (SIZE(1..32))
    MAX-ACCESS read-create
    STATUS     current
    DESCRIPTION
        "(U//FOUO) A reference string pointing to one more entries in the
         hManualSecAttrsProfileTable and/or hIKEv1SecAttrsProfileTable and/or
         hIKEv2CHLDSecAttrsProfileTable. This reference directly ties the
         hPolicyRuleTable entry to a set of cryptographic attributes. In regards
         to IKEv1 and IKEv2, the set of cryptographic attributes are used for
         negotiation and setting up the appropriate proposal.

         (U//FOUO) If hPolicyRuleAction is set to protect(1), then a valid 
         reference string must be specified in order for hPolicyRuleRowStatus
         to be 'active'."
    ::= { hPolicyRuleTableEntry 4 }

hPolicyRuleAction OBJECT-TYPE
    SYNTAX     INTEGER { protect(1), discardIn(2), discardOut(3),
                         discardInAndOut(4) }
    MAX-ACCESS read-create
    STATUS     current
    DESCRIPTION
        "(U//FOUO) This object indicates what action the HAIPE should take on
    PT IP packets matching the set or sets of traffic selectors linked by
    the hPolicyRuleTrafficSelectorName column. The value of this column can
    take one of four enumeration values: (1) 'protect', (2) 'discardIn',
    (3) 'discardOut', or (4) 'discardInAndOut'.

         (U//FOUO) [protect] The 'protect' enumeration value indicates that
         outbound packets should be protected by a security association
         establishment mechanism (manual, IKEv1, or IKEv2) with cryptographic
         and network parameters linked by the hPolicyRuleSecAttrsProfileName
         column. For inbound packets matching an entry, this enumeration
         indicates such packets may pass onto the HAIPE's PT interface.

         (U//FOUO) [discardIn] The 'discardIn' enumeration value indicates that
         an incoming post-decrypted packet should be discarded (i.e. traffic
         does not flow out the PT interface).

         (U//FOUO) [discardOut] The 'discardOut' enumeration value indicates
         that an outbound post-encrypted packet should be discarded (i.e.
         traffic does not flow out the CT interface).

         (U//FOUO) [discardInAndOut] The 'discardInAndOut' indicates that
         all packets, agnostic of their direction, should be discarded.

         (U//FOUO) Implementations that do not support the 'discardIn' and
         'discardOut' enumeration values should return a wrongValue
         exception during a SET to the hPolicyRuleAction object.

         (U//FOUO) A valid enumeration value must be specified in order for
         hPolicyRuleRowStatus to be 'active'."
    ::= { hPolicyRuleTableEntry 5 }

hPolicyRuleDSCPClassifier OBJECT-TYPE
    SYNTAX     OCTET STRING (SIZE(8))
    MAX-ACCESS read-create
    STATUS     current
    DESCRIPTION
        "(U//FOUO) The DSCP classifier that outbound PT IP packets are checked
    against. The default value is 0xFFFFFFFFFFFFFFFF (hexadecimal). For
    IPv4 headers, the DSCP bits are the six most significant bits of the
    Type of Service (TOS) bits. For IPv6 headers, the DSCP bits are the
    six most significant bits of the Traffic Class (TC) bits.

    (U//FOUO) The hPolicyRuleDSCPClassifier provides a mechanism to allow
    packets with a certain PT DSCP value to be handled by the action
    dictated by hPolicyRuleAction (only 'discardInAndOut', 'discardOut',
    and 'protect' actions apply). Note, as defined by RFC 4301, classifiers
    are not traffic selectors since they only apply to outbound packets.

    (U//FOUO) This value must be 8 octets in length and the value in this
    column will provide a list of DSCP classifier values represented as a
    64-bit vector. Each bit of this value represents a DSCP classifier
    value and set classifiers are indicated with its mapped bit set to 1
    (binary).

         (U//FOUO) 64 bit vector representation: DSCP value matches 64-bit
         Vector Map
          0: 000...000001
          1: 000...000010
          2: 000...000100
          ...
         62: 010000...000
         63: 100000...000"
    DEFVAL{'FFFFFFFFFFFFFFFF'h}
    ::= { hPolicyRuleTableEntry 6 }

hPolicyRuleUseROHC OBJECT-TYPE
    SYNTAX     INTEGER { noROHC(1), useROHCWithoutFeedback(2),
                         useROHCWithFeedback(3), 
			 rohcAcceptableWithoutFeedback (4), 
			 rohcAcceptableWithFeedback (5)}
    MAX-ACCESS read-create
    STATUS     current
    DESCRIPTION
        "(U//FOUO) An indication of whether (1) ROHC parameters should
    	be signaled in the N(ROHC_SUPPORTED) payload during IKE AUTH, 
	CREATE CHILD SA and Rekey exchanges and whether (2) feedback 
	should be sent on the newly created IKEv2 CHILD_SA.

         (U//FOUO) [hPolicyRuleUseROHC='noROHC'] If the column is set to
         'noROHC', then HAIPE will not signal ROHC parameters during the 
	 above three exchanges as an initiator or responder.
	

         (U//FOUO) [hPolicyRuleUseROHC='useROHCWithoutFeedback'] If the 
	 column is set to 'useROHCWithoutFeedback', then HAIPE will signal 
	 ROHC parameters during the above three exchanges as an initiator 
	 or responder.  Feedback will not be sent on the ROHC SA.


         (U//FOUO) [hPolicyRuleUseROHC='useROHCWithFeedback'] If the column is
         set to 'useROHCWithFeedback', then HAIPE will signal ROHC parameters
	 during the above three exchanges as an initiator or responder. 
	 Feedback will be sent on the ROHC SA.

         (U//FOUO) [hPolicyRuleUseROHC='rohcAcceptableWithoutFeedback'] If the 
	 column is set to 'rohcAcceptableWithoutFeedback', then HAIPE will 
	 not signal ROHC parameters as an initiator during the above three exchanges. 
	 However, if the peer HAIPE signals ROHC parameters as an initiator, the 
	 HAIPE will signal ROHC parameters as a responder.  Feedback will not be 
	 sent on the ROHC SA.

         (U//FOUO) [hPolicyRuleUseROHC='rohcAcceptableWithFeedback'] If the column 
	 is set to 'rohcAcceptableWithFeedback', then HAIPE will not signal 
	 ROHC parameters as an initiator during the above three exchanges. However, 
	 if the peer HAIPE signals ROHC parameters as an initiator, the HAIPE will 
	 signal ROHC parameters as a responder.  Feedback will be sent on the ROHC SA.

         (U//FOUO) The support of the useROHCWithFeedback is optional if the
         implementation does not support sending feedback.  The support of
         rohcAcceptableWithoutFeedback and rohcAcceptableWithFeedback are optional.

    	 (U//FOUO) This column must not exist if the implementation does
         not support ROHC and IKEv2."
    ::= { hPolicyRuleTableEntry 7 }

hPolicyRuleUseBM OBJECT-TYPE
    SYNTAX     SnmpAdminString (SIZE(0..32))
    MAX-ACCESS read-create
    STATUS     current
    DESCRIPTION
        "(U//FOUO) An indication of whether bandwidth management [BM] will
         be negotiated in IKEv2.
	 
         (U//FOUO) This column is a reference string that points to an entry in
         the hBMParamsProfileTable, detailing the bandwidth management
         parameters to negotiate.

         (U//FOUO) If this column is not populated or set to a zero length empty
	 string, then no bandwidth management parameters will be negotiated at 
	 the time of creation for a CHILD_SA. 
	 
	 (U//FOUO) This column must not exist for Manual SAs.

         (U//FOUO) This column must not exist if the implementation does
         not support the Bandwidth Management Extension."
    ::= { hPolicyRuleTableEntry 8 }

hPolicyRuleRowStatus OBJECT-TYPE
    SYNTAX     RowStatus
    MAX-ACCESS read-create
    STATUS     current
    DESCRIPTION
        "U//FOUO) The status of the row, by which new entries may be created, or
         old entries deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

         (U//FOUO) A row cannot be set to active while
         hPolicyRuleTrafficSelectorName or hPolicyRuleSecAttrsProfileName do not
         point to active rows in their respective tables.

         (U//FOUO) The hPolicyRuleTrafficSelectorName and
         hPolicyRuleSecAttrsProfileName columns of an active row may not be
         changed to values that are not valid, active rows in their respective
         tables (an inconsistentValue error will be returned).

         (U//FOUO) Note that for the hPolicyRuleTrafficSelectorName column to
         be valid, the rows in the hPolicyLocalTSTable and hPolicyRemoteTSTable
         with the same hPolicyLocalTSName and hPolicyRemoteTSName as
         hPolicyRuleTrafficSelectorName must be consistent in terms of
         having the same address type for all addresses and the same protocol
         value."
    ::= { hPolicyRuleTableEntry 9 }

-- **********************************************************************
-- Manual SA Profile(s)
-- **********************************************************************

-- =========
-- Manual SA Security Attributes Profile
-- =========

hManualSAProfileTableCount OBJECT-TYPE
    SYNTAX     Unsigned32
    MAX-ACCESS read-only
    STATUS     current
    DESCRIPTION
        "(U//FOUO) The number of rows in the hManualSecAttrsProfileTable."
    ::= { hManualSASecAttrProfiles 1 }

hManualSAProfileTableLastChanged OBJECT-TYPE
    SYNTAX     TimeStamp
    MAX-ACCESS read-only
    STATUS     current
    DESCRIPTION
        "(U//FOUO) The value of hSystemUpTime the last time any entry in the
         hManualSecAttrsProfileTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hManualSASecAttrProfiles 2 }

hManualSecAttrsProfileTable OBJECT-TYPE
    SYNTAX     SEQUENCE OF HManualSecAttrsProfileTableEntry
    MAX-ACCESS not-accessible
    STATUS     current
    DESCRIPTION
        "(U//FOUO) The table containing prioritized sets of cryptographic
         attributes (i.e. security attributes profile) for manual SAs associated
         with a particular hPolicyRuleTable entry. This table, in contrast to
         the hIKEv1SecAttrsProfileTable and hIKEv2CHLDSecAttrsProfileTable, is not
         used to create a manual SA, since the cryptographic attributes are
         already manually configured in the hManualSADTable. Instead, this table
         is used in outbound packet processing, distinguishing between multiple,
         viable manual SAs that an outbound packet can be sent on and aiding in
         the selection of the most appropriate one based on the
         hManualSecAttrsProfilePriority."
    ::= { hManualSASecAttrProfiles 3 }

hManualSecAttrsProfileTableEntry OBJECT-TYPE
    SYNTAX     HManualSecAttrsProfileTableEntry
    MAX-ACCESS not-accessible
    STATUS     current
    DESCRIPTION
        "(U//FOUO) A row which details one set of cryptographic attributes for a
         manual SA associated with a particular hPolicyRuleTable entry."
    INDEX  { hManualSecAttrsProfileName, hManualSecAttrsProfilePriority }
    ::= { hManualSecAttrsProfileTable 1 }

HManualSecAttrsProfileTableEntry ::= SEQUENCE
{
   hManualSecAttrsProfileName      SnmpAdminString,
   hManualSecAttrsProfilePriority  Unsigned32,
   hManualProfileTransformSuite    HaipeManualSATransformSuites,
   hManualSecAttrsProfileRowStatus RowStatus
}

hManualSecAttrsProfileName OBJECT-TYPE
    SYNTAX     SnmpAdminString (SIZE(1..32))
    MAX-ACCESS not-accessible
    STATUS     current
    DESCRIPTION
        "(U//FOUO) The unique administrative name identifying the set of
         cryptographic attributes of a manual SA associated with particular
         hPolicyRuleTable entry. Both this column and
         hManualSecAttrsProfilePriority serve as indices to this table."
    ::= { hManualSecAttrsProfileTableEntry 1 }

hManualSecAttrsProfilePriority OBJECT-TYPE
    SYNTAX     Unsigned32
    MAX-ACCESS not-accessible
    STATUS     current
    DESCRIPTION
        "(U//FOUO) A unique numeric index, indicating which cryptographic
         attributes for manual SAs are preferred over others. Lower values have
         a higher priority, indicating the most preferred cryptographic
         attributes for a manual SA. (e.g. a value of 1 indicates that the
         entry's cryptographic attributes are more preferred than those in an
         entry with a value of 2). Both this column and
    hManualSecAttrsProfileName serve as indices to this table."
    ::= { hManualSecAttrsProfileTableEntry 2 }

hManualProfileTransformSuite OBJECT-TYPE
    SYNTAX     HaipeManualSATransformSuites
    MAX-ACCESS read-create
    STATUS     current
    DESCRIPTION
        "(U//FOUO) A set of cryptographic attributes respective to manual SAs."
    ::= { hManualSecAttrsProfileTableEntry 3 }

hManualSecAttrsProfileRowStatus OBJECT-TYPE
    SYNTAX     RowStatus
    MAX-ACCESS read-create
    STATUS     current
    DESCRIPTION
        "(U//FOUO) The status of the row, by which new entries may be created, or
         old entries deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row."
    ::= { hManualSecAttrsProfileTableEntry 4 }

-- **********************************************************************
-- IKEv1 SA Profile(s)
-- **********************************************************************

-- =========
-- IKEv1 SA Security Attributes Profile
-- =========

hIKEv1SAProfileTableCount OBJECT-TYPE
    SYNTAX     Unsigned32
    MAX-ACCESS read-only
    STATUS     current
    DESCRIPTION
        "(U//FOUO) The number of rows in the hIKEv1SecAttrsProfileTable."
    ::= { hIKEv1SASecAttrProfiles 1 }

hIKEv1SAProfileTableLastChanged OBJECT-TYPE
    SYNTAX     TimeStamp
    MAX-ACCESS read-only
    STATUS     current
    DESCRIPTION
        "(U//FOUO) The value of hSystemUpTime the last time any entry in the
         hIKEv1SecAttrsProfileTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hIKEv1SASecAttrProfiles 2 }

hIKEv1SecAttrsProfileTable OBJECT-TYPE
    SYNTAX     SEQUENCE OF HIKEv1SecAttrsProfileTableEntry
    MAX-ACCESS not-accessible
    STATUS     current
    DESCRIPTION
        "(U//FOUO) The table containing prioritized sets of cryptographic
         attributes (i.e. security attributes profile) for IKEv1 SAs associated
         with a particular hPolicyRuleTable entry. This table is used to
         determine how the cryptographic suites are negotiated in the IKEv1
         exchange."
    ::= { hIKEv1SASecAttrProfiles 3 }

hIKEv1SecAttrsProfileTableEntry OBJECT-TYPE
    SYNTAX     HIKEv1SecAttrsProfileTableEntry
    MAX-ACCESS not-accessible
    STATUS     current
    DESCRIPTION
        "(U//FOUO) A row which details one set of cryptographic attributes for
    an IKEv1 SA associated with a particular hPolicyRuleTable entry."
    INDEX  { hIKEv1SecAttrsProfileName, hIKEv1SecAttrsProfilePriority }
    ::= { hIKEv1SecAttrsProfileTable 1 }

HIKEv1SecAttrsProfileTableEntry ::= SEQUENCE
{
   hIKEv1SecAttrsProfileName       SnmpAdminString,
   hIKEv1SecAttrsProfilePriority   Unsigned32,
   hIKEv1ProfileNtwkParamsRef      SnmpAdminString,
   hIKEv1ProfileTransformSuite     HaipeIKEv1SATransformSuites,
   hIKEv1SecAttrsProfileRowStatus  RowStatus
}

hIKEv1SecAttrsProfileName OBJECT-TYPE
    SYNTAX     SnmpAdminString (SIZE(1..32))
    MAX-ACCESS not-accessible
    STATUS     current
    DESCRIPTION
        "(U//FOUO) The unique administrative name identifying the set of
         cryptographic attributes of an IKEv1 SA associated with particular
         hPolicyRuleTable entry. Both this column and
         hIKEv1SecAttrsProfilePriority serve as indices to this table."
    ::= { hIKEv1SecAttrsProfileTableEntry 1 }

hIKEv1SecAttrsProfilePriority OBJECT-TYPE
    SYNTAX     Unsigned32
    MAX-ACCESS not-accessible
    STATUS     current
    DESCRIPTION
        "(U//FOUO) A unique numeric index, indicating which cryptographic
         attributes for IKEv1 SAs are preferred over others. Lower values have a
         higher priority, indicating the most preferred cryptographic attributes
         for an IKEv1 SA. (e.g. a value of 1 indicates that the entry's
         cryptographic attributes are more preferred than those in an entry with
         a value of 2). The value in this column also indicates the ordering of
         the cryptographic attributes in the IKEv1 proposal.

         (U//FOUO) Both this column and hIKEv1SecAttrsProfileName serve as
         indices to this table."
    ::= { hIKEv1SecAttrsProfileTableEntry 2 }

hIKEv1ProfileNtwkParamsRef OBJECT-TYPE
    SYNTAX     SnmpAdminString (SIZE(1..32))
    MAX-ACCESS read-create
    STATUS     current
    DESCRIPTION
        "(U//FOUO) A reference string pointing to one entry in the
         hIKEv1NtwkParamsProfileTable, providing the associated, locally-
         configured network parameters tied to a set of cryptographic attributes
         in an hIKEv1SecAttrsProfileTable entry.

         (U//FOUO) A valid reference string must be specified in order for
         hIKEv1SecAttrsProfileRowStatus to be 'active'."
    ::= { hIKEv1SecAttrsProfileTableEntry 3 }

hIKEv1ProfileTransformSuite OBJECT-TYPE
    SYNTAX     HaipeIKEv1SATransformSuites
    MAX-ACCESS read-create
    STATUS     current
    DESCRIPTION
        "(U//FOUO) A set of cryptographic attributes respective to IKEv1 SAs.

         (U//FOUO) The enumeration value paired with
         hIKEv1SecAttrsProfilePriority indicate the ordering of the transform
         suite within the IKEv1 proposal."
    ::= { hIKEv1SecAttrsProfileTableEntry 4 }

hIKEv1SecAttrsProfileRowStatus OBJECT-TYPE
    SYNTAX     RowStatus
    MAX-ACCESS read-create
    STATUS     current
    DESCRIPTION
        "U//FOUO) The status of the row, by which new entries may be created, or
         old entries deleted from this table.

         (U//FOUO) If an attempt to create a new row via createAndGo does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

         (U//FOUO) A row cannot be set to active while hIKEv1ProfileNtwkParamsRef
         does not point to an active row in the respective table.

         (U//FOUO) The hIKEv1ProfileNtwkParamsRef column of an active row may not
         be changed to values that are not valid, active rows in their
         respective tables (an inconsistentValue error will be returned)."
    ::= { hIKEv1SecAttrsProfileTableEntry 5 }

-- =========
-- IKEv1 SA Network Parameters Profile
-- =========

hIKEv1NPProfileTableCount OBJECT-TYPE
    SYNTAX     Unsigned32
    MAX-ACCESS read-only
    STATUS     current
    DESCRIPTION
        "(U//FOUO) The number of rows in the hIKEv1NtwkParamsProfileTable."
    ::= { hIKEv1SANtwkParamsProfiles 1 }

hIKEv1NPProfileTableLastChanged OBJECT-TYPE
    SYNTAX     TimeStamp
    MAX-ACCESS read-only
    STATUS     current
    DESCRIPTION
        "(U//FOUO) The value of hSystemUpTime the last time any entry in the
         hIKEv1NtwkParamsProfileTable was modified, created, or deleted by
         either SNMP or other management method (e.g. via an HMI).

         (U//FOUO) Managers can use this object to ensure that no changes to
         configuration of this table have happened since the last time it
         examined the table.

         (U//FOUO) A value of 0 indicates that no entry has been changed since
         the agent initialized."
    ::= { hIKEv1SANtwkParamsProfiles 2 }

hIKEv1NtwkParamsProfileTable OBJECT-TYPE
    SYNTAX     SEQUENCE OF HIKEv1NtwkParamsProfileTableEntry
    MAX-ACCESS not-accessible
    STATUS     current
    DESCRIPTION
        "(U//FOUO) The table containing locally-configured network parameters
         that are tied to a set of cryptographic attributes in an
         hIKEv1SecAttrsProfileTable entry. Note that these parameters are not
         negotiated during the IKEv1 exchange."
    ::= { hIKEv1SANtwkParamsProfiles 3 }

hIKEv1NtwkParamsProfileTableEntry OBJECT-TYPE
    SYNTAX     HIKEv1NtwkParamsProfileTableEntry
    MAX-ACCESS not-accessible
    STATUS     current
    DESCRIPTION
        "(U//FOUO) A row which details one set of locally-configured network
         parameters of an IKEv1 SA associated with a particular
         hIKEv1SecAttrsProfileTable entry."
    INDEX  { hIKEv1NtwkParamsProfileName }
    ::= { hIKEv1NtwkParamsProfileTable 1 }

HIKEv1NtwkParamsProfileTableEntry ::= SEQUENCE
{
   hIKEv1NtwkParamsProfileName      SnmpAdminString,
   hIKEv1ProfileTFCConfigName       SnmpAdminString,
   hIKEv1ProfileECNSetting          INTEGER,
   hIKEv1ProfileDFBitSetting        INTEGER,
   hIKEv1ProfileDSCPSetting         INTEGER,
   hIKEv1ProfileDSCPValue           OCTET STRING,
   hIKEv1ProfileFlowLabelSetting    INTEGER,
   hIKEv1ProfileFlowLabelValue      OCTET STRING,
   hIKEv1ProfilePDUNEnabled         TruthValue,
   hIKEv1ProfilePHRDRate            Unsigned32,
   hIKEv1ProfilePHRDLimit           Unsigned32,
   hIKEv1NtwkParamsProfileRowStatus RowStatus
}

hIKEv1NtwkParamsProfileName OBJECT-TYPE
    SYNTAX     SnmpAdminString (SIZE(1..32))
    MAX-ACCESS not-accessible
    STATUS     current
    DESCRIPTION
        "(U//FOUO) The unique administrative name identifying the set of
         locally-configured network parameters of an IKEv1 SA associated with a
         particular hIKEv1SecAttrsProfileTable entry. This column is the primary
         index to the hIKEv1NtwkParamsProfileTable."
    ::= { hIKEv1NtwkParamsProfileTableEntry 1 }

hIKEv1ProfileTFCConfigName OBJECT-TYPE
    SYNTAX     SnmpAdminString (SIZE(0..32))
    MAX-ACCESS read-create
    STATUS     current
    DESCRIPTION
        "(U//FOUO) A reference string pointing to one entry in the
         hTFCConfigTable, providing the associated TFC configuration to be
         used.

         (U//FOUO) If populated, the value of this object indicates which row in
         the hTFCConfigTable is to be used. This value must match the
         hTFCConfigName index value of the desired configuration.

         (U//FOUO) If this object is not populated or set to a zero length empty
         string, then no TFC mechanisms will be used by this SA."
    ::= { hIKEv1NtwkParamsProfileTableEntry 2 }

hIKEv1ProfileECNSetting OBJECT-TYPE
    SYNTAX     INTEGER { disabled(1), congestionNotification(2),
                         admissionControl(3) }
    MAX-ACCESS read-create
    STATUS     current
    DESCRIPTION
        "(U//FOUO) The setting that controls the processing mode of the Explicit
         Congestion Notification (ECN) bits, during encapsulation and
         decapsulation - the possible values are: disabled,
         congestionNotification, admissionControl.  For IPv4 headers, the ECN
         bits are Bits 1-0 (low/right) of the Type of Service (TOS) bits.  For
         IPv6 headers, the ECN bits are Bits 1-0 (low/right) of the Traffic
         Class (TC) bits.

         (U//FOUO) [disabled] If this column is set to disabled, when
         encapsulation takes place the ECN bits must be set to (10) in the CT
         header regardless of the values in the PT header of the packet being
         encapsulated.  For decapsulation, the inner headers are passed through
         unmodified.

         (U//FOUO) [congestionNotification] If this column is set to
         congestionNotification, when encapsulation takes place the ECN bits
         must be set to (10) in the CT header regardless of the values in the PT
         header of the packet being encapsulated.  For decapsulation, see the
         HAIPE IS for more details on the ECN bits processing.

         (U//FOUO) [admissionControl] If this column is set to admissionControl,
         when encapsulation takes place the ECN bits must be copied from PT
         header to the CT header.  For decapsulation, the ECN bits must be
         copied from CT header to PT header."
    DEFVAL{disabled}
    ::= { hIKEv1NtwkParamsProfileTableEntry 3 }

hIKEv1ProfileDFBitSetting OBJECT-TYPE
    SYNTAX     INTEGER { set(1), clear(2), copy(3) }
    MAX-ACCESS read-create
    STATUS     current
    DESCRIPTION
        "(U//FOUO) The setting that controls the processing mode of the Don't
         Fragment (DF) bit in the IPv4 CT header (encapsulation) - the possible
         values are: set, clear, copy.

         (U//FOUO) [set] If this column is set to set, the IPv4 CT header DF bit
         must be set to 1 (binary).

         (U//FOUO) [clear] If this column is set to clear, the IPv4 CT header DF
         Bit must be set to 0 (binary).

         (U//FOUO) [copy] If this column is set to copy, the IPv4 PT header's DF
         Bit value is copied to the IPv4 CT header's DF Bit, during
         encapsulation."
    DEFVAL{clear}
    ::= { hIKEv1NtwkParamsProfileTableEntry 4 }

hIKEv1ProfileDSCPSetting OBJECT-TYPE
    SYNTAX     INTEGER { set(1), acceptList(2) }
    MAX-ACCESS read-create
    STATUS     current
    DESCRIPTION
        "(U//FOUO) The setting that controls the processing mode of the
         Differentiated Service Code Points (DSCP) bits in the CT header
         (encapsulation); the possible values are: set, acceptList. For IPv4
         headers, the DSCP bits are the six most significant bits of the Type of
         Service (TOS) field.  For IPv6 headers, the DSCP bits are the six most
         significant bits of the Traffic Class (TC) field.

         (U//FOUO) [set] If this column is set to set, the CT header DSCP bits
         must be set to the value defined in the hIKEv1ProfileDSCPValue column.

         (U//FOUO) [acceptList] If this column is set to acceptList, the PT
         header DSCP bits are compared against a list of values defined in the
         hIKEv1ProfileDSCPValue column; if the compared DSCP bits is matched,
    they are copied over to the CT header DSCP bits.  If there is no match,
    the CT header DSCP bits are set to all 0s. "
    DEFVAL{set}
    ::= { hIKEv1NtwkParamsProfileTableEntry 5 }

hIKEv1ProfileDSCPValue OBJECT-TYPE
    SYNTAX     OCTET STRING (SIZE(1|8))
    MAX-ACCESS read-create
    STATUS     current
    DESCRIPTION
        "(U//FOUO) Depending on the value set in the hIKEv1ProfileDSCPSetting
         column (set, acceptList), this column is used in two ways.  For IPv4
         headers, the DSCP bits are the six most significant bits of the Type of
         Service (TOS) field.  For IPv6 headers, the DSCP bits are the six most
         significant bits of the Traffic Class (TC) field.

         (U//FOUO) [hIKEv1ProfileDSCPSetting=set] If the
    hIKEv1ProfileDSCPSetting column is set to set, the CT header
    Differentiated Service Code Points (DSCP) bits must be set to the value
    defined in this column and the value in this column must be one octet
    in length in the range 0x00 to 0x3f.  The DSCP value garnered from the
    Bits 5-0 (low/right most 6-bits) of this column's value is placed in
    the CT header DSCP bits. Note, if the hIKEv1ProfileDSCPSetting column
    is set to set, an attempt to set this column to value outside of the
    range 0x00 to 0x3f should fail with an invalid value error.

         (U//FOUO) [hIKEv1ProfileDSCPSetting=acceptList] If the
         hIKEv1ProfileDSCPSetting column is set to acceptList, this value must
    be 8 octets in length and the value in this column will provide a list
    of acceptable DSCP values represented as a 64-bit vector.  Each bit of
         this value represents one acceptable DSCP value and acceptable matches
         are indicated with its mapped bit is set to 1 (binary).  If the
         outgoing PT packet's DSCP value matches a value represented in the
         vector, that value is placed in the CT header DSCP bits.  If none of
         the values in the vector match an outgoing PT packet's DSCP value, the
         CT header DSCP bits are set to all 0s.

         (U//FOUO)64 bit vector representation:
         DSCP value matches 64-bit Vector Map
                  0         000...000001
                  1         000...000010
                  2         000...000100
                     . . .
                     . . .
                     . . .
                 62         010000...000
                 63         100000...000"
    DEFVAL{'00'h}
    ::= { hIKEv1NtwkParamsProfileTableEntry 6 }

hIKEv1ProfileFlowLabelSetting OBJECT-TYPE
    SYNTAX     INTEGER { set(1), copy(2) }
    MAX-ACCESS read-create
    STATUS     current
    DESCRIPTION
        "(U//FOUO) The setting that controls the processing mode of the Flow
         Label bits in the CT header (encapsulation) - the possible values are:
         set, copy; the default value is set.  Note, this column is only
         relevant to Outbound IPv6 IKEv1 SAs.

         (U//FOUO) [set] If this column is set to set, the CT header Flow Label
         bits must be set to the value defined in the
         hIKEv1ProfileFlowLabelValue column.

         (U//FOUO) [copy] If this column is set to copy, when encapsulation
         takes place the Flow Label bits must be copied from PT header to the CT
         header."
    DEFVAL{set}
    ::= { hIKEv1NtwkParamsProfileTableEntry 7 }

hIKEv1ProfileFlowLabelValue OBJECT-TYPE
    SYNTAX     OCTET STRING (SIZE(3))
    MAX-ACCESS read-create
    STATUS     current
    DESCRIPTION
        "(U//FOUO) The flow label value for the IKEv1 SA. The use of this value
    is dependent on the value of the hIKEv1ProfileFlowLabelSetting column
    (set, copy) in this row.

         (U//FOUO) [hIKEv1ProfileFlowLabelSetting=set] If the column is set to
         set, the CT header Flow Label bits must be set to the value defined in
         this column and the value in this column must be one 20-bits in length
         in the range 0x00 - 0xfffff.  The Flow Label value garnered from the
         Bits 19-0 (low/right most 20-bits) of this column's value is placed in
         the CT header Flow Label bits.

         (U//FOUO) Note, if the hIKEv1ProfileFlowLabelSetting column is set to
         'set', an attempt to set this column to value outside of the range
         0x00 - 0xfffff should fail with an invalid value error. 
	 
	 (U//FOUO) If hIKEv1ProfileFlowLabelSetting is set to 'copy', this
	 column must not exist."
    ::= { hIKEv1NtwkParamsProfileTableEntry 8 }

hIKEv1ProfilePDUNEnabled OBJECT-TYPE
    SYNTAX     TruthValue
    MAX-ACCESS read-create
    STATUS     current
    DESCRIPTION
        "(U//FOUO) The setting that determines whether or not Peer Destination
         Unreachable Notification (PDUN) messages are transmitted upon
         determination that a host is unreachable on an Inbound IKEv1 SA - the
         possible values are: true, false.

         (U//FOUO) Note, for IKEv1 SAs, PDUN messages are transmitted on the
         paired Outbound IKEv1 SA established with the remote HAIPE. "
    ::= { hIKEv1NtwkParamsProfileTableEntry 9 }

hIKEv1ProfilePHRDRate OBJECT-TYPE
    SYNTAX     Unsigned32
    MAX-ACCESS read-create
    STATUS     current
    DESCRIPTION
        "(U//FOUO) The setting that determines the rate (in seconds) at which
         Peer HAIPE Reachability Detection (PHRD) messages are transmitted on
         the IKEv1 SA; the default value is 0 (decimal).  A value of zero
         (decimal) indicates the disabled PHRD Setting, meaning that PHRD
         messages will not be transmitted."
    DEFVAL{0}
    ::= { hIKEv1NtwkParamsProfileTableEntry 10 }

hIKEv1ProfilePHRDLimit OBJECT-TYPE
    SYNTAX     Unsigned32
    MAX-ACCESS read-create
    STATUS     current
    DESCRIPTION
        "(U//FOUO) Setting that determines the number of successive missed Peer
         HAIPE Reachability Detection (PHRD) responses that will trigger the
         HAIPE to mark the IKEv1 SA as UNREACHABLE.  A PHRD response or any
         inbound traffic received on an Inbound IKEv1 SA established with the
         remote HAIPE resets the internal PHRD successive missed counter to its
         initial state.  Note, this column must only exist when the
         hIKEv1ProfilePHRDRate column is set to a non-zero value (decimal)."
    ::= { hIKEv1NtwkParamsProfileTableEntry 11 }

hIKEv1NtwkParamsProfileRowStatus OBJECT-TYPE
    SYNTAX     RowStatus
    MAX-ACCESS read-create
    STATUS     current
    DESCRIPTION
        "U//FOUO) The status of the row, by which new entries may be created, or
         old entries deleted from this table.

         (U//FOUO) If an attempt to create a new row via createAndGo does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row."
    ::= { hIKEv1NtwkParamsProfileTableEntry 12 }

-- **********************************************************************
-- IKEv2 CHILD_SA Profile(s)
-- **********************************************************************

-- =========
-- IKEv2 CHILD_SA Security Attributes Profile
-- =========

hIKEv2CHDSAtProfTableCount OBJECT-TYPE
    SYNTAX     Unsigned32
    MAX-ACCESS read-only
    STATUS     current
    DESCRIPTION
        "(U//FOUO) The number of rows in the hIKEv2CHLDSecAttrsProfileTable."
    ::= { hIKEv2CHILDSASecAttrProfiles 1 }

hIKEv2CHDSAtProfTableLastChanged OBJECT-TYPE
    SYNTAX     TimeStamp
    MAX-ACCESS read-only
    STATUS     current
    DESCRIPTION
        "(U//FOUO) The value of hSystemUpTime the last time any entry in the
         hIKEv2CHLDSecAttrsProfileTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hIKEv2CHILDSASecAttrProfiles 2 }

hIKEv2CHLDSecAttrsProfileTable OBJECT-TYPE
    SYNTAX     SEQUENCE OF HIKEv2CHLDSAtProfTableEntry
    MAX-ACCESS not-accessible
    STATUS     current
    DESCRIPTION
        "(U//FOUO) The table containing prioritized sets of cryptographic
         attributes (i.e. security attributes profile) for IKEv2 CHILD_SAs
         associated with a particular hPolicyRuleTable entry. This table is used
         to determine how the cryptographic suites are negotiated in the
         IKEv2 Create Child_SA exchange."
    ::= { hIKEv2CHILDSASecAttrProfiles 3 }

hIKEv2CHLDSAtProfTableEntry OBJECT-TYPE
    SYNTAX     HIKEv2CHLDSAtProfTableEntry
    MAX-ACCESS not-accessible
    STATUS     current
    DESCRIPTION
        "(U//FOUO) A row which details one set of cryptographic attributes for
    an IKEv2 CHILD_SA associated with a particular hPolicyRuleTable entry."
    INDEX  { hIKEv2CHLDSecAttrsProfName, hIKEv2CHLDSecAttrsProfPriority }
    ::= { hIKEv2CHLDSecAttrsProfileTable 1 }

HIKEv2CHLDSAtProfTableEntry ::= SEQUENCE
{
   hIKEv2CHLDSecAttrsProfName       SnmpAdminString,
   hIKEv2CHLDSecAttrsProfPriority   Unsigned32,
   hIKEv2CHLDProfileNtwkParamsRef   SnmpAdminString,
   hIKEv2CHLDProfileEncapMode       INTEGER,
   hIKEv2CHLDProfileTransformSuite  HaipeIKEv2CHILDSATransformSuites,
   hIKEv2CHLDSecAttrsProfRowStatus  RowStatus
}

hIKEv2CHLDSecAttrsProfName OBJECT-TYPE
    SYNTAX     SnmpAdminString (SIZE(1..32))
    MAX-ACCESS not-accessible
    STATUS     current
    DESCRIPTION
        "(U//FOUO) The unique administrative name identifying the set of
         cryptographic attributes of an IKEv2 CHILD_SA associated with
         particular hPolicyRuleTable entry. Both this column and
         hIKEv2CHLDSecAttrsProfPriority serve as indices to this table."
    ::= { hIKEv2CHLDSAtProfTableEntry 1 }

hIKEv2CHLDSecAttrsProfPriority OBJECT-TYPE
    SYNTAX     Unsigned32
    MAX-ACCESS not-accessible
    STATUS     current
    DESCRIPTION
        "(U//FOUO) A unique numeric index, indicating which cryptographic
         attributes for IKEv2 CHILD_SAs are preferred over others. Lower values
         have a higher priority, indicating the most preferred cryptographic
         attributes for an IKEv2 CHILD_SA. (e.g. a value of 1 indicates that the
         entry's cryptographic attributes are more preferred than those in an
         entry with a value of 2). The value in this column also indicates the
         ordering of the cryptographic attributes in the IKEv2 proposal.

         (U//FOUO) Both this column and hIKEv2CHLDSecAttrsProfName serve as
         indices to this table."
    ::= { hIKEv2CHLDSAtProfTableEntry 2 }

hIKEv2CHLDProfileNtwkParamsRef OBJECT-TYPE
    SYNTAX     SnmpAdminString (SIZE(1..32))
    MAX-ACCESS read-create
    STATUS     current
    DESCRIPTION
        "(U//FOUO) A reference string pointing to one entry in the
         hIKEv2CHLDNtwkParamsProfileTable, providing the associated, locally-
         configured network parameters tied to a set of cryptographic attributes
         in an hIKEv2CHLDSecAttrsProfileTable entry.

         (U//FOUO) A valid reference string must be specified in order for
         hIKEv2CHLDSecAttrsProfRowStatus to be 'active'."
    ::= { hIKEv2CHLDSAtProfTableEntry 3 }

hIKEv2CHLDProfileEncapMode OBJECT-TYPE
    SYNTAX     INTEGER { transportPreferred(1), transportOnly(2),
                         tunnelOnly(3) }
    MAX-ACCESS read-create
    STATUS     current
    DESCRIPTION
        "(U//FOUO) The IKEv2 CHILD_SA's Encapsulation Mode; the possible values
         are: transportPreferred, transportOnly, and tunnelOnly

         (U//FOUO) [transportPreferred] If hIKEv2CHLDProfileEncapMode is set to
    transportPreferred, the HAIPE will include a N(USE_TRANSPORT_MODE)
    payload in the IKEv2 CREATE_CHILD_SA exchange, but will choose not to
    delete the CHILD_SA if the response does not include the
    N(USE_TRANSPORT_MODE) payload. A tunnel-mode CHILD_SA would then be
    established.

    (U//FOUO) [transportOnly] If hIKEv2CHLDProfileEncapMode is set to
    transportOnly, the HAIPE will include a N(USE_TRANSPORT_MODE)
    payload in the IKEv2 CREATE_CHILD_SA exchange, but would delete the
    CHILD_SA if the response does not include the N(USE_TRANSPORT_MODE)
    payload.

    (U//FOUO) [tunnelOnly] If hIKEv2CHLDProfileEncapMode is set to
    tunnelOnly, the HAIPE will not include a N(USE_TRANSPORT_MODE) payload
    in the IKEv2 CREATE_CHILD_SA exchange."
    ::= { hIKEv2CHLDSAtProfTableEntry 4 }

hIKEv2CHLDProfileTransformSuite OBJECT-TYPE
    SYNTAX     HaipeIKEv2CHILDSATransformSuites
    MAX-ACCESS read-create
    STATUS     current
    DESCRIPTION
        "(U//FOUO) A set of cryptographic attributes respective to IKEv2 CHILD
         SAs.

    (U//FOUO) The enumeration value paired with
         hIKEv2CHLDSecAttrsProfPriority indicate the ordering of the transform
         suite within the IKEv2 proposal."
    ::= { hIKEv2CHLDSAtProfTableEntry 5 }

hIKEv2CHLDSecAttrsProfRowStatus OBJECT-TYPE
    SYNTAX     RowStatus
    MAX-ACCESS read-create
    STATUS     current
    DESCRIPTION
        "U//FOUO) The status of the row, by which new entries may be created, or
         old entries deleted from this table.

         (U//FOUO) If an attempt to create a new row via createAndGo does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

         (U//FOUO) A row cannot be set to active while
         hIKEv2CHLDProfileNtwkParamsRef does not point to an active row in the
         respective table.

         (U//FOUO) The hIKEv2CHLDProfileNtwkParamsRef column of an active row
         may not be changed to values that are not valid, active rows in their
         respective tables (an inconsistentValue error will be returned)."
    ::= { hIKEv2CHLDSAtProfTableEntry 6 }

-- =========
-- IKEv2 CHILD_SA Network Parameters Profile
-- =========

hIKEv2CHDNPProfTableCount OBJECT-TYPE
    SYNTAX     Unsigned32
    MAX-ACCESS read-only
    STATUS     current
    DESCRIPTION
        "(U//FOUO) The number of rows in the hIKEv2CHLDNtwkParamsProfileTable."
    ::= { hIKEv2CHILDSANtwkParamsProfiles 1 }

hIKEv2CHDNPProfTableLastChanged OBJECT-TYPE
    SYNTAX     TimeStamp
    MAX-ACCESS read-only
    STATUS     current
    DESCRIPTION
        "(U//FOUO) The value of hSystemUpTime the last time any entry in the
         hIKEv2CHLDNtwkParamsProfileTable was modified, created, or deleted by
         either SNMP or other management method (e.g. via an HMI).

         (U//FOUO) Managers can use this object to ensure that no changes to
         configuration of this table have happened since the last time it
         examined the table.

         (U//FOUO) A value of 0 indicates that no entry has been changed since
         the agent initialized."
    ::= { hIKEv2CHILDSANtwkParamsProfiles 2 }

hIKEv2CHLDNtwkParamsProfileTable OBJECT-TYPE
    SYNTAX     SEQUENCE OF HIKEv2CHLDNtwkParamsProfileEntry
    MAX-ACCESS not-accessible
    STATUS     current
    DESCRIPTION
        "(U//FOUO) The table containing locally-configured network parameters
         that are tied to a set of cryptographic attributes in an
         hIKEv2CHLDSecAttrsProfileTable entry. Note that these parameters are not
         negotiated during the IKEv2 Create Child_SA exchange."
    ::= { hIKEv2CHILDSANtwkParamsProfiles 3 }

hIKEv2CHLDNtwkParamsProfileEntry OBJECT-TYPE
    SYNTAX     HIKEv2CHLDNtwkParamsProfileEntry
    MAX-ACCESS not-accessible
    STATUS     current
    DESCRIPTION
        "(U//FOUO) A row which details one set of locally-configured network
         parameters of an IKEv2 CHILD_SA associated with a particular
         hIKEv2CHILDSAtProfTableEntry entry."
    INDEX  { hIKEv2CHLDNPPName }
    ::= { hIKEv2CHLDNtwkParamsProfileTable 1 }

HIKEv2CHLDNtwkParamsProfileEntry ::= SEQUENCE
{
   hIKEv2CHLDNPPName                SnmpAdminString,
   hIKEv2CHLDNPIKENtwkParamsRef     SnmpAdminString,
   hIKEv2CHLDNPPTFCConfigName       SnmpAdminString,
   hIKEv2CHLDNPPECNSetting          INTEGER,
   hIKEv2CHLDNPPDFBitSetting        INTEGER,
   hIKEv2CHLDNPPDSCPSetting         INTEGER,
   hIKEv2CHLDNPPDSCPValue           OCTET STRING,
   hIKEv2CHLDNPPFlowLabelSetting    INTEGER,
   hIKEv2CHLDNPPFlowLabelValue      OCTET STRING,
   hIKEv2CHLDNPPPDUNEnabled          TruthValue,
   hIKEv2CHLDNPPRowStatus           RowStatus
}

hIKEv2CHLDNPPName OBJECT-TYPE
    SYNTAX     SnmpAdminString (SIZE(1..32))
    MAX-ACCESS not-accessible
    STATUS     current
    DESCRIPTION
        "(U//FOUO) The unique administrative name identifying the set of
         locally-configured network parameters of an IKEv2 CHILD_SA associated
         with a particular hIKEv2CHLDSecAttrsProfileTable entry. This column is
         the primary index to the hIKEv2CHLDNtwkParamsProfileTable."
    ::= { hIKEv2CHLDNtwkParamsProfileEntry 1 }

hIKEv2CHLDNPIKENtwkParamsRef OBJECT-TYPE
    SYNTAX     SnmpAdminString (SIZE(1..32))
    MAX-ACCESS read-create
    STATUS     current
    DESCRIPTION
        "(U//FOUO) A reference string pointing to one entry in the
         hIKEv2IKENtwkParamsProfileTable, providing the associated, locally-
         configured network parameters tied to an IKEv2 IKE_SA.

         (U//FOUO) A valid reference string must be specified in order for
         hIKEv2CHLDSecAttrsProfRowStatus to be 'active'."
    ::= { hIKEv2CHLDNtwkParamsProfileEntry 2 }

hIKEv2CHLDNPPTFCConfigName OBJECT-TYPE
    SYNTAX     SnmpAdminString (SIZE(0..32))
    MAX-ACCESS read-create
    STATUS     current
    DESCRIPTION
        "(U//FOUO) A reference string that points to an entry in the
         hTFCConfigTable, which details the Traffic Flow Confidentiality (TFC)
         mechanisms employed by this IKEv2 CHILD_SA.  Note, if this column is
         not populated or set to a zero length empty string, then no TFC
    mechanisms will be employed by the IKEv2 CHILD_SA."
    ::= { hIKEv2CHLDNtwkParamsProfileEntry 3 }

hIKEv2CHLDNPPECNSetting OBJECT-TYPE
    SYNTAX     INTEGER { disabled(1), congestionNotification(2),
                         admissionControl(3) }
    MAX-ACCESS read-create
    STATUS     current
    DESCRIPTION
        "(U//FOUO) The setting that controls the processing mode of the Explicit
         Congestion Notification (ECN) bits, during encapsulation and
         decapsulation - the possible values are: disabled,
         congestionNotification, admissionControl.  For IPv4 headers, the ECN
         bits are Bits 1-0 (low/right) of the Type of Service (TOS) bits.  For
         IPv6 headers, the ECN bits are Bits 1-0 (low/right) of the Traffic
         Class (TC) bits.

         (U//FOUO) [disabled] If this column is set to disabled, when
         encapsulation takes place the ECN bits must be set to (10) in the CT
         header regardless of the values in the PT header of the packet being
         encapsulated.  For decapsulation, the inner headers are passed through
         unmodified.

         (U//FOUO) [congestionNotification] If this column is set to
         congestionNotification, when encapsulation takes place the ECN bits
         must be set to (10) in the CT header regardless of the values in the PT
         header of the packet being encapsulated.  For decapsulation, see the
         HAIPE IS for more details on the ECN bits processing.

         (U//FOUO) [admissionControl] If this column is set to
         admissionControl, when encapsulation takes place the ECN bits must be
         copied from PT header to the CT header.  For decapsulation, the ECN
         bits must be copied from CT header to PT header."
    DEFVAL{disabled}
    ::= { hIKEv2CHLDNtwkParamsProfileEntry 4 }

hIKEv2CHLDNPPDFBitSetting OBJECT-TYPE
    SYNTAX     INTEGER { clear(1), set(2), copy(3) }
    MAX-ACCESS read-create
    STATUS     current
    DESCRIPTION
        "(U//FOUO) The setting that controls the processing mode of the Don't
         Fragment (DF) bit in the IPv4 CT header (encapsulation) - the possible
         values are: set, clear, copy.

         (U//FOUO) [set] If this column is set to set, the IPv4 CT header DF bit
         must be set to 1 (binary).

         (U//FOUO) [clear] If this column is set to clear, the IPv4 CT header DF
         Bit must be set to 0 (binary).

         (U//FOUO) [copy] If this column is set to copy, the IPv4 PT header's DF
         Bit value is copied to the IPv4 CT header's DF Bit, during
         encapsulation."
    DEFVAL{clear}
    ::= { hIKEv2CHLDNtwkParamsProfileEntry 5 }

hIKEv2CHLDNPPDSCPSetting OBJECT-TYPE
    SYNTAX     INTEGER { set(1), acceptList(2) }
    MAX-ACCESS read-create
    STATUS     current
    DESCRIPTION
        "(U//FOUO) The setting that controls the processing mode of the
         Differentiated Service Code Points (DSCP) bits in the CT header
         (encapsulation); the possible values are: set, acceptList. For IPv4
         headers, the DSCP bits are the six most significant bits of the Type of
         Service (TOS) field.  For IPv6 headers, the DSCP bits are the six most
         significant bits of the Traffic Class (TC) field.

         (U//FOUO) [set] If this column is set to set, the CT header DSCP bits
         must be set to the value defined in the hIKEv2CHLDNPPDSCPValue column.

         (U//FOUO) [acceptList] If this column is set to acceptList, the PT
         header DSCP bits are compared against a list of values defined in the
         hIKEv2CHLDNPPDSCPValue column; if the compared DSCP bits is matched,
    they are copied over to the CT header DSCP bits.  If there is no match,
    the CT header DSCP bits are set to all 0s. "
    DEFVAL{set}
    ::= { hIKEv2CHLDNtwkParamsProfileEntry 6 }

hIKEv2CHLDNPPDSCPValue OBJECT-TYPE
    SYNTAX     OCTET STRING (SIZE(1|8))
    MAX-ACCESS read-create
    STATUS     current
    DESCRIPTION
        "(U//FOUO) Depending on the value set in the hIKEv2CHLDNPPDSCPSetting
         column (set, acceptList), this column is used in two ways. For IPv4
         headers, the DSCP bits are the six most significant bits of the Type of
         Service (TOS) field.  For IPv6 headers, the DSCP bits are the six most
         significant bits of the Traffic Class (TC) field.

         (U//FOUO) [hIKEv2CHLDNPPDSCPSetting=set] If the
         hIKEv2CHLDNPPDSCPSetting column is set to set, the CT header
         Differentiated Service Code Points (DSCP) bits must be set to the value
         defined in this column and the value in this column must be one octet
         in length in the range 0x00 to 0x3f.  The DSCP value garnered from the
         Bits 5-0 (low/right most 6-bits) of this column's value is placed in
         the CT header DSCP bits.  Note, if the hIKEv2CHLDNPPDSCPSetting
         column is set to set, an attempt to set this column to value outside
    of the range 0x00 to 0x3f should fail with an invalid value error.

         (U//FOUO) [hIKEv2CHLDNPPDSCPSetting=acceptList] If the
         hIKEv2CHLDNPPDSCPSetting column is set to acceptList, this value must
         be 8 octets in length and the value in this column will provide a list
         of acceptable DSCP values represented as a 64-bit vector.  Each bit of
         this value represents one acceptable DSCP value and acceptable matches
         are indicated with its mapped bit is set to 1 (binary).  If the
         outgoing PT packet's DSCP value matches a value represented in the
         vector, that value is placed in the CT header DSCP bits.  If none of
         the values in the vector match an outgoing PT packet's DSCP value, the
         CT header DSCP bits are set to all 0s.

         (U//FOUO)64 bit vector representation:
         DSCP value matches 64-bit Vector Map
                  0         000...000001
                  1         000...000010
                  2         000...000100
                     . . .
                     . . .
                     . . .
                 62         010000...000
                 63         100000...000"
    DEFVAL{'00'h}
    ::= { hIKEv2CHLDNtwkParamsProfileEntry 7 }

hIKEv2CHLDNPPFlowLabelSetting OBJECT-TYPE
    SYNTAX     INTEGER { set(1), copy(2) }
    MAX-ACCESS read-create
    STATUS     current
    DESCRIPTION
        "(U//FOUO) The setting that controls the processing mode of the Flow
         Label bits in the CT header (encapsulation) - the possible values are:
         set, copy. Note, this column is only relevant to Outbound IPv6 IKEv2
	 CHILD_SAs.

         (U//FOUO) [set] If this column is set to set, the CT header Flow Label
         bits must be set to the value defined in the
         hIKEv2CHLDNPPFlowLabelValue column.

         (U//FOUO) [copy] If this column is set to copy, when encapsulation
         takes place the Flow Label bits must be copied from PT header to the
         CT header."
    DEFVAL{set}
    ::= { hIKEv2CHLDNtwkParamsProfileEntry 8 }

hIKEv2CHLDNPPFlowLabelValue OBJECT-TYPE
    SYNTAX     OCTET STRING (SIZE(3))
    MAX-ACCESS read-create
    STATUS     current
    DESCRIPTION
        "(U//FOUO) The flow label value for the IKEv2 CHILD_SA. The use of this
         value is dependent on the value of the hIKEv2CHLDNPPFlowLabelSetting
         column (set, copy) in this row. Note, this column is only
         relevant to Outbound IPv6 IKEv2 CHILD_SAs.

         (U//FOUO) [hIKEv2CHLDNPPFlowLabelSetting=set] If the
         column is set to set, the CT header Flow Label bits must be set to the
         value defined in this column and the value in this column must be one
         20-bits in length in the range 0x00 - 0xfffff.  The Flow Label value
         garnered from the Bits 19-0 (low/right most 20-bits) of this column's
         value is placed in the CT header Flow Label bits.  Note, if the
         hIKEv2CHLDNPPFlowLabelSetting column is set to set, an attempt to set
         this column to value outside of the range 0x00 - 0xfffff should fail
         with an invalid value error.
	 
	 (U//FOUO) If hIKEv2CHLDNPPFlowLabelSetting is set to 'copy', this
	 column must not exist."
    ::= { hIKEv2CHLDNtwkParamsProfileEntry 9 }

hIKEv2CHLDNPPPDUNEnabled OBJECT-TYPE
    SYNTAX     TruthValue
    MAX-ACCESS read-create
    STATUS     current
    DESCRIPTION
        "(U//FOUO) The setting that determines whether or not Peer Destination
         Unreachable Notification (PDUN) messages are transmitted upon
         determination that a host is unreachable on a parented Inbound IKEv2
         CHILD_SA - the possible values are: true, false.

         (U//FOUO) Note, for IKEv2 CHILD_SAs, PDUN messages are transmitted on
         the parent IKEv2 IKE_SA established with the remote HAIPE."
    ::= { hIKEv2CHLDNtwkParamsProfileEntry 10 }

hIKEv2CHLDNPPRowStatus OBJECT-TYPE
    SYNTAX     RowStatus
    MAX-ACCESS read-create
    STATUS     current
    DESCRIPTION
        "(U//FOUO) The status of the row, by which new entries may be created,
         or old entries deleted from this table.

         (U//FOUO) If an attempt to create a new row via createAndGo does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row.

    (U//FOUO) A row cannot be set to active while
         hIKEv2CHLDNPIKENtwkParamsRef does not point to an active row in the
         respective table.

         (U//FOUO) The hIKEv2CHLDNPIKENtwkParamsRef column of an active row
         may not be changed to values that are not valid, active rows in their
         respective tables (an inconsistentValue error will be returned)."
    ::= { hIKEv2CHLDNtwkParamsProfileEntry 11 }

-- **********************************************************************
-- IKEv2 IKE SA Profile(s)
-- **********************************************************************

-- =========
-- IKEv2 IKE SA Network Parameters Profile
-- =========

hIKEv2IKENPProfTableCount OBJECT-TYPE
    SYNTAX     Unsigned32
    MAX-ACCESS read-only
    STATUS     current
    DESCRIPTION
        "(U//FOUO) The number of rows in the hIKEv2IKENtwkParamsProfileTable."
    ::= { hIKEv2IKESANtwkParamsProfiles 1 }

hIKEv2IKENPProfTableLastChanged OBJECT-TYPE
    SYNTAX     TimeStamp
    MAX-ACCESS read-only
    STATUS     current
    DESCRIPTION
        "(U//FOUO) The value of hSystemUpTime the last time any entry in the
         hIKEv2IKENtwkParamsProfileTable was modified, created, or deleted by
         either SNMP or other management method (e.g. via an HMI).

         (U//FOUO) Managers can use this object to ensure that no changes to
         configuration of this table have happened since the last time it
         examined the table.

         (U//FOUO) A value of 0 indicates that no entry has been changed since
         the agent initialized."
    ::= { hIKEv2IKESANtwkParamsProfiles 2 }

hIKEv2IKENtwkParamsProfileTable OBJECT-TYPE
    SYNTAX     SEQUENCE OF HIKEv2IKENtwkParamsProfileEntry
    MAX-ACCESS not-accessible
    STATUS     current
    DESCRIPTION
        "(U//FOUO) The table containing locally-configured network parameters
         for IKEv2 IKE_SAs. Note that these parameters are not negotiated, but
         are used in the creation of an IKEv2 IKE_SA."
    ::= { hIKEv2IKESANtwkParamsProfiles 3 }

hIKEv2IKENtwkParamsProfileEntry OBJECT-TYPE
    SYNTAX     HIKEv2IKENtwkParamsProfileEntry
    MAX-ACCESS not-accessible
    STATUS     current
    DESCRIPTION
        "(U//FOUO) A row which details one set of locally-configured network
         parameters used in the creation of an IKEv2 IKE_SA."
    INDEX  { hIKEv2IKENPPName }
    ::= { hIKEv2IKENtwkParamsProfileTable 1 }

HIKEv2IKENtwkParamsProfileEntry ::= SEQUENCE
{
   hIKEv2IKENPPName                 SnmpAdminString,
   hIKEv2IKENPPLivenessTestRate     Unsigned32,
   hIKEv2IKENPPLivenessTestLimit    Unsigned32,
   hIKEv2IKENPPRowStatus            RowStatus
}

hIKEv2IKENPPName OBJECT-TYPE
    SYNTAX     SnmpAdminString (SIZE(1..32))
    MAX-ACCESS not-accessible
    STATUS     current
    DESCRIPTION
        "(U//FOUO) The unique administrative name identifying the set of
         locally-configured network parameters used in the creation of an IKEv2
         IKE_SA. This column is the primary index to the
         hIKEv2IKENtwkParamsProfileTable."
    ::= { hIKEv2IKENtwkParamsProfileEntry 1 }

hIKEv2IKENPPLivenessTestRate OBJECT-TYPE
    SYNTAX     Unsigned32
    MAX-ACCESS read-create
    STATUS     current
    DESCRIPTION
        "(U//FOUO) The setting that determines the rate (in seconds) at which
         Liveness Test request messages are transmitted on the IKEv2 IKE_SA.  A
         value of zero (decimal) indicates the disabled Liveness Test Setting,
         meaning that Liveness Test request messages will not be transmitted."
    DEFVAL{0}
    ::= { hIKEv2IKENtwkParamsProfileEntry 2 }

hIKEv2IKENPPLivenessTestLimit OBJECT-TYPE
    SYNTAX     Unsigned32
    MAX-ACCESS read-create
    STATUS     current
    DESCRIPTION
        "(U//FOUO) Setting that determines the number of successive missed
         Liveness Test response messages that will trigger the HAIPE to mark the
         created IKE_SA and all of its created, parented Outbound CHILD_SAs as
         UNREACHABLE.  A Liveness Test response message or any inbound traffic
         received on the created IKE_SA or any created and parented Inbound
         CHILD_SA established with the remote HAIPE resets the internal Liveness
         Test successive missed counter to its initial state.  Note, this column
         must only exist when hIKEv2IKENPPLivenessTestRate is set to a non-zero
         value (decimal)."
    ::= { hIKEv2IKENtwkParamsProfileEntry 3 }

hIKEv2IKENPPRowStatus OBJECT-TYPE
    SYNTAX     RowStatus
    MAX-ACCESS read-create
    STATUS     current
    DESCRIPTION
        "U//FOUO) The status of the row, by which new entries may be created, or
         old entries deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) An active row may not be changed to an inconsistent state. If
         such an attempt is made, an inconsistentValue error will be returned.
         In other words, any new values must be valid values for an active row."
    ::= { hIKEv2IKENtwkParamsProfileEntry 4 }

-- ================
-- TFC Config Table
-- ================

hTFCConfigTableCount OBJECT-TYPE
    SYNTAX     Unsigned32
    MAX-ACCESS read-only
    STATUS     current
    DESCRIPTION
        "(U//FOUO) The number of rows in the hTFCConfigTable."
    ::= { hTFCConfig 1 }

hTFCConfigTableLastChanged OBJECT-TYPE
    SYNTAX     TimeStamp
    MAX-ACCESS read-only
    STATUS     current
    DESCRIPTION
        "(U//FOUO) The value of hSystemUpTime the last time any entry in the
         hTFCConfigTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hTFCConfig 2 }

hTFCConfigTable OBJECT-TYPE
    SYNTAX     SEQUENCE OF HTFCConfigTableEntry
    MAX-ACCESS not-accessible
    STATUS     current
    DESCRIPTION
        "(U//FOUO) The table containing a list of TFC configurations. Entries in
         the hIKEv1NtwkParamsProfileTable, hIKEv2CHLDNtwkParamsProfileTable,
         hManualSADTable, hIKEv1SADTable, and hIKEv2CHILDSADTable reference entries
         in this table to indicate the desired TFC configuration for the
         associated Security Association(s).

         (U//FOUO) If referencing table entries attempt to reference an entry in
         this table which does not exist, then no TFC processing will be
         performed for those SAs."
    ::= { hTFCConfig 3 }

hTFCConfigTableEntry OBJECT-TYPE
    SYNTAX     HTFCConfigTableEntry
    MAX-ACCESS not-accessible
    STATUS     current
    DESCRIPTION
        "(U//FOUO) A row describing a particular TFC configuration."
    INDEX  { hTFCConfigName }
    ::= { hTFCConfigTable 1 }

HTFCConfigTableEntry ::= SEQUENCE
{
   hTFCConfigName                  SnmpAdminString,
   hTFCConfigTransmissionRate      Unsigned32,
   hTFCConfigPacketSizeType        INTEGER,
   hTFCConfigPacketSize            Unsigned32,
   hTFCConfigPacketSizeList        OCTET STRING,
   hTFCConfigRowStatus             RowStatus
}

hTFCConfigName OBJECT-TYPE
    SYNTAX     SnmpAdminString (SIZE(1..32))
    MAX-ACCESS not-accessible
    STATUS     current
    DESCRIPTION
        "(U//FOUO) The administrative name for this TFC configuration - the
         hTFCConfigName column is the primary index for this table."
    ::= { hTFCConfigTableEntry 1 }

hTFCConfigTransmissionRate OBJECT-TYPE
    SYNTAX     Unsigned32
    UNITS      "packets/second"
    MAX-ACCESS read-create
    STATUS     current
    DESCRIPTION
        "(U//FOUO) The fixed rate, in packets per second, of transmission to be
         used for the SA. If no Mandatory Transmission mechanisms are used, this
         column must not exist.

         (U//FOUO) Note, the Mandatory Transmission packet size is determined
         by the hTFCConfigPacketSizeType column value - for more details on
         how Mandatory Transmission packet size is determined, see the
         hTFCConfigPacketSizeType column description."
    ::= { hTFCConfigTableEntry 2 }

hTFCConfigPacketSizeType OBJECT-TYPE
    SYNTAX     INTEGER { noPadding(1), fixedSize(2), randomSize(3),
                         fixedListSize(4) }
    MAX-ACCESS read-create
    STATUS     current
    DESCRIPTION
        "(U//FOUO) The type of TFC packet length control mechanism the SAs in
         the hManualSADTable, hIKEv1SADTable, and hIKEv2CHILDSADTable will use.

         (U//FOUO) [noPadding] If this column is set to 'noPadding', it
         indicates that no TFC packet length control mechanism is used on
         packets encapsulated (including Mandatory Transmission packets) by SAs
         referencing this entry.  The values in hTFCConfigPacketSize and
         hTFCConfigPacketSizeList will thus be ignored.

         (U//FOUO) [fixedSize] If this column is set to 'fixedSize', it
         indicates that all packets encapsulated (including Mandatory
         Transmission packets) by SAs referencing this entry must use a fixed
         ESP packet size, with the desired size specified in
         hTFCConfigPacketSize.  The value in hTFCConfigPacketSizeList will
         thus be ignored.

         (U//FOUO) [randomSize] If this column is set to 'randomSize', it
         indicates that all packets encapsulated (including Mandatory
         Transmission packets) by SAs referencing this entry must use randomly
         variable ESP packet size. The values in hTFCConfigPacketSize and
         hTFCConfigPacketSizeList will thus be ignored.

         (U//FOUO) [fixedListSize] If this column is set to 'fixedListSize', it
         indicates that all packets encapsulated by SAs (including Mandatory
         Transmission packets) referencing this entry must restrict ESP packet
         sizes to those specified in hTFCConfigPacketSizeList. The value in
         hTFCConfigPacketSize will thus be ignored.

         (U//FOUO) Implementations not supporting a particular packet length
         control mechanism should return a wrongValue error if a manager
         attempts to set this object."
    ::= { hTFCConfigTableEntry 3 }

hTFCConfigPacketSize OBJECT-TYPE
    SYNTAX     Unsigned32
    MAX-ACCESS read-create
    STATUS     current
    DESCRIPTION
        "(U//FOUO) The fixed ESP packet size - this object is only used if
         hTFCConfigPacketSizeType is set to 'fixedSize'.  If the
         hTFCConfigPacketSizeType column is set to 'fixedSize', it
         indicates that all packets encapsulated (including Mandatory
         Transmission packets) by SAs referencing this entry must use a fixed
         ESP packet size, with the desired size specified in this column.

         (U//FOUO) The value specified by this object is the number of octets
         from the SPI through the authentication/integrity data inclusive. i.e.,
         the specified fixed packet size applies only to the ESP data, and not
         the outer CT IP header.

         (U//FOUO) Implementations will certainly not support the setting of all
         possible values to this object, and a wrongValue exception should be
         returned when an attempt to set this object to an unsupported value
         occurs."
    ::= { hTFCConfigTableEntry 4 }

hTFCConfigPacketSizeList OBJECT-TYPE
    SYNTAX     OCTET STRING (SIZE(0..256))
    MAX-ACCESS read-create
    STATUS     current
    DESCRIPTION
        "(U//FOUO) The ordered list of ESP packet sizes - this object is only
         used if hTFCConfigPacketSizeType is set to 'fixedListSize'.  If the
         hTFCConfigPacketSizeType column is set to 'fixedListSize', it indicates
         that all packets encapsulated by SAs (including Mandatory Transmission
         packets) referencing this entry must restrict ESP packet sizes to those
         specified in this column.

         (U//FOUO) The OCTET STRING will be multiple 2-octet SHORTs in network
         byte order (high octet first).  They will be sorted by the manager
         uploading the list to the object and implementations MAY choose to
         reject configuration of lists that are not properly sorted.

         (U//FOUO) ESP packet sizes specified by this object correspond to the
         number of octets from the SPI through the authentication/integrity data
         inclusive. i.e., the specified packet size applies only to the ESP
         data, and not the outer CT IP header.

         (U//FOUO) Implementations will certainly not support the setting of all
         possible values to this object, and a wrongValue exception should be
         returned when an attempt to set this object to an unsupported value
         occurs."
    ::= { hTFCConfigTableEntry 5 }

hTFCConfigRowStatus OBJECT-TYPE
    SYNTAX     RowStatus
    MAX-ACCESS read-create
    STATUS     current
    DESCRIPTION
        "(U//FOUO) The status of this row, by which new entries may be created,
         or old entries deleted from this table.

         (U//FOUO) If any column is set to an unsupported value (during row
         creation or any other time), a wrongValue error will be returned for
         that object."
    ::= { hTFCConfigTableEntry 6 }

-- **********************************************************************
-- SAD (Established) Traffic Selectors
-- **********************************************************************

-- =========
-- Established Local Traffic Selector Table
-- =========

hEstLocalTSTableCount OBJECT-TYPE
    SYNTAX     Unsigned32
    MAX-ACCESS read-only
    STATUS     current
    DESCRIPTION
        "(U//FOUO) The number of rows in the hEstLocalTSTable."
    ::= { hEstablishedLocalTS 1 }

hEstLocalTSTableLastChanged OBJECT-TYPE
    SYNTAX     TimeStamp
    MAX-ACCESS read-only
    STATUS     current
    DESCRIPTION
        "(U//FOUO) The value of hSystemUpTime the last time any entry in the
         hEstLocalTSTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hEstablishedLocalTS 2 }

hEstLocalTSTable OBJECT-TYPE
    SYNTAX     SEQUENCE OF HEstLocalTSTableEntry
    MAX-ACCESS not-accessible
    STATUS     current
    DESCRIPTION
        "(U//FOUO) The table containing a list of local traffic selectors that
         IP packets are checked against when they arrive on the HAIPE's
         interface. IP packets are also checked against selectors in the
         hEstRemoteTSTable. Note the two indices to this table: (1)
         hEstLocalTSName and (2) hEstLocalTSIndex. This table allows multiple
         traffic selectors to be grouped under the same hEstLocalTSName with
         each set of traffic selectors distinguished by hEstLocalTSIndex.

         (U//FOUO) An implementation is not required to support multiple traffic
         selectors. Single traffic selectors may be supported with one entry
         identified by a unique hEstLocalTSName and any hEstLocalTSIndex value.
         If single traffic selectors are only desired, the implementation should
         prevent configuration of multiple entries with the same
         hEstLocalTSName.

         (U//FOUO) A complete selector (Local and Remote) is constructed by
         using both this table and the hEstRemoteTSTable. The hEstRemoteTSTable
         must contain at least one selector of the same name (i.e. there must be
         at least one row in the hEstRemoteTSTable with a value in
         hEstRemoteTSName equal to hEstLocalTSName). Configured multiple traffic
         selectors abide by RFC 4306's 'mix-and-match' semantics. Hence, any
         combination of local and remote PT address and port ranges with the
         same hEstLocalTSName and hEstRemoteTSName are handled under the same
         rule.

         (U//FOUO) As an example, suppose two hEstLocalTSTable entries exist
         with the following:(1) local PT address and port range of A, (2) local
         PT address and port range of B, and two hEstRemoteTSTable entries exist
         with the following: (1) remote PT address and port range of C, (2)
         remote PT address and port range of D. This means that traffic is
         allowed to flow between every possible combination (A-C, A-D, B-C,
         B-D). If every possible combination of traffic selectors violates the
         security policy (for example, traffic cannot flow between B and C),
         single entries with unique hEstRemoteTSName (in turn, multiple security
         associations) would need to be configured (in this example, the traffic
         selector pairs would consist of two groups: A-C, A-D; and B-D).

         (U//FOUO) Note, for IKEv2, the address ranges and ports under one value
         in the hEstLocalTSName column constitute the TSi payload, while the
         remote PT address ranges and port under the same value in the
         hEstRemoteTSName column (hEstRemoteTSTable) constitute the TSr payload.

         (U//FOUO) A row in this table defines a set of traffic selectors to
         which the IP packet is checked against."
    ::= { hEstablishedLocalTS 3 }

hEstLocalTSTableEntry OBJECT-TYPE
    SYNTAX     HEstLocalTSTableEntry
    MAX-ACCESS not-accessible
    STATUS     current
    DESCRIPTION
        "(U//FOUO) An entry in the hEstLocalTSTable."
    INDEX  { hEstLocalTSName, hEstLocalTSIndex }
    ::= { hEstLocalTSTable 1 }

HEstLocalTSTableEntry ::= SEQUENCE
{
   hEstLocalTSName                 SnmpAdminString,
   hEstLocalTSIndex                Unsigned32,
   hEstLocalTSPTAddrType           IPAddressType,
   hEstLocalTSPTAddrBegin          IPAddress,
   hEstLocalTSPTAddrEnd            IPAddress,
   hEstLocalTSProtocol             Unsigned32,
   hEstLocalTSPortBegin            PortNumber,
   hEstLocalTSPortEnd              PortNumber,
   hEstLocalTSRowStatus            RowStatus
}

hEstLocalTSName OBJECT-TYPE
    SYNTAX     SnmpAdminString (SIZE(1..32))
    MAX-ACCESS not-accessible
    STATUS     current
    DESCRIPTION
        "(U//FOUO) The administrative name defining the set of local traffic
         selectors that an IP packet may match. Multiple traffic selectors may
         use the same administrative name implying a group. It is the combination
         of hEstLocalTSName and hEstLocalTSIndex that uniquely identifies each
         row or set of traffic selectors."
    ::= { hEstLocalTSTableEntry 1 }

hEstLocalTSIndex OBJECT-TYPE
    SYNTAX     Unsigned32
    MAX-ACCESS not-accessible
    STATUS     current
    DESCRIPTION
        "(U//FOUO) A unique numeric index for rows, or sets of traffic
         selectors, with the same hEstLocalTSName. This value, in combination
         with hEstLocalTSName, uniquely identifies each row, or set of traffic
         selectors."
    ::= { hEstLocalTSTableEntry 2 }

hEstLocalTSPTAddrType OBJECT-TYPE
    SYNTAX     IPAddressType
    MAX-ACCESS read-create
    STATUS     current
    DESCRIPTION
        "(U//FOUO) The Internet Protocol Version, IPv4 or IPv6, of the local PT
         address range. Specifically, the value of this property determines the
         size and format of the hEstLocalTSPTAddrBegin and
         hEstLocalTSPTAddrEnd."
    ::= { hEstLocalTSTableEntry 3 }

hEstLocalTSPTAddrBegin OBJECT-TYPE
    SYNTAX     IPAddress
    MAX-ACCESS read-create
    STATUS     current
    DESCRIPTION
        "(U//FOUO) The starting address of a local address range that an IP
         packet must match in order for the row, or set of traffic selectors, to
         be considered a match.

    (U//FOUO) The address type value set (IPv4 address value,
         IPv6 address value) in this column should be consistent with the
         hEstLocalTSPTAddrType column.

         (U//FOUO) Since established selectors are bidirectional, the value in
         this column will be compared against the packet's source address for
         outgoing data traffic and the packet's desination address for incoming
         data traffic.

         (U//FOUO) To have the local PT address range set to the ANY value (i.e.
         packet will not be checked against this selector), this object must be
         set to 0.0.0.0 for IPv4 or to ::0 for IPv6, while hEstLocalTSPTAddrEnd
         is set to 255.255.255.255 for IPv4 or to
         FFFF:FFFF:FFFF:FFFF:FFFF:FFFF:FFFF:FFFF for IPv6.

         (U//FOUO) Note, for all outgoing multicast SAs, the local PT address
         range should represent either a specific host range or the ANY value
         (0.0.0.0-255.255.255.255 for IPv4, or ::0 to
         FFFF:FFFF:FFFF:FFFF:FFFF:FFFF:FFFF:FFFF for IPv6). For all incoming
         multicast SAs, the local PT address range should represent one or
         possibly multiple PT multicast addresses to which the local HAIPE
         listens on. "
    ::= { hEstLocalTSTableEntry 4 }

hEstLocalTSPTAddrEnd OBJECT-TYPE
    SYNTAX     IPAddress
    MAX-ACCESS read-create
    STATUS     current
    DESCRIPTION
        "(U//FOUO) The ending address of a local address range that an IP packet
         must match in order for the row, or set of traffic selectors, to be
         considered a match. If this column is set to the same value as the
         hEstLocalTSPTAddrBegin, the local PT address range indicates an exact
         single address match.

    (U//FOUO) The address type value set (IPv4 address value,
         IPv6 address value) in this column should be consistent with the
         hEstLocalTSPTAddrType column.

         (U//FOUO) Since established selectors are bidirectional, the value in
         this column will be compared against the packet's source address for
         outgoing data traffic and the packet's desination address for incoming
         data traffic.

         (U//FOUO) To set this selector to a single host, this column's value
         should be the same as hEstLocalTSPTAddrBegin.

         (U//FOUO) To have the local PT address range set to the ANY value (i.e.
         packet will not be checked against this selector), this object must be
         set to 255.255.255.255 for IPv4 or to
         FFFF:FFFF:FFFF:FFFF:FFFF:FFFF:FFFF:FFFF for IPv6, while
         hEstLocalTSPTAddrBegin is set to 0.0.0.0 for IPv4 or ::0 for IPv6.

         (U//FOUO) Note, for all outgoing multicast SAs, the local PT address
         range should represent either a specific host range or the ANY value
         (0.0.0.0-255.255.255.255 for IPv4, or ::0 to
         FFFF:FFFF:FFFF:FFFF:FFFF:FFFF:FFFF:FFFF for IPv6). For all incoming
         multicast SAs, the local PT address range should represent one or
         possibly multiple PT multicast addresses to which the local HAIPE
         listens on. "
    ::= { hEstLocalTSTableEntry 5 }

hEstLocalTSProtocol OBJECT-TYPE
    SYNTAX     Unsigned32 (0..255)
    MAX-ACCESS read-create
    STATUS     current
    DESCRIPTION
        "(U//FOUO) The protocol selector value for this set of traffic
         selectors. If this column is set to 0, the packet's protocol value will
         not be checked."
    ::= { hEstLocalTSTableEntry 6 }

hEstLocalTSPortBegin OBJECT-TYPE
    SYNTAX     PortNumber
    MAX-ACCESS read-create
    STATUS     current
    DESCRIPTION
        "(U//FOUO) The starting port of a local port range that an IP packet
         must match in order for the row, or set of traffic selectors, to be
         considered a match.

         (U//FOUO) Since established selectors are bidirectional, the value in
         this column will be compared against the packet's source port for
         outgoing data traffic and the packet's destination port for incoming
         data traffic.

         (U//FOUO) To have the local port range set to the ANY value, this
         object must be set to 0, while hEstLocalTSPortEnd is set to 65535.

         (U//FOUO) To have the local port range set to the OPAQUE value, this
         object must be set to 65535, while hEstLocalTSPortEnd is set to 0.

         (U//FOUO) For SAs intended for discovery, the local port range should
         include port 3623."
    ::= { hEstLocalTSTableEntry 7 }

hEstLocalTSPortEnd OBJECT-TYPE
    SYNTAX     PortNumber
    MAX-ACCESS read-create
    STATUS     current
    DESCRIPTION
        "(U//FOUO) The ending port of a local port range that an IP packet must
         match in order for the row, or set of traffic selectors, to be
         considered a match. If this column is set to the same value as the
         hEstLocalTSPortBegin, the local port range indicates an exact single
         port match.

         (U//FOUO) Since established selectors are bidirectional, the value in
         this column will be compared against the packet's source port for
         outgoing data traffic and the packet's destination port for incoming
         data traffic.

         (U//FOUO) To set this selector to a single port, this column's value
         should be the same as hEstLocalTSPortBegin.

         (U//FOUO) To have the local port range set to the ANY value, this
         object must be set to 65535, while hEstLocalTSPortBegin is set to 0.

         (U//FOUO) To have the local port range set to the OPAQUE value, this
         object must be set to 0, while hEstLocalTSPortBegin is set to 65535.

         (U//FOUO) For SAs intended for discovery, the local port range should
         include port 3623."
    ::= { hEstLocalTSTableEntry 8 }

hEstLocalTSRowStatus OBJECT-TYPE
    SYNTAX     RowStatus
    MAX-ACCESS read-create
    STATUS     current
    DESCRIPTION
        "(U//FOUO) The status of the row, by which new entries may be created,
         or existing entries modified or deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) A traffic selector which is referenced by any
         hIKEv2CHILDSAEstTrafficSelName cannot be modified. Any attempt to
         modify any part of such a selector (including this RowStatus column)
         will return a readOnly error. Similarly, any attempts to add another
         selector with the same hEstLocalTSName as a selector referenced by any
         hIKEv2CHILDSAEstTrafficSelName will return an inconsistentValue error.

         (U//FOUO) Row creation within this table is only valid for Manual
         Security Associations. An active row may not be changed to an
         inconsistent state. If such an attempt is made, an inconsistentValue
         error will be returned. In other words, any new values must be valid
         values for an active row.

         (U//FOUO) If an active row is deleted, and it is the only row with a
         particular hEstLocalTSName, the Manual Security Association referencing
         this selector (if any) will be changed to notInService.

         (U//FOUO) At a minimum, implementations must support createAndGo and
         destroy management functions. Support for createAndWait, active,
         notInService, and notReady management functions is optional."
    ::= { hEstLocalTSTableEntry 9 }

-- =========
-- Established Remote Traffic Selector Table
-- =========

hEstRemoteTSTableCount OBJECT-TYPE
    SYNTAX     Unsigned32
    MAX-ACCESS read-only
    STATUS     current
    DESCRIPTION
        "(U//FOUO) The number of rows in the hEstRemoteTSTable."
    ::= { hEstablishedRemoteTS 1 }

hEstRemoteTSTableLastChanged OBJECT-TYPE
    SYNTAX     TimeStamp
    MAX-ACCESS read-only
    STATUS     current
    DESCRIPTION
        "(U//FOUO) The value of hSystemUpTime the last time any entry in the
         hEstRemoteTSTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hEstablishedRemoteTS 2 }

hEstRemoteTSTable OBJECT-TYPE
    SYNTAX     SEQUENCE OF HEstRemoteTSTableEntry
    MAX-ACCESS not-accessible
    STATUS     current
    DESCRIPTION
        "(U//FOUO) The table containing a list of remote traffic selectors that
         IP packets are checked against when they arrive on the HAIPE's
         interface. IP packets are also checked against selectors in the
         hEstLocalTSTable. Note the two indices to this table: (1)
         hEstRemoteTSName and (2) hEstRemoteTSIndex. This table allows multiple
         traffic selectors to be grouped under the same hEstRemoteTSName with
         each set of traffic selectors distinguished by hEstRemoteTSIndex.

         (U//FOUO) An implementation is not required to support multiple traffic
         selectors. Single traffic selectors may be supported with one entry
         identified by a unique hEstRemoteTSName and any hEstRemoteTSIndex
         value. If single traffic selectors are only desired, the implementation
         should prevent configuration of multiple entries with the same
         hEstRemoteTSName.

         (U//FOUO) A complete selector (Local and Remote) is constructed by
         using both this table and the hEstLocalTSTable. The hEstLocalTSTable
         must contain at least one selector of the same name (i.e. there must be
         at least one row in the hEstLocalTSTable with a value in
         hEstLocalTSName equal to hEstRemoteTSName). Configured multiple traffic
         selectors abide by RFC 4306's 'mix-and-match' semantics. Hence, any
         combination of local and remote PT address and port ranges with the
         same hEstLocalTSName and hEstRemoteTSName are handled under the same
         rule.

         (U//FOUO) As an example, suppose two hEstLocalTSTable entries exist
         with the following:(1) local PT address and port range of A, (2) local
         PT address and port range of B, and two hEstRemoteTSTable entries exist
         with the following: (1) remote PT address and port range of C, (2)
         remote PT address and port range of D. This means that traffic is
         allowed to flow between every possible combination (A-C, A-D, B-C,
         B-D). If every possible combination of traffic selectors violates the
         security policy (for example, traffic cannot flow between B and C),
         single entries with unique hEstRemoteTSName (in turn, multiple security
         associations) would need to be configured (in this example, the traffic
         selector pairs would consist of two groups: A-C, A-D; and B-D).

         (U//FOUO) Note, for IKEv2, the address ranges and ports under one value
         in the hEstRemoteTSName column constitute the TSr payload, while the
         local PT address ranges and port under the same value in the
         hEstLocalTSName column (hEstLocalTSTable) constitute the TSi payload.

         (U//FOUO) A row in this table defines a set of traffic selectors to
         which the IP packet is checked against."
    ::= { hEstablishedRemoteTS 3 }

hEstRemoteTSTableEntry OBJECT-TYPE
    SYNTAX     HEstRemoteTSTableEntry
    MAX-ACCESS not-accessible
    STATUS     current
    DESCRIPTION
        "(U//FOUO) An entry in the hEstRemoteTSTable."
    INDEX  { hEstRemoteTSName, hEstRemoteTSIndex }
    ::= { hEstRemoteTSTable 1 }

HEstRemoteTSTableEntry ::= SEQUENCE
{
   hEstRemoteTSName                SnmpAdminString,
   hEstRemoteTSIndex               Unsigned32,
   hEstRemoteTSPTAddrType          IPAddressType,
   hEstRemoteTSPTAddrBegin         IPAddress,
   hEstRemoteTSPTAddrEnd           IPAddress,
   hEstRemoteTSProtocol            Unsigned32,
   hEstRemoteTSPortBegin           PortNumber,
   hEstRemoteTSPortEnd             PortNumber,
   hEstRemoteTSRowStatus           RowStatus
}

hEstRemoteTSName OBJECT-TYPE
    SYNTAX     SnmpAdminString (SIZE(1..32))
    MAX-ACCESS not-accessible
    STATUS     current
    DESCRIPTION
        "(U//FOUO) The administrative name defining the set of remote traffic
         selectors that an IP packet may match. Multiple traffic selectors may
         use the same administrative name implying a group. It is the combination
         of hEstRemoteTSName and hEstRemoteTSIndex that uniquely identifies
         each row or set of traffic selectors."
    ::= { hEstRemoteTSTableEntry 1 }

hEstRemoteTSIndex OBJECT-TYPE
    SYNTAX     Unsigned32
    MAX-ACCESS not-accessible
    STATUS     current
    DESCRIPTION
        "(U//FOUO) A unique numeric index for rows, or sets of traffic
         selectors, with the same hEstRemoteTSName. This value, in combination
         with hEstRemoteTSName, uniquely identifies each row, or set of traffic
         selectors."
    ::= { hEstRemoteTSTableEntry 2 }

hEstRemoteTSPTAddrType OBJECT-TYPE
    SYNTAX     IPAddressType
    MAX-ACCESS read-create
    STATUS     current
    DESCRIPTION
        "(U//FOUO) The Internet Protocol Version, IPv4 or IPv6, of the remote PT
         address range. Specifically, the value of this property determines the
         size and format of the hEstRemoteTSPTAddrBegin and
         hEstRemoteTSPTAddrEnd."
    ::= { hEstRemoteTSTableEntry 3 }

hEstRemoteTSPTAddrBegin OBJECT-TYPE
    SYNTAX     IPAddress
    MAX-ACCESS read-create
    STATUS     current
    DESCRIPTION
        "(U//FOUO) The starting address of a remote address range that an IP
         packet must match in order for the row, or set of traffic selectors, to
         be considered a match.

    (U//FOUO) The address type value set (IPv4 address value,
         IPv6 address value) in this column should be consistent with the
         hEstRemoteTSPTAddrType column.

         (U//FOUO) Since established selectors are bidirectional, the value in
         this column will be compared against the packet's destination address
         for outgoing data traffic and the packet's source address for incoming
         data traffic.

         (U//FOUO) To have the remote PT address range set to the ANY value
         (i.e. packet will not be checked against this selector), this object
         must be set to 0.0.0.0 for IPv4 or to ::0 for IPv6, while
         hEstRemoteTSPTAddrEnd is set to 255.255.255.255 for IPv4 or to
         FFFF:FFFF:FFFF:FFFF:FFFF:FFFF:FFFF:FFFF for IPv6.

         (U//FOUO) For outbound multicast SAs, the remote PT address range
         represents one or possibly multiple destination PT multicast addresses.
         For inbound multicast SAs, the remote PT address range represents
         either a specific host range or the ANY value 
         (0.0.0.0-255.255.255.255 for IPv4, or ::0 to
         FFFF:FFFF:FFFF:FFFF:FFFF:FFFF:FFFF:FFFF for IPv6)."
    ::= { hEstRemoteTSTableEntry 4 }

hEstRemoteTSPTAddrEnd OBJECT-TYPE
    SYNTAX     IPAddress
    MAX-ACCESS read-create
    STATUS     current
    DESCRIPTION
        "(U//FOUO) The ending address of a remote address range that an IP
         packet must match in order for the row, or set of traffic selectors, to
         be considered a match. If this column is set to the same value as the
         hEstRemoteTSPTAddrBegin, the local PT address range indicates an exact
         single address match.

    (U//FOUO) The address type value set (IPv4 address value,
         IPv6 address value) in this column should be consistent with the
         hEstRemoteTSPTAddrType column.

         (U//FOUO) Since established selectors are bidirectional, the value in
         this column will be compared against the packet's destination address
         for outgoing data traffic and the packet's source address for incoming
         data traffic.

         (U//FOUO) To set this selector to a single host, this column's value
         should be the same as hEstRemoteTSPTAddrBegin.

         (U//FOUO) To have the remote PT address range set to the ANY value
         (i.e. packet will not be checked against this selector), this object
         must be set to 255.255.255.255 for IPv4 or
         FFFF:FFFF:FFFF:FFFF:FFFF:FFFF:FFFF:FFFF for IPv6, while
         hEstRemoteTSPTAddrBegin is set to 0.0.0.0 for IPv4 or ::0 for IPv6.

         (U//FOUO) For outbound multicast SAs, the remote PT address range
         represents one or possibly multiple destination PT multicast addresses.
         For inbound multicast SAs, the remote PT address range represents
         either a specific host range or the ANY value 
         (0.0.0.0-255.255.255.255 for IPv4, or ::0 to
         FFFF:FFFF:FFFF:FFFF:FFFF:FFFF:FFFF:FFFF for IPv6)."
    ::= { hEstRemoteTSTableEntry 5 }

hEstRemoteTSProtocol OBJECT-TYPE
    SYNTAX     Unsigned32 (0..255)
    MAX-ACCESS read-create
    STATUS     current
    DESCRIPTION
        "(U//FOUO) The protocol selector value for this set of traffic
         selectors. If this column is set to 0, the packet's protocol value will
         not be checked."
    ::= { hEstRemoteTSTableEntry 6 }

hEstRemoteTSPortBegin OBJECT-TYPE
    SYNTAX     PortNumber
    MAX-ACCESS read-create
    STATUS     current
    DESCRIPTION
        "(U//FOUO) The starting port of a remote port range that an IP packet
         must match in order for the row, or set of traffic selectors, to be
         considered a match.

         (U//FOUO) Since established selectors are bidirectional, the value in
         this column will be compared against the packet's destination port for
         outgoing data traffic and the packet's source port for incoming data
         traffic.

         (U//FOUO) To have the remote port range set to the ANY value, this
         object must be set to 0, while hEstRemoteTSPortEnd is set to 65535.

         (U//FOUO) To have the remote port range set to the OPAQUE value, this
         object must be set to 65535, while hEstRemoteTSPortEnd is set to 0.

         (U//FOUO) For SAs intended for discovery, the remote port range should
         include port 3623."
    ::= { hEstRemoteTSTableEntry 7 }

hEstRemoteTSPortEnd OBJECT-TYPE
    SYNTAX     PortNumber
    MAX-ACCESS read-create
    STATUS     current
    DESCRIPTION
        "(U//FOUO) The ending port of a remote port range that an IP packet must
         match in order for the row, or set of traffic selectors, to be
         considered a match. If this column is set to the same value as the
         hEstRemoteTSPortBegin, the remote port range indicates an exact single
         port match.

         (U//FOUO) Since established selectors are bidirectional, the value in
         this column will be compared against the packet's destination port for
         outgoing data traffic and the packet's source port for incoming data
         traffic.

         (U//FOUO) To set this selector to a single port, this column's value
         should be the same as hEstRemoteTSPortBegin.

         (U//FOUO) To have the remote port range set to the ANY value, this
         object must be set to 65535, while hEstRemoteTSPortBegin is set to 0.

         (U//FOUO) To have the remote port range set to the OPAQUE value, this
         object must be set to 0, while hEstRemoteTSPortBegin is set to 65535.

         (U//FOUO) For SAs intended for discovery, the remote port range should
         include port 3623."
    ::= { hEstRemoteTSTableEntry 8 }

hEstRemoteTSRowStatus OBJECT-TYPE
    SYNTAX     RowStatus
    MAX-ACCESS read-create
    STATUS     current
    DESCRIPTION
        "(U//FOUO) The status of the row, by which new entries may be created,
         or existing entries modified or deleted from this table.

         (U//FOUO) If an attempt to create a new row via 'createAndGo' does
         not include a value for any column for the new row, an inconsistentName
         error will be returned for this object.

         (U//FOUO) If any column is set to an invalid or unsupported value
         (during row creation or any other time), a wrongValue error will be
         returned for that object.

         (U//FOUO) A traffic selector which is referenced by any
         hIKEv2CHILDSAEstTrafficSelName cannot be modified. Any attempt to
         modify any part of such a selector (including this RowStatus column)
         will return a readOnly error. Similarly, any attempts to add another
         selector with the same hEstRemoteTSName as a selector referenced by any
         hIKEv2CHILDSAEstTrafficSelName will return an inconsistentValue error.

         (U//FOUO) Row creation within this table is only valid for Manual
         Security Associations. An active row may not be changed to an
         inconsistent state. If such an attempt is made, an inconsistentValue
         error will be returned. In other words, any new values must be valid
         values for an active row.

         (U//FOUO) If an active row is deleted, and it is the only row with a
         particular hEstRemoteTSName, the Manual Security Association
         referencing this selector (if any) will be changed to notInService."
    ::= { hEstRemoteTSTableEntry 9 }

-- **********************************************************************
-- Manual SAD
-- **********************************************************************

-- =========
-- Manual SAD Table
-- =========

hManualSADTableCount OBJECT-TYPE
    SYNTAX     Unsigned32
    MAX-ACCESS read-only
    STATUS     current
    DESCRIPTION
        "(U//FOUO) The number of rows in the hManualSADTable."
    ::= { hManualSAD 1 }

hManualSADTableLastChanged OBJECT-TYPE
    SYNTAX     TimeStamp
    MAX-ACCESS read-only
    STATUS     current
    DESCRIPTION
        "(U//FOUO) The value of hSystemUpTime the last time any entry in the
         hManualSADTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hManualSAD 2 }

hManualSADTable OBJECT-TYPE
    SYNTAX     SEQUENCE OF HManualSADTableEntry
    MAX-ACCESS not-accessible
    STATUS     current
    DESCRIPTION
        "(U//FOUO) The table for configuring and viewing Manual SAs relevant
         to a HAIPE device.  Note, columns may apply to only Inbound Manual
         SAs, Outbound Manual SAs, or both; each column's description describes
         the Inbound/Outbound context applicability."
    ::= { hManualSAD 3 }

hManualSADTableEntry OBJECT-TYPE
    SYNTAX     HManualSADTableEntry
    MAX-ACCESS not-accessible
    STATUS     current
    DESCRIPTION
        "(U//FOUO) A row describing the information about the relevant Manual
         SAs on this HAIPE.  Each row signifies either an Outbound Manual SA
         or an Inbound Manual SA; the value in the hManualSADirection column
         determines this directionality."
    INDEX  { hManualSAIndex }
    ::= { hManualSADTable 1 }

HManualSADTableEntry ::= SEQUENCE
{
   hManualSAIndex                  Unsigned32,
   hManualSAKeyChainName           SnmpAdminString,
   hManualSAEstTrafficSelectorName SnmpAdminString,
   hManualSAAddressType            IPAddressType,
   hManualSALocalCTAddress         IPAddress,
   hManualSARemoteCTAddress        IPAddress,
   hManualSALocalPTAddress         IPAddress,
   hManualSARemotePTAddress        IPAddress,
   hManualSASPIChainReference      SnmpAdminString,
   hManualSADirection              INTEGER,
   hManualSAStartTime              DateAndTime,
   hManualSATransformSuite         HaipeManualSATransformSuites,
   hManualSADSCPClassifier         OCTET STRING,
   hManualSAECNSetting             INTEGER,
   hManualSADFBitSetting           INTEGER,
   hManualSACTDSCPSetting          INTEGER,
   hManualSACTDSCPValue            OCTET STRING,
   hManualSAFlowLabelSetting       INTEGER,
   hManualSACTFlowLabelValue       OCTET STRING,
   hManualSACtlPlaneSignalEnabled  TruthValue,
   hManualSAPDUNEnabled            TruthValue,
   hManualSAPHRDRate               Unsigned32,
   hManualSAPHRDLimit              Unsigned32,
   hManualSAReachabilityStatus     TruthValue,
   hManualSATFCConfigName          SnmpAdminString,
   hManualSAEstROHCParamsIndex     Unsigned32,
   hManualSARowStatus              RowStatus,
   hManualSAEstBMParamsIndex       SnmpAdminString
}

hManualSAIndex OBJECT-TYPE
    SYNTAX     Unsigned32
    MAX-ACCESS not-accessible
    STATUS     current
    DESCRIPTION
        "(U//FOUO) An unique numeric index that identifies this Manual SA; the
         hManualSAIndex column is the primary index column for this table."
    ::= { hManualSADTableEntry 1 }

hManualSAKeyChainName OBJECT-TYPE
    SYNTAX     SnmpAdminString (SIZE(1..32))
    MAX-ACCESS read-create
    STATUS     current
    DESCRIPTION
        "(U//FOUO) A reference string that points to a group of PPKs/APPKs in
         the hManSAKeyChainTable, which provides the key chain material
         associated with this Manual SA.  Note, a row's hManualSARowStatus
         column can only be set to Active if a valid value has been set for the
         hManSAKeyChainName column; the current effective PPK/APPK in the
         PPK/APPK chain must have a Row Status of Active."
    ::= { hManualSADTableEntry 2 }

hManualSAEstTrafficSelectorName OBJECT-TYPE
    SYNTAX     SnmpAdminString (SIZE(1..32))
    MAX-ACCESS read-create
    STATUS     current
    DESCRIPTION
        "(U//FOUO) A reference string that points to one or more entries in the
         hEstLocalTSTable and hEstRemoteTSTable.  These referenced rows define
         the allowable set of traffic selectors (one or more can be associated
         in a Mix and Match semantic) allowed on this Manual SA.  Note, a row's
         Row Status column can only be set to Active if a valid value has been
         set for the hManualSAEstTrafficSelectorName column; there must be at
         least one pair of rows (local and remote) pointed to by this column
         that both have a Row Status of Active.

         (U//FOUO) Note, if the Manual SA is operating in Transport Mode, this
         column must reference one entry in the hEstLocalTSTable and one entry
         in the hEstRemoteTSTable; these entries contains the specific host pair
         address selectors.

         (U//FOUO) Note, for Inbound/Outbound Multicast SAs, in conjunction with
         the hManualSALocalCTAddress column and the hManualSARemoteCTAddress
         column, the hEstLocalTSTable and the hEstRemoteTSTable are used to
         store the CT Multicast to PT Multicast address mappings."
    ::= { hManualSADTableEntry 3 }

hManualSAAddressType OBJECT-TYPE
    SYNTAX     IPAddressType
    MAX-ACCESS read-create
    STATUS     current
    DESCRIPTION
        "(U//FOUO) The local and remote HAIPE address types (CT and PT)
         associated with this Manual SA; the possible values are: IPv4 and
         IPv6.  The value in this column directly influences the address type
         values in the hManualSALocalCTAddress, hManualSARemoteCTAddress,
         hManualSALocalPTAddress, and the hManualSARemotePTAddress columns."
    ::= { hManualSADTableEntry 4 }

hManualSALocalCTAddress OBJECT-TYPE
    SYNTAX     IPAddress
    MAX-ACCESS read-create
    STATUS     current
    DESCRIPTION
        "(U//FOUO) The local HAIPE CT address associated with this Manual SA.
         The address type value set (IPv4 address value, IPv6 address value) in
         this column should be consistent with the hManualSAAddressType column.

         (U//FOUO) For Inbound Multicast SAs (User Traffic Multicast, Legacy
         Discovery Multicast, Generic Discovery Client Multicast), this column
         contains the CT Multicast address associated with this Multicast SA.

         (U//FOUO) For Outbound Multicast SAs (User Traffic Multicast, Legacy
         Discovery Multicast, Generic Discovery Client Multicast), this column
         contains the local HAIPE CT address associated with this Multicast
         SA.  In respect to Outbound Multicast SAs, this column, in
         conjunction with the hEstLocalTSTable, is used to store the PT
         Multicast to CT Multicast address mapping."

    ::= { hManualSADTableEntry 5 }

hManualSARemoteCTAddress OBJECT-TYPE
    SYNTAX     IPAddress
    MAX-ACCESS read-create
    STATUS     current
    DESCRIPTION
        "(U//FOUO) The remote HAIPE CT address associated with this Manual SA.
         The address type value set (IPv4 address value, IPv6  address value) in
         this column should be consistent with the hManualSAAddressType column.

         (U//FOUO) For Inbound Multicast SAs (User Traffic Multicast, Legacy
         Discovery Multicast, Generic Discovery Client Multicast), this column
         must not exist.

         (U//FOUO) For Outbound Multicast SAs (User Traffic Multicast, Legacy
         Discovery Multicast, Generic Discovery Client Multicast), this column
         contains the CT Multicast address associated with this Multicast SA.

         (U//FOUO) In respect to Outbound Multicast SAs, this column, in
         conjunction with the hEstRemoteTSTable, is used to store the PT
         Multicast to CT Multicast address mapping."
    ::= { hManualSADTableEntry 6 }

hManualSALocalPTAddress OBJECT-TYPE
    SYNTAX     IPAddress
    MAX-ACCESS read-create
    STATUS     current
    DESCRIPTION
        "(U//FOUO) The local HAIPE PT address associated with this Manual SA.
         The address type value set (IPv4 address value, IPv6 address value) in
         this column should be consistent with the hManualSAAddressType column.

         (U//FOUO) For Inbound and Outbound Multicast SAs (User Traffic
         Multicast, Legacy Discovery Multicast, Generic Discovery Client
         Multicast), this column contains the local HAIPE PT address associated
         with this Multicast SA."
    ::= { hManualSADTableEntry 7 }

hManualSARemotePTAddress OBJECT-TYPE
    SYNTAX     IPAddress
    MAX-ACCESS read-create
    STATUS     current
    DESCRIPTION
        "(U//FOUO) The remote HAIPE PT Address associated with this Manual SA.
         The address type value set (IPv4 address value, IPv6 address value) in
         this column should be consistent with the hManualSAAddressType column.

         (U//FOUO) For Inbound and Outbound Multicast SAs (User Traffic
         Multicast, Legacy Discovery Multicast, Generic Discovery Client
         Multicast), this column must not exist."
    ::= { hManualSADTableEntry 8 }

hManualSASPIChainReference OBJECT-TYPE
    SYNTAX     SnmpAdminString (SIZE(1..32))
    MAX-ACCESS read-create
    STATUS     current
    DESCRIPTION
        "(U//FOUO) A reference string that points to a SPI chain group in the
         hManualSASPIChainTable; this referenced SPI chain group provides this
         Manual SA a group of SPIs that are cycled through upon SPI changeover.
         In conjunction with the value in the hManualSAStartTime column and the
         current Real Time Clock value, a single SPI in the SPI chain group is
         utilized as the current SPI in context.

         (U//FOUO) Note, a row's hManualSARowStatus column can only be set to
         Active if a valid value has been set for the
         hManualSASPIChainReference column; the SPI chain group pointed to by
         this column must have at least one row that has a Row Status of
         Active."
    ::= { hManualSADTableEntry 9 }

hManualSADirection OBJECT-TYPE
    SYNTAX     INTEGER {inbound(1), outbound(2)}
    MAX-ACCESS read-create
    STATUS     current
    DESCRIPTION
        "(U//FOUO) The traffic flow direction for this Manual SA; the possible
         values are: inbound and outbound."
    ::= { hManualSADTableEntry 10 }

hManualSAStartTime OBJECT-TYPE
    SYNTAX     DateAndTime
    MAX-ACCESS read-create
    STATUS     current
    DESCRIPTION
        "(U//FOUO) The local date and time when this Manual SA was or will be
         established. Note, the value in this column may be set to a date and
         time prior to the effective date of the key material for this Manual
         SA. Note, if this column value is not manually configured with a date
         and time then the value will be automatically populated with the
         current Real Time Clock value in respect to when the hManualSARowStatus
         column is first set to Active.

         (U//FOUO) The hManualSAStartTime defines the alpha date for this
         Manual SA.  In conjunction with the hManualSASPIChainReference column
         and the current Real Time Clock value, the hManualSAStartTime is
         utilized to determine the current SPI in context for this Manual SA.

         (U//FOUO) For example, if the hManualSAStartTime has an equivalent
         value of September 8, 2009, 2:00 AM, on September 8, 2009 at 2:00 AM
         the current SPI for the Manual SA would be the first SPI in the SPI
         Chain Group.  On September 15, 2009, the current SPI for the Manual
         SA would be the eighth SPI in the SPI chain group; note, if the SPI
         chain group has less than eight valid SPIs, a cycling to the first
         SPI in the chain group occurs."
    ::= { hManualSADTableEntry 11 }

hManualSATransformSuite OBJECT-TYPE
    SYNTAX     HaipeManualSATransformSuites
    MAX-ACCESS read-create
    STATUS     current
    DESCRIPTION
        "(U//FOUO) A set of cryptographic attributes respective to the
         established Manual SA."
    ::= { hManualSADTableEntry 12 }

hManualSADSCPClassifier OBJECT-TYPE
    SYNTAX     OCTET STRING (SIZE(8))
    MAX-ACCESS read-create
    STATUS     current
    DESCRIPTION
        "(U//FOUO) The DSCP classifiers for this Manual SA; the default
         value is 0xFFFFFFFFFFFFFFFF (hexadecimal).  Note, this column must only
         exist for Outbound Manual SAs.  For IPv4 headers, the DSCP bits are
         the six most significant bits of the Type of Service (TOS) field.  For
         IPv6 headers, the DSCP bits are the six most significant bits of the
         Traffic Class (TC) field.

         (U//FOUO) The DSCP classifier provides the mechanism to determine
         whether outbound packets are allowed to traverse the Manual SA as
         based on the PT DSCP value.  Note, as defined by RFC 4301, classifiers
         are not traffic selectors since they only apply to outbound packets.

         (U//FOUO) This value must be 8 octets in length and the value in this
         column will provide a list of DSCP classifier values represented as a
         64-bit vector.  Each bit of this value represents a DSCP classifier
         value and set classifiers are indicated with its mapped bit is set to
         1 (binary).

         (U//FOUO)64 bit vector representation:
         DSCP value matches 64-bit Vector Map
                  0         000...000001
                  1         000...000010
                  2         000...000100
                     . . .
                     . . .
                     . . .
                 62         010000...000
                 63         100000...000"
    DEFVAL{'FFFFFFFFFFFFFFFF'h}
    ::= { hManualSADTableEntry 13 }

hManualSAECNSetting OBJECT-TYPE
    SYNTAX     INTEGER {disabled(1), congestionNotification(2), admissionControl(3)}
    MAX-ACCESS read-create
    STATUS     current
    DESCRIPTION
        "(U//FOUO) The setting that controls the processing mode of the
         Explicit Congestion Notification (ECN) bits, during encapsulation and
         decapsulation; the possible values are: disabled,
         congestionNotification, admissionControl; the default value is
         disabled.  For IPv4 headers, the ECN bits are Bits 1-0 (low/right) of
         the Type of Service (TOS) bits.  For IPv6 headers, the ECN bits are
         Bits 1-0 (low/right) of the Traffic Class (TC) bits.

         (U//FOUO) [disabled] If this column is set to disabled, when
         encapsulation takes place the ECN bits must be set to (10) in the CT
         header regardless of the values in the PT header of the packet being
         encapsulated.  For decapsulation, the inner headers are passed
         through unmodified.

         (U//FOUO) [congestionNotification] If this column is set to
         congestionNotification, when encapsulation takes place the ECN bits
         must be set to (10) in the CT header regardless of the values in the PT
         header of the packet being encapsulated.  For decapsulation, see the
         HAIPE IS for more details on the ECN bits processing.

         (U//FOUO) [admissionControl] If this column is set to admissionControl,
         when encapsulation takes place the ECN bits must be copied from PT header
         to the CT header.  For decapsulation, the ECN bits must be copied from CT
         header to PT header."
    DEFVAL {disabled}
    ::= { hManualSADTableEntry 14 }

hManualSADFBitSetting OBJECT-TYPE
    SYNTAX     INTEGER {set(1), clear(2), copy(3)}
    MAX-ACCESS read-create
    STATUS     current
    DESCRIPTION
        "(U//FOUO) The setting that controls the processing mode of the Don't
         Fragment (DF) bit in the IPv4 CT header (encapsulation); the possible
         values are: set, clear, copy; the default value is clear.  Note, this
         column must only exist for Outbound IPv4 Manual SAs.

         (U//FOUO) [set] If this column is set to set, the IPv4 CT header DF bit
         must be set to 1 (binary).

         (U//FOUO) [clear] If this column is set to clear, the IPv4 CT header DF
         Bit must be set to 0 (binary).

         (U//FOUO) [copy] If this column is set to copy, the IPv4 PT header's DF
         Bit value is copied to the IPv4 CT header's DF Bit, during
         encapsulation."
    DEFVAL {clear}
    ::= { hManualSADTableEntry 15 }

hManualSACTDSCPSetting OBJECT-TYPE
    SYNTAX     INTEGER {set(1), acceptList(2)}
    MAX-ACCESS read-create
    STATUS     current
    DESCRIPTION
        "(U//FOUO) The setting that controls the processing mode of the
         Differentiated Service Code Points (DSCP) bits in the CT header
         (encapsulation); the possible values are: set, acceptList; the default
         value is set.  Note, this column must only exist for Outbound Manual
         SAs.  For IPv4 headers, the DSCP bits are the six most significant bits
         of the Type of Service (TOS) field.  For IPv6 headers, the DSCP bits
         are the six most significant bits of the Traffic Class (TC) field.

         (U//FOUO) [set] If this column is set to set, the CT header DSCP bits
         must be set to the value defined in the hManualSACTDSCPValue column.

         (U//FOUO) [acceptList] If this column is set to acceptList, the PT
         header DSCP bits are compared against a list of values defined in the
         hManualSACTDSCPValue column; if the compared DSCP bits is matched,
         they are copied over to the CT header DSCP bits.  If there is no match,
         the CT header DSCP bits are set to all 0s."
    DEFVAL {set}
    ::= { hManualSADTableEntry 16 }

hManualSACTDSCPValue OBJECT-TYPE
    SYNTAX     OCTET STRING (SIZE (1|8))
    MAX-ACCESS read-create
    STATUS     current
    DESCRIPTION
        "(U//FOUO) Depending on the value set in the hManualSACTDSCPSetting
         column (set, acceptList), this column is used in two ways; the
         default value is 0 (decimal).  Note, this column must only exist for
         Outbound Manual SAs.  For IPv4 headers, the DSCP bits are the six
         most significant bits of the Type of Service (TOS) field.  For IPv6
         headers, the DSCP bits are the six most significant bits of the
         Traffic Class (TC) field.

         (U//FOUO) [hManualSACTDSCPSetting=set] If the hManualSACTDSCPSetting
         column is set to set, the CT header Differentiated Service Code Points
         (DSCP) bits must be set to the value defined in this column and the
         value in this column must be one octet in length in the range 0x00 to
         0x3f.  The DSCP value garnered from the Bits 5-0 (low/right most
         6-bits) of this column's value is placed in the CT header DSCP bits.
         Note, if the hManualSACTDSCPSetting column is set to set, an attempt
         to set this column to value outside of the range 0x00 to 0x3f should
         fail with an invalid value error.

         (U//FOUO) [hManualSACTDSCPSetting=acceptList] If the
         hManualSACTDSCPSetting column is set to acceptList, this value must be
         8 octets in length and the value in this column will provide a list of
         acceptable DSCP values represented as a 64-bit vector.  Each bit of
         this value represents one acceptable DSCP value and acceptable matches
         are indicated with its mapped bit is set to 1 (binary).  If the
         outgoing PT packet's DSCP value matches a value represented in the
         vector, that value is placed in the CT header DSCP bits.  If none of
         the values in the vector match an outgoing PT packet's DSCP value, the
         CT header DSCP bits are set to all 0s.

         (U//FOUO)64 bit vector representation:
         DSCP value matches 64-bit Vector Map
                  0         000...000001
                  1         000...000010
                  2         000...000100
                     . . .
                     . . .
                     . . .
                 62         010000...000
                 63         100000...000"
    DEFVAL {'00'h}
    ::= { hManualSADTableEntry 17 }

hManualSAFlowLabelSetting OBJECT-TYPE
    SYNTAX     INTEGER {set(1), copy(2)}
    MAX-ACCESS read-create
    STATUS     current
    DESCRIPTION
        "(U//FOUO) The setting that controls the processing mode of the Flow
         Label bits in the CT header (encapsulation); the possible values are:
         set, copy; the default value is set.  Note, this column must only
         exist for Outbound IPv6 Manual SAs.

         (U//FOUO) [set] If this column is set to set, the CT header Flow Label
         bits must be set to the value defined in the hManualSACTFlowLabelValue
         column.

         (U//FOUO) [copy] If this column is set to copy, when encapsulation
         takes place the Flow Label bits must be copied from PT header to the
         CT header."
    DEFVAL {set}
    ::= { hManualSADTableEntry 18 }

hManualSACTFlowLabelValue  OBJECT-TYPE
    SYNTAX     OCTET STRING (SIZE(3))
    MAX-ACCESS read-create
    STATUS     current
    DESCRIPTION
        "(U//FOUO) The flow label value for this Manual SA. The use of this
         value is dependent on the value of the hManualSAFlowLabelSetting
         column (set, copy) in this row.  Note, this column must only exist for
         Outbound IPv6 Manual SAs.

         (U//FOUO) [hManualSAFlowLabelSetting=set] If the  column is set to set,
         the CT header Flow Label bits must be set to the value defined in this
         column and the value in this column must be one 20-bits in length in
         the range between 0x00 to 0xfffff.  The Flow Label value garnered from
         the Bits 19-0 (low/right most 20-bits) of this column's value is placed
         in the CT header Flow Label bits.  Note, if the
         hManualSAFlowLabelSetting column is set to set, an attempt to set this
         column to value outside of the range 0x00 to 0xfffff should fail with an
         invalid value error.
	 
	 (U//FOUO) If hManualSAFlowLabelSetting is set to 'copy', this column
	 must not exist."
    ::= { hManualSADTableEntry 19 }

hManualSACtlPlaneSignalEnabled OBJECT-TYPE
    SYNTAX     TruthValue
    MAX-ACCESS read-create
    STATUS     current
    DESCRIPTION
        "(U//FOUO) The setting that determines whether or not Control Plane
         Signaling bits are set in transmitted Control Plane Messages (PDUN and
         PHRD) on Manual Transport Mode SAs; the possible values are: true,
         false.  Note, this column must only exist for Outbound Transport Mode
         Manual SAs.  Note, this column must not exist for Multicast SAs."
    ::= { hManualSADTableEntry 20 }

hManualSAPDUNEnabled  OBJECT-TYPE
    SYNTAX     TruthValue
    MAX-ACCESS read-create
    STATUS     current
    DESCRIPTION
        "(U//FOUO) The setting that determines whether or not Peer Destination
         Unreachable Notification (PDUN) messages are transmitted upon
         determination that a host is unreachable on an Inbound Manual SA; the
         possible values are: true, false.  Note, this column must only exist
         for Inbound Manual SAs.  Note, this column must not exist for Multicast
         SAs.

         (U//FOUO) Note, for Manual SAs, PDUN messages are transmitted on any
         Outbound Manual SA established with the remote HAIPE."
    ::= { hManualSADTableEntry 21 }

hManualSAPHRDRate OBJECT-TYPE
    SYNTAX     Unsigned32
    MAX-ACCESS read-create
    STATUS     current
    DESCRIPTION
        "(U//FOUO) The setting that determines the rate (in seconds) at which
         Peer HAIPE Reachability Detection (PHRD) messages are transmitted on
         this Manual SA; the default value is 0 (decimal).  A value of zero
         (decimal) indicates the disabled PHRD Setting, meaning that PHRD
         messages will not be transmitted.  Note, this column must only exist
         for Outbound Manual SAs.  Note, this column must not exist for
         Multicast SAs."
    DEFVAL {0}
    ::= { hManualSADTableEntry 22 }

hManualSAPHRDLimit OBJECT-TYPE
    SYNTAX     Unsigned32
    MAX-ACCESS read-create
    STATUS     current
    DESCRIPTION
        "(U//FOUO) Setting that determines the number of successive missed Peer
         HAIPE Reachability Detection (PHRD) responses that will trigger the
         HAIPE to mark this Manual SA as UNREACHABLE.  A PHRD response or any
         inbound traffic received on an Inbound Manual SA established with the
         remote HAIPE resets the internal PHRD successive missed counter to its
         initial state.  Note, this column must only exist for Outbound Manual
         SAs and when the hManualSAPHRDRate column is set to a non-zero value 
	 (decimal).  Note, this column must not exist for Multicast SAs."
    ::= { hManualSADTableEntry 23 }

hManualSAReachabilityStatus OBJECT-TYPE
    SYNTAX     TruthValue
    MAX-ACCESS read-only
    STATUS     current
    DESCRIPTION
        "(U//FOUO) The Reachability Status of this Manual SA; the possible
         values are: true, false.   The value in this column is determined by
         the hManualSAPHRDRate column and the hManualSAPHRDLimit column; a
         Manual SA is determined UNREACHABLE if the hManualSAPHRDLimit threshold
         is reached for the number of successive missed PHRD responses.  Note,
         this column must only exist for Outbound Manual SAs.  Note, this column
         must not exist for Multicast SAs.

         (U//FOUO) [true] If this column is set to true, this Manual SA is
         REACHABLE.

         (U//FOUO) [false] If this column is set to false, this Manual SA is
         UNREACHABLE."
    ::= { hManualSADTableEntry 24 }

hManualSATFCConfigName OBJECT-TYPE
    SYNTAX     SnmpAdminString (SIZE(0..32))
    MAX-ACCESS read-create
    STATUS     current
    DESCRIPTION
        "(U//FOUO) A reference string that points to an entry in the
         hTFCConfigTable, which details the Traffic Flow Confidentiality (TFC)
         mechanisms employed by this Manual SA.  Note, if this column is not
         populated or set to a zero length empty string, then no TFC mechanisms
         will be employed by the Manual SA."
    ::= { hManualSADTableEntry 25 }

hManualSAEstROHCParamsIndex OBJECT-TYPE
    SYNTAX     Unsigned32
    MAX-ACCESS read-create
    STATUS     current
    DESCRIPTION
        "(U//FOUO) An unique numeric index that references a row in the
         hEstROHCParamTable; this referenced row stores the RoHC parameters
         associated with this Manual SA.  Note, if this column exists, a
         row's Row Status column can only be set to Active if a valid value
         has been set for the hManualSAEstROHCParamsIndex column; the row
         pointed to by this column must have a Row Status of Active.

         (U//FOUO) This column must only exist if the Header Compression
         Extension is supported."
    ::= { hManualSADTableEntry 26 }
    
hManualSAEstBMParamsIndex OBJECT-TYPE
    SYNTAX     SnmpAdminString (SIZE(1..32))
    MAX-ACCESS read-create
    STATUS     current
    DESCRIPTION
        "(U//FOUO) A unique administrative name that references a row in the
         hEstBMParamTable. This referenced row stores the established BM 
	 parameters associated with this Manual SA. If BM is disabled, this column
	 must not be populated or it must be set to a zero length empty string.
	 
	 (U//FOUO) If this column exists and is populated with any value other 
	 than a zero length empty string then: (1) hManualSARowStatus can only 
	 be set to 'active' if a valid value has been set for this column and 
	 (2) the row pointed to by this column must have an hEstBMParamRowStatus 
	 value of 'active'.

         (U//FOUO) This column must only exist if the Bandwidth Management
         Extension is supported."
    ::= { hManualSADTableEntry 27 }     
    
hManualSARowStatus OBJECT-TYPE
    SYNTAX     RowStatus
    MAX-ACCESS read-create
    STATUS     current
    DESCRIPTION
        "(U//FOUO) The status of the row, by which new entries may be created,
         or old entries deleted from this table.

         (U//FOUO) Entries created within this table may not become active
         unless all read-create columns in this table have valid values, as
         detailed by each individual column's description.

         (U//FOUO) At a minimum, implementations must support createAndGo and
         destroy management functions. Support for createAndWait, active,
         notInService, and notReady management functions is optional."
    ::= { hManualSADTableEntry 28 }  

-- =========
-- Manual SPI Chain Table
-- =========

hManualSASPIChainTableCount OBJECT-TYPE
    SYNTAX     Unsigned32
    MAX-ACCESS read-only
    STATUS     current
    DESCRIPTION
        "(U//FOUO) The number of rows in the hManualSASPIChainTable."
    ::= { hManualSAD 4 }

hManualSASPIChainTableLastChanged OBJECT-TYPE
    SYNTAX     TimeStamp
    MAX-ACCESS read-only
    STATUS     current
    DESCRIPTION
        "(U//FOUO) The value of hSystemUpTime the last time any entry in the
         hManualSASPIChainTable was modified, created, or deleted by either SNMP
         or other management method (e.g. via an HMI).

         (U//FOUO) Managers can use this object to ensure that no changes to
         configuration of this table have happened since the last time it
         examined the table.

         (U//FOUO) A value of 0 indicates that no entry has been changed since
         the agent initialized."
    ::= { hManualSAD 5 }

hManualSASPIChainTable OBJECT-TYPE
    SYNTAX     SEQUENCE OF HManualSASPIChainTableEntry
    MAX-ACCESS not-accessible
    STATUS     current
    DESCRIPTION
        "(U//FOUO) The table for configuring Security Parameter Indices (SPIs)
         for Manual SAs.  The hManualSASPIChainTable contains SPI chain groups,
         as ordered by the hManualSASPIChainOrder column.  Each SPI chain group
         is associated to one or more Manual SAs, thus providing an ordered set
         SPIs that a Manual SA cycles through upon SPI changeover.

         (U//FOUO) The hManualSASPIChainReference column in the hManualSADTable
         stores a reference string that points to a specific SPI chain group in
         the hManualSASPIChainTable.  The hManualSASPIChainReference column
         provides an associated SPI chain group to a Manual SA and in
         conjunction with the hManualSAStartTime provides the current SPI value
         to use for the Manual SA.  Upon SPI changeover, the next SPI in the
         SPI chain group is utilized; the process of stepping through the entire
         SPI chain group is continues through the life of the Manual SA.  If
         the end of a SPI chain group is reached, the process resets and the
         next SPI to be utilized is the first SPI in the SPI chain group as
         defined by the hManualSASPIChainName column and hManualSASPIChainOrder
         column."
    ::= { hManualSAD 6 }

hManualSASPIChainTableEntry OBJECT-TYPE
    SYNTAX     HManualSASPIChainTableEntry
    MAX-ACCESS not-accessible
    STATUS     current
    DESCRIPTION
        "(U//FOUO) A row describing the Security Parameter Index (SPI)
         information in the context of a SPI chain group."
    INDEX  { hManualSASPIChainName, hManualSASPIChainOrder }
    ::= { hManualSASPIChainTable 1 }

HManualSASPIChainTableEntry ::= SEQUENCE
{
   hManualSASPIChainName           SnmpAdminString,
   hManualSASPIChainOrder          Unsigned32,
   hManualSASPI                    Unsigned32,
   hManualSASPIChainRowStatus      RowStatus
}

hManualSASPIChainName OBJECT-TYPE
    SYNTAX     SnmpAdminString (SIZE(1..32))
    MAX-ACCESS not-accessible
    STATUS     current
    DESCRIPTION
        "(U//FOUO) The unique administrative name identifying a SPI chain group.
         It is the combination of the hManualSASPIChainName column and the
         hManualSASPIChainOrder that uniquely identifies each row in this table.

         (U//FOUO) The hManualSASPIChainReference column in the hManualSADTable
         stores a reference string that points to a specific SPI chain group in
         the hManualSASPIChainTable.  The hManualSASPIChainReference column
         provides an associated SPI chain group to a Manual SA and in
         conjunction with the hManualSAStartTime provides the current SPI value
         to use for the Manual SA.  Upon SPI changeover, the next SPI in the
         SPI chain group is utilized; the process of stepping through the entire
         SPI chain group is continues through the life of the Manual SA.  If the
         end of a SPI chain group is reached, the process resets and the next
         SPI to be utilized is the first SPI in the SPI chain group as defined
         by the hManualSASPIChainName column and hManualSASPIChainOrder column.

         (U//FOUO) Note, hManualSASPIChainOrder defines the order within the SPI
         chain group."
    ::= { hManualSASPIChainTableEntry 1 }

hManualSASPIChainOrder OBJECT-TYPE
    SYNTAX     Unsigned32
    MAX-ACCESS not-accessible
    STATUS     current
    DESCRIPTION
        "(U//FOUO) The unique numeric index that defines the chain ordering
         within a SPI chain group.  It is the combination of the
         hManualSASPIChainName column and the hManualSASPIChainOrder that
         uniquely identifies each row in this table.  Upon SPI changeover, the
         the next SPI to be utilized would be the next SPI in the SPI chain
         group as ordered by the value in this column.  Note, the first SPI to
         use for a Manual SA is defined by the Manual SA's alpha date, which is
         defined by the value in the hManualSADTable's hManualSAStartTime
         column.

         (U//FOUO) Note, if the end of a SPI chain group is reached, the next
         SPI to be utilized is the first SPI in the SPI chain group as
         defined by the hManualSASPIChainName column and hManualSASPIChainOrder
         column."
    ::= { hManualSASPIChainTableEntry 2 }

hManualSASPI OBJECT-TYPE
    SYNTAX     Unsigned32 (256..4294967295)
    MAX-ACCESS read-create
    STATUS     current
    DESCRIPTION
        "(U//FOUO) The Security Parameter Index (SPI) associated with the Manual
         SAs (one or more hManualSADTable rows).  Note, the hManualSASPI column
         can not be set to any value in the range 0-255 (decimal).  Note, for
         Legacy Discovery Multicast SAs, the last byte of the SPI must be set to
         0xFF; this value is used to determine which Outbound Multicast SA to
         send Legacy PROBE messages."
    ::= { hManualSASPIChainTableEntry 3 }

hManualSASPIChainRowStatus OBJECT-TYPE
    SYNTAX     RowStatus
    MAX-ACCESS read-create
    STATUS     current
    DESCRIPTION
        "(U//FOUO) The status of the row, by which new entries may be created,
         or old entries deleted from this table.

         (U//FOUO) Entries created within this table may not become active
         unless all read-create columns in this table have valid values, as
         detailed by each individual column's description.

         (U//FOUO) At a minimum, implementations must support createAndGo and
         destroy management functions. Support for createAndWait, active,
         notInService, and notReady management functions is optional."
    ::= { hManualSASPIChainTableEntry 4 }

-- **********************************************************************
-- IKEv1 SAD
-- **********************************************************************

-- =========
-- IKEv1 SAD Table
-- =========

hIKEv1SADTableCount OBJECT-TYPE
    SYNTAX     Unsigned32
    MAX-ACCESS read-only
    STATUS     current
    DESCRIPTION
        "(U//FOUO) The number of rows in the hIKEv1SADTable."
    ::= { hIKEv1SAD 1 }

hIKEv1SADTableLastChanged OBJECT-TYPE
    SYNTAX     TimeStamp
    MAX-ACCESS read-only
    STATUS     current
    DESCRIPTION
        "(U//FOUO) The value of hSystemUpTime the last time any entry in the
         hIKEv1SADTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hIKEv1SAD 2 }

hIKEv1SADTable OBJECT-TYPE
    SYNTAX     SEQUENCE OF HIKEv1SADTableEntry
    MAX-ACCESS not-accessible
    STATUS     current
    DESCRIPTION
        "(U//FOUO) The table for configuring and viewing IKEv1 SAs relevant to
         a HAIPE device.  Note, columns may apply to only Inbound IKEv1 SAs,
         Outbound IKEv1 SAs, or both; each column's description describes the
         Inbound/Outbound context applicability."
    ::= { hIKEv1SAD 3 }

hIKEv1SADTableEntry OBJECT-TYPE
    SYNTAX     HIKEv1SADTableEntry
    MAX-ACCESS not-accessible
    STATUS     current
    DESCRIPTION
        "(U//FOUO) A row describing the information about the relevant,
         established IKEv1 SAs on this HAIPE.  Each row signifies either an
         Outbound IKEv1 SA or an Inbound IKEv1 SA; the value in the
         hIKEv1SADirection column determines this directionality."
    INDEX  { hIKEv1SAIndex }
    ::= { hIKEv1SADTable 1 }

HIKEv1SADTableEntry ::= SEQUENCE
{
   hIKEv1SAIndex                   Unsigned32,
   hIKEv1SAEstTrafficSelectorName  SnmpAdminString,
   hIKEv1SAAddressType             IPAddressType,
   hIKEv1SALocalCTAddress          IPAddress,
   hIKEv1SARemoteCTAddress         IPAddress,
   hIKEv1SALocalPTAddress          IPAddress,
   hIKEv1SARemotePTAddress         IPAddress,
   hIKEv1SARemoteNATAddress        IPAddress,
   hIKEv1SARemoteNATDestinationPort PortNumber,
   hIKEv1SASPI                     Unsigned32,
   hIKEv1SADirection               INTEGER,
   hIKEv1SATransformSuite          HaipeIKEv1SATransformSuites,
   hIKEv1SADSCPClassifiers         OCTET STRING,
   hIKEv1SAECNSetting              INTEGER,
   hIKEv1SADFBitSetting            INTEGER,
   hIKEv1SACTDSCPSetting           INTEGER,
   hIKEv1SACTDSCPValue             OCTET STRING,
   hIKEv1SAFlowLabelSetting        INTEGER,
   hIKEv1SACTFlowLabelValue        OCTET STRING,
   hIKEv1SAPDUNEnabled             TruthValue,
   hIKEv1SAPHRDRate                Unsigned32,
   hIKEv1SAPHRDLimit               Unsigned32,
   hIKEv1SAReachabilityStatus      TruthValue,
   hIKEv1SATFCConfigName           SnmpAdminString,
   hIKEv1SARowStatus               RowStatus
}

hIKEv1SAIndex OBJECT-TYPE
    SYNTAX     Unsigned32
    MAX-ACCESS not-accessible
    STATUS     current
    DESCRIPTION
        "(U//FOUO) An unique numeric index that identifies this IKEv1 SA; the
         hIKEv1SAIndex column is the primary index column for this table.  Note,
         this column is populated internally and can not be read or configured."
    ::= { hIKEv1SADTableEntry 1 }

hIKEv1SAEstTrafficSelectorName OBJECT-TYPE
    SYNTAX     SnmpAdminString (SIZE(1..32))
    MAX-ACCESS read-only
    STATUS     current
    DESCRIPTION
        "(U//FOUO) A reference string that points to one entry in the
         hEstLocalTSTable and one entry in the hEstRemoteTSTable.  These
         referenced rows define the allowable set of traffic selectors (one or
         more can be associated in a Mix and Match semantic) allowed on this
         IKEv1 SA.  If the IKEv1 SA is operating in Tunnel Mode, the local and
         remote traffic selectors (address, ports, protocol) are populated
         with *.

         (U//FOUO) Note, if the IKEv1 SA is operating in Transport Mode, this
         column must reference one entry in the hEstLocalTSTable and one entry
         in the hEstRemoteTSTable; these entries contains the specific host pair
         address selectors."
    ::= { hIKEv1SADTableEntry 2 }

hIKEv1SAAddressType OBJECT-TYPE
    SYNTAX     IPAddressType
    MAX-ACCESS read-only
    STATUS     current
    DESCRIPTION
        "(U//FOUO) The local and remote HAIPE address types (CT and PT)
         associated with this IKEv1 SA; the possible values are: IPv4 and IPv6.
         The value in this column directly influences the address type values in
         the hIKEv1SALocalCTAddress, hIKEv1SARemoteCTAddress,
         hIKEv1SALocalPTAddress, hIKEv1SARemotePTAddress and the
         hIKEv1SARemoteNATAddress (if applicable) columns."
    ::= { hIKEv1SADTableEntry 3 }

hIKEv1SALocalCTAddress OBJECT-TYPE
    SYNTAX     IPAddress
    MAX-ACCESS read-only
    STATUS     current
    DESCRIPTION
        "(U//FOUO) The local HAIPE CT address associated with this IKEv1 SA.
         The address type value set (IPv4 address value, IPv6 address value) in
         this column should be consistent with the hIKEv1SAAddressType column."
    ::= { hIKEv1SADTableEntry 4 }

hIKEv1SARemoteCTAddress OBJECT-TYPE
    SYNTAX     IPAddress
    MAX-ACCESS read-only
    STATUS     current
    DESCRIPTION
        "(U//FOUO) The remote HAIPE CT address associated with this IKEv1 SA.
         The address type value set (IPv4 address value, IPv6  address value) in
         this column should be consistent with the hIKEv1SAAddressType column."
    ::= { hIKEv1SADTableEntry 5 }

hIKEv1SALocalPTAddress  OBJECT-TYPE
    SYNTAX     IPAddress
    MAX-ACCESS read-only
    STATUS     current
    DESCRIPTION
        "(U//FOUO) The local HAIPE PT address associated with this IKEv1 SA.
         The address type value set (IPv4 address value, IPv6 address value) in
         this column should be consistent with the hIKEv1SAAddressType column."
    ::= { hIKEv1SADTableEntry 6 }

hIKEv1SARemotePTAddress OBJECT-TYPE
    SYNTAX     IPAddress
    MAX-ACCESS read-only
    STATUS     current
    DESCRIPTION
        "(U//FOUO) The remote HAIPE PT Address associated with this IKEv1 SA.
         The address type value set (IPv4 address value, IPv6 address value) in
         this column should be consistent with the hIKEv1SAAddressType
         column."
    ::= { hIKEv1SADTableEntry 7 }

hIKEv1SARemoteNATAddress OBJECT-TYPE
    SYNTAX     IPAddress
    MAX-ACCESS read-only
    STATUS     current
    DESCRIPTION
        "(U//FOUO) The remote Network Address Translation (NAT) address of the
         NAT device associated with a remote peer of this IKEv1 SA.  Note, this
         column is created and automatically populated by the HAIPE not fronted
         by the NAT, for both inbound and outbound IKEv1 SAs when a NAT device
         is detected via IKEv1.

         (U//FOUO) The address type value set (IPv4 address value, IPv6 address
         value) in this column should be consistent with the hIKEv1SAAddressType
         column. "
    ::= { hIKEv1SADTableEntry 8 }

hIKEv1SARemoteNATDestinationPort  OBJECT-TYPE
    SYNTAX     PortNumber
    MAX-ACCESS read-only
    STATUS     current
    DESCRIPTION
        "(U//FOUO) The remote Destination Port of the Network Address
         Translation (NAT) device associated with the remote peer of this IKEv1
         SA.  Note, this column is created and automatically populated by the
         HAIPE not fronted by the NAT, for both inbound and outbound IKEv1 SAs
         when a NAT device is detected via IKEv1."
    ::= { hIKEv1SADTableEntry 9 }

hIKEv1SASPI OBJECT-TYPE
    SYNTAX     Unsigned32 (256..4294967295)
    MAX-ACCESS read-only
    STATUS     current
    DESCRIPTION
        "(U//FOUO) The Security Parameter Index (SPI) associated with this IKEv1
         SA; in respect to IKEv1, the value is determined by the local HAIPE
         when the SA Direction is Inbound and is determined by the remote HAIPE
         when the SA Direction is Outbound.  Note, the hIKEv1SASPI column can
         not be set to any value in the range 0-255 (decimal)."
    ::= { hIKEv1SADTableEntry 10 }

hIKEv1SADirection OBJECT-TYPE
    SYNTAX     INTEGER {inbound(1), outbound(2)}
    MAX-ACCESS read-only
    STATUS     current
    DESCRIPTION
        "(U//FOUO) The traffic flow direction for this IKEv1 SA; the possible
         values are: inbound and outbound."
    ::= { hIKEv1SADTableEntry 11 }

hIKEv1SATransformSuite OBJECT-TYPE
    SYNTAX     HaipeIKEv1SATransformSuites
    MAX-ACCESS read-only
    STATUS     current
    DESCRIPTION
        "(U//FOUO) A set of cryptographic attributes respective to the
         established IKEv1 SA."
    ::= { hIKEv1SADTableEntry 12 }

hIKEv1SADSCPClassifiers OBJECT-TYPE
    SYNTAX     OCTET STRING (SIZE(8))
    MAX-ACCESS read-only
    STATUS     current
    DESCRIPTION
        "(U//FOUO) The DSCP classifiers for this IKEv1 SA; the default
         value is 0 (decimal).  Note, this column must only exist for Outbound
         IKEv1 SAs.  For IPv4 headers, the DSCP bits are the six most
         significant bits of the Type of Service (TOS) field.  For IPv6
         headers, the DSCP bits are the six most significant bits of the
         Traffic Class (TC) field.

         (U//FOUO) The DSCP classifier provides the mechanism to determine
         whether outbound packets are allowed to traverse the IKEv1 SA as
         based on the PT DSCP value.  Note, as defined by RFC 4301, classifiers
         are not traffic selectors since they only apply to outbound packets.

         (U//FOUO) This value must be 8 octets in length and the value in this
         column will provide a list of DSCP classifier values represented as a
         64-bit vector.  Each bit of this value represents a DSCP classifier
         value and set classifiers are indicated with its mapped bit is set to
         1 (binary).

         (U//FOUO)64 bit vector representation:
         DSCP value matches 64-bit Vector Map
                  0         000...000001
                  1         000...000010
                  2         000...000100
                     . . .
                     . . .
                     . . .
                 62         010000...000
                 63         100000...000"
    ::= { hIKEv1SADTableEntry 13 }

hIKEv1SAECNSetting OBJECT-TYPE
    SYNTAX     INTEGER {disabled(1), congestionNotification(2), admissionControl(3)}
    MAX-ACCESS read-write
    STATUS     current
    DESCRIPTION
        "(U//FOUO) The setting that controls the processing mode of the Explicit
         Congestion Notification (ECN) bits, during encapsulation and
         decapsulation; the possible values are: disabled,
         congestionNotification, admissionControl.  For IPv4 headers, the ECN
         bits are Bits 1-0 (low/right) of the Type of Service (TOS) bits.  For
         IPv6 headers, the ECN bits are Bits 1-0 (low/right) of the Traffic
         Class (TC) bits.

         (U//FOUO) [disabled] If this column is set to disabled, when
         encapsulation takes place the ECN bits must be set to (10) in the CT
         header regardless of the values in the PT header of the packet being
         encapsulated.  For decapsulation, the inner headers are passed
         through unmodified.

         (U//FOUO) [congestionNotification] If this column is set to
         congestionNotification, when encapsulation takes place the ECN bits
         must be set to (10) in the CT header regardless of the values in the
         PT header of the packet being encapsulated.  For decapsulation, see
         the HAIPE IS for more details on the ECN bits processing.

         (U//FOUO) [admissionControl] If this column is set to admissionControl,
         when encapsulation takes place the ECN bits must be copied from PT
         header to the CT header.  For decapsulation, the ECN bits must be
         copied from CT header to PT header."
    ::= { hIKEv1SADTableEntry 14 }

hIKEv1SADFBitSetting OBJECT-TYPE
    SYNTAX     INTEGER {set(1), clear(2), copy(3)}
    MAX-ACCESS read-write
    STATUS     current
    DESCRIPTION
        "(U//FOUO) The setting that controls the processing mode of the Don't
         Fragment (DF) bit in the IPv4 CT header (encapsulation); the possible
         values are: set, clear, copy.  Note, this column must only exist for
         Outbound IPv4 IKEv1 SAs.

         (U//FOUO) [set] If this column is set to set, the IPv4 CT header DF
         bit must be set to 1 (binary).

         (U//FOUO) [clear] If this column is set to clear, the IPv4 CT header
         DF Bit must be set to 0 (binary).

         (U//FOUO) [copy] If this column is set to copy, the IPv4 PT header's
         DF Bit value is copied to the IPv4 CT header's DF Bit, during
         encapsulation."
    ::= { hIKEv1SADTableEntry 15 }

hIKEv1SACTDSCPSetting OBJECT-TYPE
    SYNTAX     INTEGER {set(1), acceptList(2)}
    MAX-ACCESS read-write
    STATUS     current
    DESCRIPTION
        "(U//FOUO) The setting that controls the processing mode of the
         Differentiated Service Code Points (DSCP) bits in the CT header
         (encapsulation); the possible values are: set, acceptList.  Note, this
         column must only exist for Outbound IKEv1 SAs.  For IPv4 headers, the
         DSCP bits are the six most significant bits of the Type of Service
         (TOS) field.  For IPv6 headers, the DSCP bits are the six most
         significant bits of the Traffic Class (TC) field.

         (U//FOUO) [set] If this column is set to set, the CT header DSCP bits
         must be set to the value defined in the hIKEv1SACTDSCPValue column.

         (U//FOUO) [acceptList] If this column is set to acceptList, the PT
         header DSCP bits are compared against a list of values defined in the
         hIKEv1SACTDSCPValue column; if the compared DSCP bits is matched, they
         are copied over to the CT header DSCP bits.  If there is no match, the
         CT header DSCP bits are set to all 0s. "
    ::= { hIKEv1SADTableEntry 16 }

hIKEv1SACTDSCPValue OBJECT-TYPE
    SYNTAX     OCTET STRING (SIZE (1|8))
    MAX-ACCESS read-write
    STATUS     current
    DESCRIPTION
        "(U//FOUO) Depending on the value set in the hIKEv1SACTDSCPSetting
         column (set, acceptList), this column is used in two ways.  Note, this
         column must only exist for Outbound IKEv1 SAs.  For IPv4 headers, the
         DSCP bits are the six most significant bits of the Type of Service
         (TOS) field.  For IPv6 headers, the DSCP bits are the six most
         significant bits of the Traffic Class (TC) field.

         (U//FOUO) [hIKEv1SACTDSCPSetting=set] If the hIKEv1SACTDSCPSetting
         column is set to set, the CT header Differentiated Service Code Points
         (DSCP) bits must be set to the value defined in this column and the
         value in this column must be one octet in length in the range 0x00 to
         0x3f.  The DSCP value garnered from the Bits 5-0 (low/right most
         6-bits) of this column's value is placed in the CT header DSCP bits.
         Note, if the hIKEv1SACTDSCPSetting column is set to set, an attempt to
         set this column to value outside of the range 0x00 to 0x3f should fail
         with an invalid value error.

         (U//FOUO) [hIKEv1SACTDSCPSetting=acceptList] If the
         hIKEv1SACTDSCPSetting column is set to acceptList, this value must be
         8 octets in length and the value in this column will provide a list of
         acceptable DSCP values represented as a 64-bit vector.  Each bit of
         this value represents one acceptable DSCP value and acceptable matches
         are indicated with its mapped bit is set to 1 (binary).  If the
         outgoing PT packet's DSCP value matches a value represented in the
         vector, that value is placed in the CT header DSCP bits.  If none of
         the values in the vector match an outgoing PT packet's DSCP value, the
         CT header DSCP bits are set to all 0s.

         (U//FOUO)64 bit vector representation:
         DSCP value matches 64-bit Vector Map
                  0         000...000001
                  1         000...000010
                  2         000...000100
                     . . .
                     . . .
                     . . .
                 62         010000...000
                 63         100000...000"
    ::= { hIKEv1SADTableEntry 17 }

hIKEv1SAFlowLabelSetting OBJECT-TYPE
    SYNTAX     INTEGER {set(1), copy(2)}
    MAX-ACCESS read-write
    STATUS     current
    DESCRIPTION
        "(U//FOUO) The setting that controls the processing mode of the Flow
         Label bits in the CT header (encapsulation); the possible values are:
         set, copy; the default value is set.  Note, this column must only
         exists for Outbound IPv6 IKEv1 SAs.

         (U//FOUO) [set] If this column is set to set, the CT header Flow Label
         bits must be set to the value defined in the hIKEv1SACTFlowLabelValue
         column.

         (U//FOUO) [copy] If this column is set to copy, when encapsulation
         takes place the Flow Label bits must be copied from PT header to the
         CT header."
    ::= { hIKEv1SADTableEntry 18 }

hIKEv1SACTFlowLabelValue  OBJECT-TYPE
    SYNTAX     OCTET STRING (SIZE(3))
    MAX-ACCESS read-write
    STATUS     current
    DESCRIPTION
        "(U//FOUO) The flow label value for this IKEv1 SA. The use of this value
         is dependent on the value of the hIKEv1SAFlowLabelSetting column (set,
         copy) in this row.  Note, this column must only exist for Outbound IPv6
         IKEv1 SAs.

         (U//FOUO) [hIKEv1SAFlowLabelSetting=set] If the  column is set to set,
         the CT header Flow Label bits must be set to the value defined in this
         column and the value in this column must be one 20-bits in length in
         the range between 0x00 and 0xfffff.  The Flow Label value garnered from
         the Bits 19-0 (low/right most 20-bits) of this column's value is placed
         in the CT header Flow Label bits.  Note, if the
         hIKEv1SAFlowLabelSetting column is set to set, an attempt to set this
         column to value outside of the range 0x00 to 0xfffff should fail with
         an invalid value error.
	 
	 (U//FOUO) If hIKEv1SAFlowLabelSetting is set to 'copy', this column
	 must not exist."
    ::= { hIKEv1SADTableEntry 19 }

hIKEv1SAPDUNEnabled OBJECT-TYPE
    SYNTAX     TruthValue
    MAX-ACCESS read-write
    STATUS     current
    DESCRIPTION
        "(U//FOUO) The setting that determines whether or not Peer Destination
         Unreachable Notification (PDUN) messages are transmitted upon
         determination that a host is unreachable on an Inbound IKEv1 SA; the
         possible values are: true, false.  Note, this column must only exist
         for Inbound IKEv1 SAs.

         (U//FOUO) Note, for IKEv1 SAs, PDUN messages are transmitted on the
         paired Outbound IKEv1 SA established with the remote HAIPE."
    ::= { hIKEv1SADTableEntry 20 }

hIKEv1SAPHRDRate OBJECT-TYPE
    SYNTAX     Unsigned32
    MAX-ACCESS read-write
    STATUS     current
    DESCRIPTION
        "(U//FOUO) The setting that determines the rate (in seconds) at which
         Peer HAIPE Reachability Detection (PHRD) messages are transmitted on
         this IKEv1 SA; the default value is 0 (decimal).  A value of zero
         (decimal) indicates the disabled PHRD Setting, meaning that PHRD
         messages will not be transmitted.  Note, this column must only exist
         for Outbound IKEv1 SAs."
    ::= { hIKEv1SADTableEntry 21 }

hIKEv1SAPHRDLimit OBJECT-TYPE
    SYNTAX     Unsigned32
    MAX-ACCESS read-write
    STATUS     current
    DESCRIPTION
        "(U//FOUO) Setting that determines the number of successive missed Peer
         HAIPE Reachability Detection (PHRD) responses that will trigger the
         HAIPE to mark this IKEv1 SA as UNREACHABLE.  A PHRD response or any
         inbound traffic received on an Inbound IKEv1 SA established with the
         remote HAIPE resets the internal PHRD successive missed counter to its
         initial state.  Note, this column must only exist for Outbound IKEv1
         SAs and when the hIKEv1SAPHRDRate column is set to a non-zero value 
	 (decimal)."
    ::= { hIKEv1SADTableEntry 22 }

hIKEv1SAReachabilityStatus OBJECT-TYPE
    SYNTAX     TruthValue
    MAX-ACCESS read-only
    STATUS     current
    DESCRIPTION
        "(U//FOUO) The Reachability Status of this IKEv1 SA; the possible values
         are: true, false.   The value in this column is determined by the
         hIKEv1SAPHRDRate column and the hIKEv1SAPHRDLimit column; a IKEv1 SA is
         determined UNREACHABLE if the hIKEv1SAPHRDLimit threshold is reached
         for the number of successive missed PHRD responses.  Note, this column
         must only exist for Outbound IKEv1 SAs.

         (U//FOUO) [true] If this column is set to true, this IKEv1 SA is
         REACHABLE.

         (U//FOUO) [false] If this column is set to false, this IKEv1 SA is
         UNREACHABLE."
    ::= { hIKEv1SADTableEntry 23 }

hIKEv1SATFCConfigName OBJECT-TYPE
    SYNTAX     SnmpAdminString (SIZE(0..32))
    MAX-ACCESS read-write
    STATUS     current
    DESCRIPTION
        "(U//FOUO) A reference string that points to an entry in the
         hTFCConfigTable, which details the Traffic Flow Confidentiality (TFC)
         mechanisms employed by this IKEv1 SA.  Note, if this column is not
         populated or set to a zero length empty string, then no TFC mechanisms
         will be employed by the IKEv1 SA."
    ::= { hIKEv1SADTableEntry 24 }

hIKEv1SARowStatus OBJECT-TYPE
    SYNTAX     RowStatus
    MAX-ACCESS read-write
    STATUS     current
    DESCRIPTION
        "(U//FOUO) The status of the row, by which old entries may be edited or
         deleted from this table.

         (U//FOUO) At a minimum, implementations must support active and destroy
         management functions. Support for notInService, and notReady management
         functions is optional. Implementations must not support createAndWait and
         createAndGo management functions for this object."
    ::= { hIKEv1SADTableEntry 25 }

-- **********************************************************************
-- IKEv2 SAD
-- **********************************************************************

-- =========
-- IKEv2 CHILD SAD Table
-- =========

hIKEv2CHILDSADTableCount OBJECT-TYPE
    SYNTAX     Unsigned32
    MAX-ACCESS read-only
    STATUS     current
    DESCRIPTION
        "(U//FOUO) The number of rows in the hIKEv2CHILDSADTable."
    ::= { hIKEv2CHILDSAD 1 }

hIKEv2CHILDSADTableLastChanged OBJECT-TYPE
    SYNTAX     TimeStamp
    MAX-ACCESS read-only
    STATUS     current
    DESCRIPTION
        "(U//FOUO) The value of hSystemUpTime the last time any entry in the
         hIKEv2CHILDSADTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hIKEv2CHILDSAD 2 }

hIKEv2CHILDSADTable OBJECT-TYPE
    SYNTAX     SEQUENCE OF HIKEv2CHILDSADTableEntry
    MAX-ACCESS not-accessible
    STATUS     current
    DESCRIPTION
        "(U//FOUO) The table for configuring and viewing IKEv2 CHILD_SAs
         relevant to a HAIPE device.  IKEv2 CHILD_SAs must have one parent IKEv2
         IKE_SA associated; an IKEv2 CHILD_SA can not exist without a parent
         IKE_SA and upon deletion of an IKE_SA, all CHILD_SAs will also be
         deleted.  All IKEv2 IKE_SAs are represented by the hIKEv2IKESADTable.
         Note, columns may apply to only Inbound IKEv2 CHILD_SAs, Outbound IKEv2
         CHILD_SAs, or both; each column's description describes the
         Inbound/Outbound context applicability."
    ::= { hIKEv2CHILDSAD 3 }

hIKEv2CHILDSADTableEntry OBJECT-TYPE
    SYNTAX     HIKEv2CHILDSADTableEntry
    MAX-ACCESS not-accessible
    STATUS     current
    DESCRIPTION
        "(U//FOUO) A row describing the information about the relevant,
         established IKEv2 CHILD_SAs on this HAIPE.  Each row signifies either
         an Outbound IKEv2 CHILD_SA or an Inbound IKEv2 CHILD_SA; the value in
         the hIKEv2CHILDSADirection column determines this directionality.
         Note, IKEv2 CHILD_SAs must have an associated parent IKEv2 IKE_SA; the
         value in the hIKEv2CHILDSAIKESAIndex column captures this
         relationship."
    INDEX  { hIKEv2CHILDSAIndex }
    ::= { hIKEv2CHILDSADTable 1 }

HIKEv2CHILDSADTableEntry ::= SEQUENCE
{
   hIKEv2CHILDSAIndex              Unsigned32,
   hIKEv2CHILDSAIKESAIndex         Unsigned32,
   hIKEv2CHILDSAEstTrafficSelName  SnmpAdminString,
   hIKEv2CHILDSAAddressType        IPAddressType,
   hIKEv2CHILDSALocalCTAddress     IPAddress,
   hIKEv2CHILDSARemoteCTAddress    IPAddress,
   hIKEv2CHILDSALocalPTAddress     IPAddress,   
   hIKEv2CHILDSARemotePTAddress    IPAddress,
   hIKEv2CHILDSARemoteNATAddress   IPAddress,
   hIKEv2CHILDSARemoteNATDestPort  PortNumber,
   hIKEv2CHILDSASPI                Unsigned32,
   hIKEv2CHILDSADirection          INTEGER,
   hIKEv2CHILDSAEncapsulationMode  INTEGER,
   hIKEv2CHILDSATransformSuite     HaipeIKEv2CHILDSATransformSuites,
   hIKEv2CHILDSADSCPClassifiers    OCTET STRING,
   hIKEv2CHILDSAECNSetting         INTEGER,
   hIKEv2CHILDSADFBitSetting       INTEGER,
   hIKEv2CHILDSACTDSCPSetting      INTEGER,
   hIKEv2CHILDSACTDSCPValue        OCTET STRING,
   hIKEv2CHILDSAFlowLabelSetting   INTEGER,
   hIKEv2CHILDSACTFlowLabelValue   OCTET STRING,
   hIKEv2CHILDSAPDUNEnabled        TruthValue,
   hIKEv2CHILDSAReachabilityStatus TruthValue,
   hIKEv2CHILDSATFCConfigName      SnmpAdminString,
   hIKEv2CHILDSAEstROHCParamsIndex Unsigned32,
   hIKEv2CHILDSAEstBMParamsIndex   SnmpAdminString,
   hIKEv2CHILDSARowStatus          RowStatus
}

hIKEv2CHILDSAIndex OBJECT-TYPE
    SYNTAX      Unsigned32
    MAX-ACCESS not-accessible
    STATUS     current
    DESCRIPTION
        "(U//FOUO) An unique numeric index that identifies this IKEv2 CHILD_SA;
         the hIKEv2CHILDSAIndex column is the primary index column for this
         table.  Note, this column is populated internally and can not be read
         or configured."
    ::= { hIKEv2CHILDSADTableEntry 1 }

hIKEv2CHILDSAIKESAIndex OBJECT-TYPE
    SYNTAX     Unsigned32
    MAX-ACCESS read-only
    STATUS     current
    DESCRIPTION
        "(U//FOUO) A reference index that points to one entry in the
         hIKEv2IKESADTable.  This referenced row defines the parent IKEv2
         IKE_SA associated with this IKEv2 CHILD_SA."
    ::= { hIKEv2CHILDSADTableEntry 2 }

hIKEv2CHILDSAEstTrafficSelName OBJECT-TYPE
    SYNTAX     SnmpAdminString (SIZE(1..32))
    MAX-ACCESS read-only
    STATUS     current
    DESCRIPTION
        "(U//FOUO) A reference string that points to one entry in the
         hEstLocalTSTable and one entry in the
         hEstRemoteTSTable.  These referenced rows define the
         allowable set of traffic selectors (one or more can be associated in a
         Mix and Match semantic) allowed on this IKEv2 CHILD_SA.

         (U//FOUO) Note, if the hIKEv2CHILDSAEncapsulationMode column is set to
         transportMode, this column must reference one entry in the
         hEstLocalTSTable and one entry in the
         hEstRemoteTSTable; these  entries contains the specific
         host pair address selectors."
    ::= { hIKEv2CHILDSADTableEntry 3 }

hIKEv2CHILDSAAddressType OBJECT-TYPE
    SYNTAX     IPAddressType
    MAX-ACCESS read-only
    STATUS     current
    DESCRIPTION
        "(U//FOUO) The local and remote HAIPE address types (CT and PT)
         associated with this IKEv2 CHILD_SA; the possible values are: IPv4 and
         IPv6.  The value in this column directly influences the address type
         values in the hIKEv2CHILDSALocalCTAddress,
         hIKEv2CHILDSARemoteCTAddress, hIKEv2CHILDSARemotePTAddress and the 
         hIKEv2CHILDSARemoteNATAddress (if applicable) columns."
    ::= { hIKEv2CHILDSADTableEntry 4 }

hIKEv2CHILDSALocalCTAddress OBJECT-TYPE
    SYNTAX     IPAddress
    MAX-ACCESS read-only
    STATUS     current
    DESCRIPTION
        "(U//FOUO) The local HAIPE CT address associated with this IKEv2
         CHILD_SA.  The address type value set (IPv4 address value, IPv6 address
         value) in this column should be consistent with the
         hIKEv2CHILDSAAddressType column."
    ::= { hIKEv2CHILDSADTableEntry 5 }

hIKEv2CHILDSARemoteCTAddress OBJECT-TYPE
    SYNTAX     IPAddress
    MAX-ACCESS read-only
    STATUS     current
    DESCRIPTION
        "(U//FOUO) The remote HAIPE CT address associated with this IKEv2
         CHILD_SA.  The address type value set (IPv4 address value, IPv6
         address value) in this column should be consistent with the
         hIKEv2CHILDSAAddressType column."
    ::= { hIKEv2CHILDSADTableEntry 6 }
    
hIKEv2CHILDSALocalPTAddress OBJECT-TYPE
    SYNTAX     IPAddress
    MAX-ACCESS read-only
    STATUS     current
    DESCRIPTION
        "(U//FOUO) The local HAIPE PT address associated with this IKEv2
         CHILD_SA.  The address type value set (IPv4 address value, IPv6 address
         value) in this column should be consistent with the
         hIKEv2CHILDSAAddressType column."
    ::= { hIKEv2CHILDSADTableEntry 7 }     
    
hIKEv2CHILDSARemotePTAddress  OBJECT-TYPE
    SYNTAX     IPAddress
    MAX-ACCESS read-only
    STATUS     current
    DESCRIPTION
        "(U//FOUO) The remote HAIPE PT Address associated with this IKEv2
         CHILD_SA.  The address type value set (IPv4 address value, IPv6 address
         value) in this column should be consistent with the
         hIKEv2CHILDSAAddressType column."
    ::= { hIKEv2CHILDSADTableEntry 8 }

hIKEv2CHILDSARemoteNATAddress OBJECT-TYPE
    SYNTAX     IPAddress
    MAX-ACCESS read-only
    STATUS     current
    DESCRIPTION
        "(U//FOUO) The remote Network Address Translation (NAT) address of the
         NAT device associated with a remote peer of this IKEv2 CHILD_SA.  Note,
         this column is created and automatically populated by the HAIPE not
         fronted by the NAT, for both inbound and outbound IKEv2 CHILD_SAs when
         a NAT device is detected via IKEv2.

         (U//FOUO) The address type value set (IPv4 address value, IPv6 address
         value) in this column should be consistent with the
         hIKEv2CHILDSAAddressType column."
    ::= { hIKEv2CHILDSADTableEntry 9 }

hIKEv2CHILDSARemoteNATDestPort OBJECT-TYPE
    SYNTAX     PortNumber
    MAX-ACCESS read-only
    STATUS     current
    DESCRIPTION
        "(U//FOUO) The remote Destination Port of the Network Address
         Translation (NAT) device associated with the remote peer of this IKEv2
         CHILD_SA.  Note, this column is created and automatically populated by
         the HAIPE not fronted by the NAT, for both inbound and outbound IKEv2
         CHILD_SAs when a NAT device is detected via IKEv2."
    ::= { hIKEv2CHILDSADTableEntry 10 }

hIKEv2CHILDSASPI OBJECT-TYPE
    SYNTAX     Unsigned32 (256..4294967295)
    MAX-ACCESS read-only
    STATUS     current
    DESCRIPTION
        "(U//FOUO) The Security Parameter Index (SPI) associated with this IKEv2
         CHILD_SA; in respect to IKEv2, the value is determined by the local
         HAIPE when the SA Direction is Inbound and is determined by the remote
         HAIPE when the SA Direction is Outbound.  Note, the hIKEv2CHILDSASPI
         column can not be set to any value in the reange 0-255 (decimal)."
    ::= { hIKEv2CHILDSADTableEntry 11 }

hIKEv2CHILDSADirection OBJECT-TYPE
    SYNTAX     INTEGER {inbound(1), outbound(2)}
    MAX-ACCESS read-only
    STATUS     current
    DESCRIPTION
        "(U//FOUO) The traffic flow direction for this IKEv2 CHILD_SA; the
         possible values are: inbound and outbound."
    ::= { hIKEv2CHILDSADTableEntry 12 }

hIKEv2CHILDSAEncapsulationMode OBJECT-TYPE
    SYNTAX     INTEGER {transportMode(1), tunnelMode(2)}
    MAX-ACCESS read-only
    STATUS     current
    DESCRIPTION
        "(U//FOUO) The IKEv2 CHILD_SA's Encapsulation Mode; the possible values
         are: transportMode and tunnelMode.

         (U//FOUO) If this column is set to transportMode, the
         hIKEv2CHILDSAEstTrafficSelName column must reference one
         hEstLocalTSTable entry and one
         hEstRemoteTSTable entry; that entry must be scoped to the
         specific host pair address selectors."
    ::= { hIKEv2CHILDSADTableEntry 13 }

hIKEv2CHILDSATransformSuite OBJECT-TYPE
    SYNTAX     HaipeIKEv2CHILDSATransformSuites
    MAX-ACCESS read-only
    STATUS     current
    DESCRIPTION
        "(U//FOUO) A set of cryptographic attributes respective to the
         established IKEv2 CHILD_SA."
    ::= { hIKEv2CHILDSADTableEntry 14 }
    
hIKEv2CHILDSADSCPClassifiers OBJECT-TYPE
    SYNTAX     OCTET STRING (SIZE(8))
    MAX-ACCESS read-only
    STATUS     current
    DESCRIPTION
        "(U//FOUO) The DSCP classifiers for this IKEv2 CHILD_SA; the
         default value is 0 (decimal).  Note, this column must only exist for
         Outbound IKEv2 CHILD_SAs.  For IPv4 headers, the DSCP bits are the
         six most significant bits of the Type of Service (TOS) field.  For
         IPv6 headers, the DSCP bits are the six most significant bits of the
         Traffic Class (TC) field.

         (U//FOUO) The DSCP classifier provides the mechanism to determine
         whether outbound packets are allowed to traverse the IKEv2 CHILD_SA as
         based on the PT DSCP value.  Note, as defined by RFC 4301, classifiers
         are not traffic selectors since they only apply to outbound packets.

         (U//FOUO) This value must be 8 octets in length and the value in this
         column will provide a list of DSCP classifier values represented as a
         64-bit vector.  Each bit of this value represents a DSCP classifier
         value and set classifiers are indicated with its mapped bit is set to
         1 (binary).

         (U//FOUO)64 bit vector representation:
         DSCP value matches 64-bit Vector Map
                  0         000...000001
                  1         000...000010
                  2         000...000100
                     . . .
                     . . .
                     . . .
                 62         010000...000
                 63         100000...000"
    ::= { hIKEv2CHILDSADTableEntry 15 }

hIKEv2CHILDSAECNSetting OBJECT-TYPE
    SYNTAX     INTEGER {disabled(1), congestionNotification(2), admissionControl(3)}
    MAX-ACCESS read-write
    STATUS     current
    DESCRIPTION
        "(U//FOUO) The setting that controls the processing mode of the Explicit
         Congestion Notification (ECN) bits, during encapsulation and
         decapsulation; the possible values are: disabled,
         congestionNotification, admissionControl.  For IPv4 headers, the ECN
         bits are Bits 1-0 (low/right) of the Type of Service (TOS) bits.  For
         IPv6 headers, the ECN bits are Bits 1-0 (low/right) of the Traffic
         Class (TC) bits.

         (U//FOUO) [disabled] If this column is set to disabled, when
         encapsulation takes place the ECN bits must be set to (10) in the CT
         header regardless of the values in the PT header of the packet being
         encapsulated.  For decapsulation, the inner headers are passed through
         unmodified.

         (U//FOUO) [congestionNotification] If this column is set to
         congestionNotification, when encapsulation takes place the ECN bits
         must be set to (10) in the CT header regardless of the values in the
         PT header of the packet being encapsulated.  For decapsulation, see
         the HAIPE IS for more details on the ECN bits processing.

         (U//FOUO) [admissionControl] If this column is set to
         admissionControl, when encapsulation takes place the ECN bits must be
         copied from PT header to the CT header.  For decapsulation, the ECN
         bits must be copied from CT header to PT header."
    ::= { hIKEv2CHILDSADTableEntry 16 }

hIKEv2CHILDSADFBitSetting OBJECT-TYPE
    SYNTAX     INTEGER {set(1), clear(2), copy(3)}
    MAX-ACCESS read-write
    STATUS     current
    DESCRIPTION
        "(U//FOUO) The setting that controls the processing mode of the Don't
         Fragment (DF) bit in the IPv4 CT header (encapsulation); the possible
         values are: set, clear, copy.  Note, this column must only exist for
         Outbound IPv4 IKEv2 CHILD_SAs.

         (U//FOUO) [set] If this column is set to set, the IPv4 CT header DF
         bit must be set to 1 (binary).

         (U//FOUO) [clear] If this column is set to clear, the IPv4 CT header
         DF Bit must be set to 0 (binary).

         (U//FOUO) [copy] If this column is set to copy, the IPv4 PT header's DF
         Bit value is copied to the IPv4 CT header's DF Bit, during
         encapsulation."
    ::= { hIKEv2CHILDSADTableEntry 17 }

hIKEv2CHILDSACTDSCPSetting OBJECT-TYPE
    SYNTAX     INTEGER {set(1), acceptList(2)}
    MAX-ACCESS read-write
    STATUS     current
    DESCRIPTION
        "(U//FOUO) The setting that controls the processing mode of the
         Differentiated Service Code Points (DSCP) bits in the CT header
         (encapsulation); the possible values are: set, acceptList.  Note, this
         column must only exist for Outbound IKEv2 CHILD_SAs.  For IPv4 headers,
         the DSCP bits are the six most significant bits of the Type of Service
         (TOS) field.  For IPv6 headers, the DSCP bits are the six most
         significant bits of the Traffic Class (TC) field.

         (U//FOUO) [set] If this column is set to set, the CT header DSCP bits
         must be set to the value defined in the hIKEv2CHILDSACTDSCPValue column.

         (U//FOUO) [acceptList] If this column is set to acceptList, the PT
         header DSCP bits are compared against a list of values defined in the
         hIKEv2CHILDSACTDSCPValue column; if the compared DSCP bits is matched,
         they are copied over to the CT header DSCP bits.  If there is no match,
         the CT header DSCP bits are set to all 0s. "
    ::= { hIKEv2CHILDSADTableEntry 18 }

hIKEv2CHILDSACTDSCPValue OBJECT-TYPE
    SYNTAX     OCTET STRING (SIZE (1|8))
    MAX-ACCESS read-write
    STATUS     current
    DESCRIPTION
        "(U//FOUO) Depending on the value set in the hIKEv2CHILDSACTDSCPSetting
         column (set, acceptList), this column is used in two ways.  Note, this
         column must only exist for Outbound IKEv2 CHILD_SAs.  For IPv4 headers,
         the DSCP bits are the six most significant bits of the Type of Service
         (TOS) field.  For IPv6 headers, the DSCP bits are the six most
         significant bits of the Traffic Class (TC) field.

         (U//FOUO) [hIKEv2CHILDSACTDSCPSetting=set] If the
         hIKEv2CHILDSACTDSCPSetting column is set to set, the CT header
         Differentiated Service Code Points (DSCP) bits must be set to the value
         defined in this column and the value in this column must be one octet
         in length in the range 0x00 to 0x3f.  The DSCP value garnered from the
         Bits 5-0 (low/right most 6-bits) of this column's value is placed in
         the CT header DSCP bits.  Note, if the hIKEv2CHILDSACTDSCPSetting
         column is set to set, an attempt to set this column to value outside of
         the range 0x00 to 0x3f should fail with an invalid value error.

         (U//FOUO) [hIKEv2CHILDSACTDSCPSetting=acceptList] If the
         hIKEv2CHILDSACTDSCPSetting column is set to acceptList, this value must
         be 8 octets in length and the value in this column will provide a list
         of acceptable DSCP values represented as a 64-bit vector.  Each bit of
         this value represents one acceptable DSCP value and acceptable matches
         are indicated with its mapped bit is set to 1 (binary).  If the
         outgoing PT packet's DSCP value matches a value represented in the
         vector, that value is placed in the CT header DSCP bits.  If none of
         the values in the vector match an outgoing PT packet's DSCP value, the
         CT header DSCP bits are set to all 0s.

         (U//FOUO)64 bit vector representation:
         DSCP value matches 64-bit Vector Map
                  0         000...000001
                  1         000...000010
                  2         000...000100
                     . . .
                     . . .
                     . . .
                 62         010000...000
                 63         100000...000"
    ::= { hIKEv2CHILDSADTableEntry 19 }

hIKEv2CHILDSAFlowLabelSetting OBJECT-TYPE
    SYNTAX     INTEGER {set(1), copy(2)}
    MAX-ACCESS read-write
    STATUS     current
    DESCRIPTION
        "(U//FOUO) The setting that controls the processing mode of the Flow
         Label bits in the CT header (encapsulation); the possible values are:
         set, copy.  Note, this column must only exist for Outbound IPv6 IKEv2
         CHILD_SAs.

         (U//FOUO) [set] If this column is set to set, the CT header Flow Label
         bits must be set to the value defined in the
         hIKEv2CHILDSACTFlowLabelValue column.

         (U//FOUO) [copy] If this column is set to copy, when encapsulation
         takes place the Flow Label bits must be copied from PT header to the
         CT header."
    ::= { hIKEv2CHILDSADTableEntry 20 }

hIKEv2CHILDSACTFlowLabelValue OBJECT-TYPE
    SYNTAX     OCTET STRING (SIZE (3))
    MAX-ACCESS read-write
    STATUS     current
    DESCRIPTION
        "(U//FOUO) The flow label value for this IKEv2 CHILD_SA. The use of the
         value is dependent on the value of the hIKEv2CHILDSAFlowLabelSetting
         column (set, copy) in this row. Note, this column must only exist for
         Outbound IPv6 IKEv2 CHILD_SAs.

         (U//FOUO) [hIKEv2CHILDSAFlowLabelSetting=set] If the column is set to
         set, the CT header Flow Label bits must be set to the value defined in
         this column and the value in this column must be one 20-bits in length
         in the range between 0x00 and 0xfffff.  The Flow Label value garnered
         from the Bits 19-0 (low/right most 20-bits) of this column's value is
         placed in the CT header Flow Label bits.  Note, if the
         hIKEv2CHILDSAFlowLabelSetting column is set to set, an attempt to set
         this column to value outside of the range between 0x00 to 0xfffff
         should fail with an invalid value error.
	 
	 (U//FOUO) If hIKEv2CHILDSAFlowLabelSetting is set to 'copy', this
	 column must not exist."
    ::= { hIKEv2CHILDSADTableEntry 21 }

hIKEv2CHILDSAPDUNEnabled OBJECT-TYPE
    SYNTAX     TruthValue
    MAX-ACCESS read-write
    STATUS     current
    DESCRIPTION
        "(U//FOUO) The setting that determines whether or not Peer Destination
         Unreachable Notification (PDUN) messages are transmitted upon
         determination that a host is unreachable on an  Inbound IKEv2 CHILD_SA;
         the possible values are: true, false.

         (U//FOUO) Note, for IKEv2 CHILD_SAs, PDUN messages are transmitted on
         the parent IKEv2 IKE_SA established with the remote HAIPE."
    ::= { hIKEv2CHILDSADTableEntry 22 }

hIKEv2CHILDSAReachabilityStatus OBJECT-TYPE
    SYNTAX     TruthValue
    MAX-ACCESS read-only
    STATUS     current
    DESCRIPTION
        "(U//FOUO) The Reachability Status of this IKEv2 CHILD_SA; the possible
         values are: true, false.   The value in this column is determined by
         the hIKEv2IKESALivenessTestRate column and the
         hIKEv2IKESALivenessTestLimit column of the parent IKEv2 IKE_SA, nameley
         the hIKEv2IKESADTable entry as referenced by the value in the
         hIKEv2CHILDSAIKESAIndex column ; an IKEv2 CHILD_SA is determined
         UNREACHABLE if the hIKEv2IKESALivenessTestLimit threshold is reached
         for the number of successive missed Liveness responses.  As defined by
         the HAIPE IS, if an IKEv2 IKE_SA is determined UNREACHABLE, than all of
         its CHILD_SAs are also UNREACHABLE.  Note, this column must only exist
         for Outbound IKEv2 CHILD_SAs.

         (U//FOUO) [true] If this column is set to true, this IKEv2 CHILD_SA is
         REACHABLE.

         (U//FOUO) [false] If this column is set to false, this IKEv2 CHILD_SA
         is UNREACHABLE."
    ::= { hIKEv2CHILDSADTableEntry 23 }

hIKEv2CHILDSATFCConfigName OBJECT-TYPE
    SYNTAX     SnmpAdminString (SIZE(0..32))
    MAX-ACCESS read-write
    STATUS     current
    DESCRIPTION
        "(U//FOUO) A reference string that points to an entry in the
         hTFCConfigTable, which details the Traffic Flow Confidentiality (TFC)
         mechanisms employed by this IKEv2 CHILD_SA.  Note, if this column is
         not populated or set to a zero length empty string then no TFC
         mechanisms will be employed by the IKEv2 CHILD_SA."
    ::= { hIKEv2CHILDSADTableEntry 24 }

hIKEv2CHILDSAEstROHCParamsIndex OBJECT-TYPE
    SYNTAX     Unsigned32
    MAX-ACCESS read-only
    STATUS     current
    DESCRIPTION
        "(U//FOUO) An unique numeric index that references a row in the
         hEstROHCParamTable; this referenced row stores the RoHC parameters
         associated with this IKEv2 CHILD_SA.

         (U//FOUO) This column must only exist if the Header Compression
         Extension is supported."
    ::= { hIKEv2CHILDSADTableEntry 25 }

hIKEv2CHILDSAEstBMParamsIndex OBJECT-TYPE
    SYNTAX     SnmpAdminString (SIZE(1..32))
    MAX-ACCESS read-write
    STATUS     current
    DESCRIPTION
        "(U//FOUO) A unique administrative name that references a row in the
         hEstBMParamTable. This referenced row stores the established BM 
	       parameters associated with this IKEv2 CHILD_ SA. If BM is disabled,
         this column must not be populated or it must be set to a zero length
         empty string.
	 
	       (U//FOUO) If this column exists and is populated with any value other
	       than a zero length empty string then: (1) hIKEv2CHILDSARowStatus can
	       only be set to 'active' if a valid value has been set for this column
	       and (2) the row pointed to by this column must have an
	       hEstBMParamRowStatus value of 'active'.
	 
         (U//FOUO) This column must only exist if the Bandwidth Management
         Extension is supported."
    ::= { hIKEv2CHILDSADTableEntry 26 }      
    
hIKEv2CHILDSARowStatus OBJECT-TYPE
    SYNTAX     RowStatus
    MAX-ACCESS read-write
    STATUS     current
    DESCRIPTION
        "(U//FOUO) The status of the row, by which old entries may be edited or
         deleted from this table.

         (U//FOUO) At a minimum, implementations must support active and destroy
         management functions. Support for notInService, and notReady management
         functions is optional. Implementations must not support createAndWait and
         createAndGo management functions for this object."
    ::= { hIKEv2CHILDSADTableEntry 27 }   

-- =========
-- IKEv2 IKE SAD Table
-- =========

hIKEv2IKESADTableCount OBJECT-TYPE
    SYNTAX     Unsigned32
    MAX-ACCESS read-only
    STATUS     current
    DESCRIPTION
        "(U//FOUO) The number of rows in the hIKEv2IKESADTable."
    ::= { hIKEv2IKESAD 1 }

hIKEv2IKESADTableLastChanged OBJECT-TYPE
    SYNTAX     TimeStamp
    MAX-ACCESS read-only
    STATUS     current
    DESCRIPTION
        "(U//FOUO) The value of hSystemUpTime the last time any entry in the
         hIKEv2IKESADTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hIKEv2IKESAD 2 }

hIKEv2IKESADTable OBJECT-TYPE
    SYNTAX     SEQUENCE OF HIKEv2IKESADTableEntry
    MAX-ACCESS not-accessible
    STATUS     current
    DESCRIPTION
        "(U//FOUO) The table for configuring and viewing IKEv2 IKE_SAs relevant
         to a HAIPE device.  IKEv2 CHILD_SAs must have one parent IKEv2 IKE_SA
         associated - an IKEv2 CHILD_SA can not exist without a parent IKE_SA
         and upon deletion of an IKE_SA, all CHILD_SAs will also be deleted.
         All IKEv2 CHILD_SAs are represented by the hIKEv2CHILDSADTable."
    ::= { hIKEv2IKESAD 3 }

hIKEv2IKESADTableEntry OBJECT-TYPE
    SYNTAX     HIKEv2IKESADTableEntry
    MAX-ACCESS not-accessible
    STATUS     current
    DESCRIPTION
        "(U//FOUO) A row describing the information about the relevant,
         established IKEv2 IKE_SA on this HAIPE."
    INDEX  { hIKEv2IKESAIndex }
    ::= { hIKEv2IKESADTable 1 }

HIKEv2IKESADTableEntry ::= SEQUENCE
{
   hIKEv2IKESAIndex                Unsigned32,
   hIKEv2IKESAAddressType          IPAddressType,
   hIKEv2IKESALocalCTAddress       IPAddress,
   hIKEv2IKESARemoteCTAddress      IPAddress,
   hIKEv2IKESALocalPTAddress       IPAddress,
   hIKEv2IKESARemotePTAddress      IPAddress,
   hIKEv2IKESARemoteNATAddress     IPAddress,
   hIKEv2IKESARemoteNATDestPort    PortNumber,
   hIKEv2IKESAInitiatorSPI         OCTET STRING,
   hIKEv2IKESAResponderSPI         OCTET STRING,
   hIKEv2IKESATransformSuite       HaipeIKEv2IKESATransformSuites,
   hIKEv2IKESALivenessTestRate     Unsigned32,
   hIKEv2IKESALivenessTestLimit    Unsigned32,
   hIKEv2IKESAReachabilityStatus   TruthValue,
   hIKEv2IKESARowStatus            RowStatus
}

hIKEv2IKESAIndex OBJECT-TYPE
    SYNTAX     Unsigned32
    MAX-ACCESS not-accessible
    STATUS     current
    DESCRIPTION
        "(U//FOUO) An unique numeric index that identifies this IKEv2 IKE_SA;
         the hIKEv2IKESAIndex column is the primary index column for this table.
         Note, this column is populated internally and can not be read or
         configured."
    ::= { hIKEv2IKESADTableEntry 1 }

hIKEv2IKESAAddressType OBJECT-TYPE
    SYNTAX     IPAddressType
    MAX-ACCESS read-only
    STATUS     current
    DESCRIPTION
        "(U//FOUO) The local and remote HAIPE address types (CT and PT)
         associated with this IKEv2 IKE_SA; the possible values are: IPv4 and
         IPv6.  The value in this column directly influences the address type
         values in the hIKEv2IKESALocalCTAddress, hIKEv2IKESARemoteCTAddress,
         hIKEv2IKESALocalPTAddress, hIKEv2IKESARemotePTAddress and the
         hIKEv2IKESARemoteNATAddress (if applicable) columns."
    ::= { hIKEv2IKESADTableEntry 2 }

hIKEv2IKESALocalCTAddress OBJECT-TYPE
    SYNTAX     IPAddress
    MAX-ACCESS read-only
    STATUS     current
    DESCRIPTION
        "(U//FOUO) The local HAIPE CT address associated with this IKEv2 IKE_SA.
         The address type value set (IPv4 address value, IPv6 address value) in
         this column should be consistent with the hIKEv2IKESAAddressType
         column."
    ::= { hIKEv2IKESADTableEntry 3 }

hIKEv2IKESARemoteCTAddress OBJECT-TYPE
    SYNTAX     IPAddress
    MAX-ACCESS read-only
    STATUS     current
    DESCRIPTION
        "(U//FOUO) The remote HAIPE CT address associated with this IKEv2
         IKE_SA.  The address type value set (IPv4 address value, IPv6  address
         value) in this column should be consistent with the
         hIKEv2IKESAAddressType column."
    ::= { hIKEv2IKESADTableEntry 4 }

hIKEv2IKESALocalPTAddress  OBJECT-TYPE
    SYNTAX     IPAddress
    MAX-ACCESS read-only
    STATUS     current
    DESCRIPTION
        "(U//FOUO) The local HAIPE PT address associated with this IKEv2 IKE_SA.
         The address type value set (IPv4 address value, IPv6 address value) in
         this column should be consistent with the hIKEv2IKESAAddressType
         column."
    ::= { hIKEv2IKESADTableEntry 5 }

hIKEv2IKESARemotePTAddress  OBJECT-TYPE
    SYNTAX     IPAddress
    MAX-ACCESS read-only
    STATUS     current
    DESCRIPTION
        "(U//FOUO) The remote HAIPE PT Address associated with this IKEv2
         IKE_SA.  The address type value set (IPv4 address value, IPv6 address
         value) in this column should be consistent with the
         hIKEv2IKESAAddressType column."
    ::= { hIKEv2IKESADTableEntry 6 }

hIKEv2IKESARemoteNATAddress OBJECT-TYPE
    SYNTAX     IPAddress
    MAX-ACCESS read-only
    STATUS     current
    DESCRIPTION
        "(U//FOUO) The remote Network Address Translation (NAT) address of the
         NAT device associated with a remote peer of this IKEv2 IKE_SA.  Note,
         this column is created and automatically populated by the HAIPE not
         fronted by the NAT, for the IKEv2 IKE_SA when a NAT device is detected
         via IKEv2.

         (U//FOUO) The address type value set (IPv4 address value, IPv6 address
         value) in this column should be consistent with the
         hIKEv2IKESAAddressType column."
    ::= { hIKEv2IKESADTableEntry 7 }

hIKEv2IKESARemoteNATDestPort  OBJECT-TYPE
    SYNTAX     PortNumber
    MAX-ACCESS read-only
    STATUS     current
    DESCRIPTION
        "(U//FOUO) The remote Destination Port of the Network Address
         Translation (NAT) device associated with the remote peer of this IKEv2
         IKE_SA.  Note, this column is created and automatically populated by
         the HAIPE not fronted by the NAT, for the IKEv2 IKE_SA when a NAT
         device is detected via IKEv2."
    ::= { hIKEv2IKESADTableEntry 8 }

hIKEv2IKESAInitiatorSPI  OBJECT-TYPE
    SYNTAX     OCTET STRING (SIZE(8))
    MAX-ACCESS read-only
    STATUS     current
    DESCRIPTION
        "(U//FOUO) The Initiator's Security Parameter Index (SPI) associated
         with this IKE_SA; the IKE_SA Initiator's SPI column value is determined
         by the Initiator of the IKE_SA_INIT Exchange or the CREATE_CHILD_SA
         Exchange (IKE_SA Rekey)."
    ::= { hIKEv2IKESADTableEntry 9 }

hIKEv2IKESAResponderSPI OBJECT-TYPE
    SYNTAX     OCTET STRING (SIZE(8))
    MAX-ACCESS read-only
    STATUS     current
    DESCRIPTION
        "(U//FOUO) The Responder's Security Parameter Index (SPI) associated
         with this IKE_SA; the IKE_SA Responder's SPI column value is determined
         by the Responder of the IKE_SA_INIT Exchange or the CREATE_CHILD_SA
         Exchange (IKE_SA Rekey)."
    ::= { hIKEv2IKESADTableEntry 10 }

hIKEv2IKESATransformSuite OBJECT-TYPE
    SYNTAX     HaipeIKEv2IKESATransformSuites
    MAX-ACCESS read-only
    STATUS     current
    DESCRIPTION
        "(U//FOUO) A set of cryptographic attributes respective to the
         established IKEv2 IKE_SA."
    ::= { hIKEv2IKESADTableEntry 11 }

hIKEv2IKESALivenessTestRate OBJECT-TYPE
    SYNTAX     Unsigned32
    MAX-ACCESS read-write
    STATUS     current
    DESCRIPTION
        "(U//FOUO) The setting that determines the rate (in seconds) at which
         Liveness Test request messages are transmitted on this IKEv2 IKE_SA.  A
         value of zero (decimal) indicates the disabled Liveness Test Setting,
         meaning that Liveness Test request messages will not be transmitted."
    ::= { hIKEv2IKESADTableEntry 12 }

hIKEv2IKESALivenessTestLimit OBJECT-TYPE
    SYNTAX     Unsigned32
    MAX-ACCESS read-write
    STATUS     current
    DESCRIPTION
        "(U//FOUO) Setting that determines the number of successive missed
         Liveness Test response messages that will trigger the HAIPE to mark
         this IKE_SAs and all of its parented Outbound CHILD_SAs as UNREACHABLE.
         A Liveness Test response message or any inbound traffic received on the
         IKE_SA or any parented Inbound CHILD_SA established with the remote
         HAIPE resets the internal Liveness Test successive missed counter to
         its initial state.  Note, this column must only exist when 
	 hIKEv2IKESALivenessTestRate is set to a non-zero value (decimal)."
    ::= { hIKEv2IKESADTableEntry 13 }

hIKEv2IKESAReachabilityStatus OBJECT-TYPE
    SYNTAX     TruthValue
    MAX-ACCESS read-only
    STATUS     current
    DESCRIPTION
        "(U//FOUO) The Reachability Status of this IKEv2 IKE_SA; the possible
         values are: true, false.   The value in this column is determined by
         the hIKEv2IKESALivenessTestRate column and the
         hIKEv2IKESALivenessTestLimit column; an IKEv2 IKE_SA is determined
         UNREACHABLE if the hIKEv2IKESALivenessTestLimit threshold is reached
         for the number of successive missed Liveness Test response messages.

         (U//FOUO) [true] If this column is set to true, this IKEv2 IKE_SA is
         REACHABLE.

         (U//FOUO) [false] If this column is set to false, this IKEv2 IKE_SA
         is UNREACHABLE."
    ::= { hIKEv2IKESADTableEntry 14 }

hIKEv2IKESARowStatus  OBJECT-TYPE
    SYNTAX     RowStatus
    MAX-ACCESS read-write
    STATUS     current
    DESCRIPTION
        "(U//FOUO) The status of the row, by which old entries may be edited or
         deleted from this table.

         (U//FOUO) At a minimum, implementations must support active and destroy
         management functions. Support for notInService, and notReady management
         functions is optional. Implementations must not support createAndWait and
         createAndGo management functions for this object."
    ::= { hIKEv2IKESADTableEntry 15 }

END
