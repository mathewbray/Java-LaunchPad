HAIPE-V040101-MIB DEFINITIONS ::= BEGIN
IMPORTS
    MODULE-IDENTITY                 FROM SNMPv2-SMI
    MODULE-COMPLIANCE, OBJECT-GROUP FROM SNMPv2-CONF
    haipev4ComplianceMIB            FROM HAIPE-V4-COMPLIANCE-MIB
    hDeviceVersTableCount, hFirmwareDwnldAdminStatus, hSystemUpTime, hFwDwnldServerTableLastChanged, hSanitizeDevice, hResetDevice, hSystemDate, hFwDwnldServerRowStatus, hFirmwareDwnldStatus, hZeroizeAllKeysAndAlgorithms, hStationIdentifier, hFwDwnldServerURI, hFwDwnldServerTableCount, hTFTPDesiredBlkSize, hObjectLastChanged, hTFTPDesiredTimeout, hFwDwnldServerSide, hDeviceVersTableLastChanged, hDvRowStatus
      FROM HAIPE-V4-MANAGEMENT-MIB

    hEstROHCParamTableCount, hEstROHCRowStatus, hEstROHCRepeatIR, hEstROHCTimeout, hEstROHCParamTableLastChanged, hEstROHCCompressionProfiles, hEstROHCFeedbackChannel, hEstROHCMAXCID
      FROM HAIPE-V4-ROHC-MIB

    hBMProfileRowStatus, hEstMRCBMValue, hBMProfileRRBMValue, hBMParamsProfileTableCount, hEstBMParamRowStatus, hEstRRBucketSize, hBMProfileRRTimer, hBMProfileMRCBMValue, hEstBMParamTableLastChanged, hEstRRTimer, hEstBMParamTableCount, hBMParamsProfileTableLastChanged, hEstRRBucketRate, hBMProfileRRBucketSize, hBMProfileRRBucketRate, hEstRRBMValue
      FROM HAIPE-V4-BANDWIDTH-MANAGEMENT-MIB

    hDefaultRouterTableCount, hIPv6RouterAdverHopLimit, hPrefixTableLastChanged, hMLDSupportMode, hIPv6IfaceTableLastChanged, hIPv6RouterAdverTableLastChanged, hIPv6IfaceIdentifier, hPrefixAutoAddrConfigFlag, hIPv6RouterAdverRowStatus, hCIDRRouteRowStatus, hPrefixValidLifetime, hCIDRRouteMetric, hIPv6IfaceSide, hAddressAssignTableCount, hCIDRRouteProtocol, hCIDRRouteTableLastChanged, hIPv6RouterAdverTableCount, hIPv6IfaceHopLimit, hPrefixOnLinkFlag, hIPv4IfaceNATTEnable, hIPv6RouterAdverConfigFlag, hIPv6IfaceAutoAddrConfig, hAddressAssignPrefixLength, hIPv6IfaceRouterSolicitSetting, hDefaultRouterTableLastChanged, hDefaultRouterPreference, hPrefixPreferredLifetime, hPrefixOrigin, hIPv6RouterAdverEnable, hIPv6RouterAdverReachableTime, hPrefixTableCount, hIPv6IfaceDAD, hCIDRRouteType, hIPv4IfaceTTL, hIPv4IfaceStatus, hIPv6IfaceStatus, hAddressAssignTableLastChanged, hIPv6RouterAdverMinInterval, hAddressAssignRowStatus, hIPv4IfaceSide, hIPv6RouterAdverMaxInterval, hCIDRRouteIfIndex, hIPv6IfaceTableCount, hIPv4IfaceTableLastChanged, hIPv6RouterAdverRetransTime, hIPv6IfaceMTU, hDefaultRouterLifetime, hIPv4IfaceICMPEnable, hIPv6RouterAdverMTU, hIPv4IfaceTableCount, hIPv6RouterAdverDefLifetime, hIGMPSupportMode, hIPv6IfaceICMPv6Enable, hIPv4IfaceMTU, hIPv6IfaceNATTEnable, hIPv6RouterAdverManagedFlag, hCIDRRouteTableCount
      FROM HAIPE-V4-NETWORKING-MIB

    hDPModuliBaseType, hFireFlyNationalShortTitle, hFireFlyClassification, hManSAKeyChainRowStatus, hDPModuliTableCount, hPrePlacedKeyLabel, hCRLTableCount, hPrePlacedKeyisAuthenticated, hPrePlacedKeyIBKTDisable, hManSAKeyChainTableLastChanged, hTAVersion, hDGSharedKeyTableLastChanged, hPKCNotAfter, hFireFlyPartitionCode, hDGSharedKeyClassification, hCRLRowStatus, hTAKeyIdentifier, hEKKeyIndex, hDGSharedKeyUsageType, hPrePlacedKeyTableLastChanged, hPKCType, hFireFlyLabel, hPrePlacedKeyRowStatus, hGenerateSharedKey, hTATableCount, hZeroizeAllKeys, hCRLTableLastChanged, hTAName, hDPModuliNationalID, hManSAKeyChainKeyIndex, hPKCFromPDE, hDPModuliID, hFireFlyMaterialType, hPKCIsCA, hDPModuliShortTitleName, hPKCClearanceClassList, hManSAKeyChainKeyEffectiveDate, hCRLVersion, hPKCTableLastChanged, hCRLNextUpdate, hDGSharedKeyShortTitle, hPKCVersion, hPKCSignature, hEKTableLastChanged, hTATableLastChanged, hEKRowStatus, hAPPKTATableCount, hDGSharedKeyEffectiveDate, hEKUniversalID, hDGSharedKeyTableCount, hManSAKeyChainTableCount, hPrePlacedKeyTableCount, hEKTableCount, hAPPKTATableLastChanged, hPKCNotBefore, hDGSharedKeyLabel, hPKCRowStatus, hFireFlyTableLastChanged, hPrePlacedKeyUsageType, hCRLFromPDE, hDGSharedKeySuite, hFireFlyRowStatus, hFireFlyTableCount, hPKCTableCount, hEKEffectiveDate, hFireFlyisTestKey, hDPModuliUserID, hCRLLastUpdate, hAPPKTAShortTitle, hPrePlacedKeyEffectiveDate, hDPModuliCOI, hPKCSubject, hDGSharedKeyMaterial, hFireFlyExpirationDate, hFireFlyKeyType, hDGSharedKeyRowStatus, hPrePlacedKeyClassification, hCRLThisUpdate, hTARowStatus, hEKType, hEKGroupName, hDPModuliSourceID, hDPModuliTableLastChanged, hDGSharedKeyOrigin, hDGSharedKeyPushToLoadedKeyTable
      FROM HAIPE-V4-KEY-INFORMATION-MIB

    hDMDKMcastQueryTimeout, hDMDKIBKTRequestTimeout, hDMDKInfoGroupLeaderCTIPAddress, hDMDKEnableGroupLeadership, hDMDKServerPTIPAddress, hDMDKInfoGroupLeaderIPAddrType, hDMDKInfoMcastPTIPAddressEnd, hDMDKServerPTPort, hDMDKServerTableCount, hDMDKInfoMcastIPAddrType, hDMDKMcastRegistrationTimeout, hDMDKInfoManualSAIndex, hDMDKInformationTableLastChanged, hDMDKMcastQueryRetries, hDMDKInfoMcastCTIPAddress, hDMDKServerRowStatus, hDMDKInfoGroupLeaderPTIPAddress, hDMDKServerTableLastChanged, hDMDKIBKTRequestRetries, hDMDKInfoMcastPTIPAddressStart, hDMDKInfoRowStatus, hDMDKInformationTableCount, hDMDKMcastRegistrationRetries, hDMDKServerPTIPAddrType
      FROM HAIPE-V4-DMDK-MIB

    hRIPTableLastChanged, hIMPEPDTableCount, hLegacyDeliveryRowStatus, hIMPEPDTableLastChanged, hIMPEPDRowStatus, hIMPEPDifTableCount, hIMPEPDifRowStatus, hPEPTTableCount, hIMPEPDifPTSubIdentifier, hRIPLEPTLifetimeOffset , hPEPTPrefixLifetime, hPEPTNATAddress, hGDCRegistrationTimeout, hGDCSolicitDelivDestPTPort, hIMPEPDifPTtoInterfaceMapping, hGDCSolicitDelivRowStatus, hPEPTRowStatus, hIMPEPDifTableLastChanged, hGDCRegistrationTableLastChanged, hRIPDefaultRouteMetric, hLegacyDeliveryTableCount, hRIPDefaultRouteAdMode, hGDCRegistrationTableCount, hLearnedLocalPrefixAdminCost, hLEPTTableCount, hGDCRegistrationRowStatus, hGDCReceptionRowStatus, hGDCSolicitDelivRetryCount, hLegacyDeliveryTableLastChanged, hPEPTAdminCost, hRIPAdvertisementRouteTag, hRIPAdvertisementRouteMetric, hGDCRegistrationRetryCount, hIMPEPDifCTSubIdentifier, hLEPTAdminCost, hRIPAdvertiseRoutes, hGDCSolicitDelivTimeout, hPEPTNATPort, hIMPEPDifCTtoInterfaceMapping, hLEPTTableLastChanged, hGDCSolicitDelivTableLastChanged, hRIPRowStatus, hRIPSpeakerSetting, hIMPEPDifSegmentedCore, hGDCSolicitDelivDestPTAddrType, hLEPTRowStatus, hRIPTableCount, hRIPListenerSetting, hGDCReceptionTableCount, hGDCSolicitDelivDestPTAddress, hLEPTRowLifetime, hPEPTRowConfigMethod, hPEPTTableLastChanged, hLEPTRowConfigMethod, hGDCReceptionTableLastChanged, hGDCSolicitDelivTableCount
      FROM HAIPE-V4-DISCOVERY-MIB

    hIKEv1ProfileDSCPSetting, hIKEv2IKESAReachabilityStatus, hIKEv2IKESADTableLastChanged, hIKEv1NPProfileTableCount, hIKEv2CHLDNPPRowStatus, hIKEv1SAPHRDRate, hIKEv2CHDNPProfTableLastChanged, hIKEv1SALocalPTAddress, hManualSASPI, hEstLocalTSPortBegin, hIKEv1SAEstTrafficSelectorName, hIKEv2CHLDProfileEncapMode, hPolicyRemoteTSPortBegin, hIKEv1NtwkParamsProfileRowStatus, hIKEv2IKENPPLivenessTestRate, hIKEv2IKESARemoteCTAddress, hIKEv1ProfileTransformSuite, hIKEv2CHILDSALocalPTAddress, hTFCConfigPacketSize, hEstLocalTSTableLastChanged, hIKEv2IKESARemoteNATAddress, hPolicyRemoteTSPTAddrEnd, hManualSAProfileTableCount, hIKEv2CHILDSADSCPClassifiers, hIKEv2CHDSAtProfTableLastChanged, hEstRemoteTSPortEnd, hIKEv2CHILDSATFCConfigName, hPolicyRemoteTSTableCount, hEstLocalTSPortEnd, hPolicyLocalTSPTAddrType, hIKEv1ProfilePHRDLimit, hIKEv2CHILDSARemoteCTAddress, hEstRemoteTSProtocol, hIKEv2CHILDSACTDSCPValue, hEstRemoteTSTableLastChanged, hManualSASPIChainTableCount, hIKEv2CHILDSARemoteNATAddress, hPolicyLocalTSTableLastChanged, hIKEv2CHDNPProfTableCount, hManualSADSCPClassifier, hIKEv1SADSCPClassifiers, hIKEv2CHILDSATransformSuite, hPolicyRemoteTSPTAddrType, hManualSAECNSetting, hIKEv2CHILDSADFBitSetting, hIKEv1SAProfileTableCount, hIKEv2CHLDNPPFlowLabelSetting, hIKEv2IKESALocalCTAddress, hIKEv2CHLDProfileNtwkParamsRef, hManualSARemoteCTAddress, hIKEv1ProfilePHRDRate, hEstRemoteTSPTAddrType, hIKEv1ProfilePDUNEnabled, hPolicyLocalTSPortBegin, hIKEv2CHILDSAEstBMParamsIndex, hIKEv2CHILDSADTableLastChanged, hIKEv2CHILDSACTDSCPSetting, hIKEv1SARowStatus, hIKEv2CHLDNPPTFCConfigName, hManualSAProfileTableLastChanged, hIKEv2IKESAInitiatorSPI, hTFCConfigTransmissionRate, hEstLocalTSTableCount, hIKEv1ProfileDSCPValue, hIKEv1SARemoteCTAddress, hPolicyRemoteTSTableLastChanged, hIKEv2IKENPProfTableLastChanged, hPolicyRuleUseBM, hManualSAStartTime, hManualSecAttrsProfileRowStatus, hManualSADirection, hIKEv2CHLDNPPDSCPValue, hIKEv2CHILDSAECNSetting, hIKEv1ProfileNtwkParamsRef, hIKEv1SADFBitSetting, hIKEv1ProfileFlowLabelValue, hIKEv2CHILDSAFlowLabelSetting, hIKEv2CHILDSARemoteNATDestPort, hIKEv2CHLDNPPFlowLabelValue, hIKEv2CHILDSALocalCTAddress, hIKEv1SAProfileTableLastChanged, hIKEv2CHLDNPPDFBitSetting, hEstRemoteTSPTAddrBegin, hPolicyRuleTrafficSelectorName, hTFCConfigRowStatus, hTFCConfigTableLastChanged, hIKEv1SecAttrsProfileRowStatus, hManualSAKeyChainName, hManualSACTFlowLabelValue, hIKEv2CHLDProfileTransformSuite, hManualSAFlowLabelSetting, hManualSAPDUNEnabled, hIKEv1NPProfileTableLastChanged, hEstLocalTSPTAddrType, hIKEv2IKESATransformSuite, hIKEv1SADirection, hIKEv2CHILDSASPI, hManualSADFBitSetting, hManualSAReachabilityStatus, hManualSARowStatus, hIKEv2IKESADTableCount, hManualSAPHRDLimit, hIKEv2IKESALivenessTestLimit, hPolicyRuleTableCount, hIKEv1SAECNSetting, hManualSATransformSuite, hIKEv1SAAddressType, hManualSADTableLastChanged, useIKEVersion, hIKEv1ProfileECNSetting, hIKEv2CHLDNPIKENtwkParamsRef, hIKEv2IKESAResponderSPI, hIKEv1SAPDUNEnabled, hPolicyLocalTSPTAddrBegin, hEstLocalTSPTAddrEnd, hPolicyLocalTSRowStatus, hPolicyRuleSecAttrsProfileName, hManualSAEstBMParamsIndex, hManualSAAddressType, hIKEv2CHILDSARowStatus, hIKEv2CHILDSAReachabilityStatus, hManualSAPHRDRate, hManualSALocalPTAddress, hIKEv2IKESALivenessTestRate, hEstLocalTSProtocol, hIKEv2CHLDNPPECNSetting, hPolicyRuleTableLastChanged, hIKEv2CHDSAtProfTableCount, hIKEv2CHILDSAPDUNEnabled, hIKEv1SAPHRDLimit, hIKEv2CHILDSAEstTrafficSelName, hTFCConfigTableCount, hIKEv1SADTableLastChanged, hIKEv2IKENPProfTableCount, hManualSADTableCount, hIKEv2IKESARemotePTAddress, hIKEv2CHLDSecAttrsProfRowStatus, hPolicyRuleAction, hIKEv2CHLDNPPPDUNEnabled, hManualSARemotePTAddress, hManualSACTDSCPSetting, hManualSASPIChainReference, hEstRemoteTSTableCount, hManualSAEstROHCParamsIndex, hIKEv1ProfileFlowLabelSetting, hIKEv2CHILDSADirection, hIKEv2CHLDNPPDSCPSetting, hIKEv2IKESARowStatus, hIKEv2CHILDSAEncapsulationMode, hIKEv2CHILDSAIKESAIndex, hIKEv1SAReachabilityStatus, hIKEv2CHILDSACTFlowLabelValue, hIKEv2CHILDSARemotePTAddress, hManualSACtlPlaneSignalEnabled, hPolicyRuleDSCPClassifier, hManualSAEstTrafficSelectorName, hPolicyRuleUseROHC, hIKEv2IKESARemoteNATDestPort, hManualSASPIChainRowStatus, hManualSATFCConfigName, hPolicyRemoteTSRowStatus, hIKEv2IKESALocalPTAddress, hPolicyRemoteTSProtocol, hPolicyRuleRowStatus, hIKEv2IKESAAddressType, hIKEv1SADTableCount, hIKEv2IKENPPLivenessTestLimit, hIKEv2CHILDSAEstROHCParamsIndex, hManualSACTDSCPValue, hIKEv1SACTFlowLabelValue, hIKEv1SALocalCTAddress, hManualSALocalCTAddress, hIKEv1SARemotePTAddress, hTFCConfigPacketSizeList, hEstRemoteTSPTAddrEnd, hIKEv1SAFlowLabelSetting, hIKEv1SACTDSCPSetting, hIKEv1ProfileDFBitSetting, hPolicyRemoteTSPTAddrBegin, hIKEv1SARemoteNATDestinationPort, hPolicyLocalTSPTAddrEnd, hTFCConfigPacketSizeType, hPolicyLocalTSTableCount, hEstLocalTSPTAddrBegin, hEstRemoteTSPortBegin, hManualProfileTransformSuite, hIKEv1ProfileTFCConfigName, hIKEv1SATFCConfigName, hManualSASPIChainTableLastChanged, hEstLocalTSRowStatus, hIKEv1SATransformSuite, hEstRemoteTSRowStatus, hIKEv1SASPI, hIKEv2IKENPPRowStatus, hIKEv1SARemoteNATAddress, hIKEv2CHILDSAAddressType, hIKEv2CHILDSADTableCount, hIKEv1SACTDSCPValue, hPolicyLocalTSPortEnd, hPolicyRemoteTSPortEnd, hPolicyLocalTSProtocol
      FROM HAIPE-V4-TRAFFIC-PROTECTION-MIB

    hPDETableLastChanged, hPDEMappingTableCount, hPDERequestStatus, hPDERetryMaxAttempts, hPDETLSEstablishmentRetryDelay, hPDEFromPAL, hPDEMappingRowStatus, hPDEMappingTableLastChanged, hPDEType, hPDEMappingPTIPAddress, hPDEURI, hPDERetryDelay, hPDEMappingPTIPAddressType, hPDETableCount, hPDETLSEstablishmentMaxAttempts, hPDERequest, hPDEMappingHostname, hPDERowStatus
      FROM HAIPE-V4-KMI-MIB

    hOOBKTClientsTableCount, hOOBKTClientPushKey, hLoadedKeyTableLastChanged, hIBKTClientsTableCount, hIBKTClientsTableLastChanged, hOOBKTKeyFileTableLastChanged, hLoadedKeyClassification, hKTAuthCtrlsTableCount, hOOBKTClientsTableLastChanged, hKTAuthCtrlsTableLastChanged, hKTAuthCtrlsAddressType, hIBKTClientsTransferRetries, hOOBKTKeyFileRowStatus, hIBKTClientsManSAChainName, hIBKTClientsTransferTime, hOOBKTAddress, hOOBKTAddressType, hKTAuthCtrlsAddress, hIBKTClientsLoadedKey, hOOBKTKeyFileTableCount, hLoadedKeyAction, hKTAuthCtrlsRowStatus, hLoadedKeyTableCount, hIBKTClientsEffectiveDate, hLoadedKeyText, hOOBKTKeyFiles, hIBKTClientsRowStatus, hOOBKTKeyFileLoadedKey, hOOBKTClientRowStatus, hLoadedKeyUse, hLoadedKeyRowStatus, hOOBKTClientPath, hIBKTClientsTransRetryPeriod
      FROM HAIPE-V4-KEY-TRANSFER-MIB

;

haipeV040101ComplianceMIB MODULE-IDENTITY
    LAST-UPDATED "201112161600Z"
    ORGANIZATION "HAIPE PO"
    CONTACT-INFO
         "(U//FOUO) Not Available"
    DESCRIPTION
        "(U//FOUO) This MIB defines compliance statements which
        define the levels of conformance required by the various HAIPE
        Version 4.1.1 IS documents.

        (U//FOUO) This MIB is not entirely conformant to SMIv2 parsing
        rules. Specifically, object groups are only allowed to
        reference objects defined in the local MIB, and in this file
        we're importing a large number of objects from other MIBs
        rather than importing their particular object groups."
    ::= { haipev4ComplianceMIB 4 1 1 }

haipeV040101Conformance OBJECT IDENTIFIER ::= { haipeV040101ComplianceMIB 1 }
haipeV040101Groups      OBJECT IDENTIFIER ::= { haipeV040101ComplianceMIB 2 }

       

--
-- Objects referenced by the Generic Discovery Client and Reachability IS
--
hGenericDiscoveryClientANDReachabilityCapabilityGroup OBJECT-GROUP
    OBJECTS {
                hRIPLEPTLifetimeOffset 
            }
    STATUS    current
    DESCRIPTION
        "(U//FUOUO) Objects for the Generic Discovery Client and Reachability document(s).
         This group is only relevant if the extension is supported"
    ::= { haipeV040101Groups 1 }

--
-- Conformance levels required by the Generic Discovery Client and Reachability IS
--
hGenericDiscoveryClientANDReachabilityCapabilityCompliance MODULE-COMPLIANCE
    STATUS    current
    DESCRIPTION
        "(U//FOUO) Compliance levels for objects required by the
         Generic Discovery Client and Reachability document(s)."
    MODULE -- this module
    MANDATORY-GROUPS { hGenericDiscoveryClientANDReachabilityCapabilityGroup }

    OBJECT     hRIPLEPTLifetimeOffset 
    MIN-ACCESS read-create
    DESCRIPTION
        "(U//FOUO) Implementation of this object can be as low
         as read-create depending on which
         IS Objective or MIB desired requirements are
         not being met by the implementation."
::= { haipeV040101Conformance 1 }

--
-- Objects referenced by the Core IS
--
hCoreCapabilityGroup OBJECT-GROUP
    OBJECTS {
                hManualSADTableCount,
                hCIDRRouteTableLastChanged,
                hManualSARowStatus,
                hPolicyRemoteTSRowStatus,
                hIPv6IfaceRouterSolicitSetting,
                hIPv6IfaceTableCount,
                hIPv4IfaceTableLastChanged,
                hDefaultRouterTableCount,
                hPolicyLocalTSRowStatus,
                hIPv6IfaceDAD,
                hManualSADFBitSetting,
                hIPv4IfaceMTU,
                hManSAKeyChainKeyIndex,
                hIPv6IfaceStatus,
                hPrePlacedKeyClassification,
                hIPv6IfaceMTU,
                hManualSASPI,
                hEstLocalTSPortBegin,
                hIPv4IfaceICMPEnable,
                hManualSACtlPlaneSignalEnabled,
                hPolicyRuleDSCPClassifier,
                hPolicyRemoteTSPortBegin,
                hLEPTRowStatus,
                hManSAKeyChainRowStatus,
                hManualSAPHRDLimit,
                hTFCConfigTransmissionRate,
                hManualSAEstTrafficSelectorName,
                hCIDRRouteType,
                hPolicyRuleTableCount,
                hManSAKeyChainTableCount,
                hManualSATFCConfigName,
                hIPv6IfaceHopLimit,
                hSystemDate,
                hEstLocalTSTableLastChanged,
                hManualSASPIChainRowStatus,
                hManualSATransformSuite,
                hPrePlacedKeyisAuthenticated,
                hPrePlacedKeyIBKTDisable,
                hPolicyRemoteTSProtocol,
                hPolicyRemoteTSPTAddrEnd,
                hEstLocalTSTableCount,
                hPrefixOnLinkFlag,
                hTFCConfigPacketSize,
                hManualSAProfileTableCount,
                hEstLocalTSPTAddrBegin,
                hIPv4IfaceSide,
                hPolicyRuleRowStatus,
                hEstLocalTSRowStatus,
                hManSAKeyChainTableLastChanged,
                hManualSADTableLastChanged,
                hPolicyRemoteTSPTAddrBegin,
                hLEPTTableLastChanged,
                hDvRowStatus,
                hPrePlacedKeyTableCount,
                hManualSACTFlowLabelValue,
                hKTAuthCtrlsRowStatus,
                hManSAKeyChainKeyEffectiveDate,
                hEstRemoteTSPortEnd,
                hLEPTAdminCost,
                hPolicyRemoteTSTableLastChanged,
                hPrefixTableLastChanged,
                hPolicyRemoteTSTableCount,
                hEstLocalTSPortEnd,
                hLEPTTableCount,
                hTFCConfigPacketSizeList,
                hIPv6IfaceAutoAddrConfig,
                hIPv4IfaceTableCount,
                hEstRemoteTSPTAddrEnd,
                hEstRemoteTSRowStatus,
                hPolicyLocalTSPTAddrType,
                hIPv4IfaceStatus,
                hAddressAssignPrefixLength,
                hPrePlacedKeyUsageType,
                hIPv6IfaceTableLastChanged,
                hEstLocalTSPTAddrEnd,
                hSystemUpTime,
                hDeviceVersTableCount,
                hIPv4IfaceTTL,
                hManualSecAttrsProfileRowStatus,
                hPolicyRuleSecAttrsProfileName,
                hIPv6IfaceIdentifier,
                hPEPTTableCount,
                hPrefixAutoAddrConfigFlag,
                hManualSADirection,
                hDefaultRouterTableLastChanged,
                hDefaultRouterLifetime,
                hObjectLastChanged,
                hManualSAAddressType,
                hEstRemoteTSProtocol,
                hEstRemoteTSTableLastChanged,
                hDeviceVersTableLastChanged,
                hManualSASPIChainTableCount,
                hManualSAPHRDRate,
                hLEPTRowLifetime,
                hKTAuthCtrlsTableLastChanged,
                hPolicyLocalTSTableLastChanged,
                hIPv6IfaceICMPv6Enable,
                hPolicyLocalTSProtocol,
                hManualSALocalPTAddress,
                hPolicyLocalTSPTAddrEnd,
                hTFCConfigPacketSizeType,
                hCIDRRouteRowStatus,
                hPolicyLocalTSTableCount,
                hPrefixValidLifetime,
                hEstLocalTSProtocol,
                hPrePlacedKeyTableLastChanged,
                hPolicyRuleTableLastChanged,
                hEstRemoteTSPortBegin,
                hPEPTRowConfigMethod,
                hAddressAssignTableLastChanged,
                hManualSAReachabilityStatus,
                hPEPTAdminCost,
                hKTAuthCtrlsTableCount,
                hManualProfileTransformSuite,
                hPEPTTableLastChanged,
                hManualSASPIChainTableLastChanged,
                hPolicyRemoteTSPTAddrType,
                hCIDRRouteMetric,
                hPrePlacedKeyRowStatus,
                hAddressAssignRowStatus,
                hTFCConfigTableCount,
                hPolicyLocalTSPTAddrBegin,
                hLEPTRowConfigMethod,
                hManualSADSCPClassifier,
                hEstRemoteTSPTAddrBegin,
                hPrefixPreferredLifetime,
                hPrefixOrigin,
                hKTAuthCtrlsAddress,
                hPolicyRuleTrafficSelectorName,
                hCIDRRouteIfIndex,
                hManualSARemoteCTAddress,
                hTFCConfigRowStatus,
                hTFCConfigTableLastChanged,
                hKTAuthCtrlsAddressType,
                hPolicyRuleAction,
                hManualSAKeyChainName,
                hPEPTRowStatus,
                hIPv6IfaceSide,
                hPolicyLocalTSPortEnd,
                hEstRemoteTSPTAddrType,
                hManualSALocalCTAddress,
                hManualSAStartTime,
                hPolicyRemoteTSPortEnd,
                hManualSARemotePTAddress,
                hAddressAssignTableCount,
                hPolicyLocalTSPortBegin,
                hManualSAFlowLabelSetting,
                hDefaultRouterPreference,
                hManualSAProfileTableLastChanged,
                hEstLocalTSPTAddrType,
                hPrefixTableCount,
                hCIDRRouteProtocol,
                hManualSASPIChainReference,
                hEstRemoteTSTableCount,
                hCIDRRouteTableCount,
                hStationIdentifier
            }
    STATUS    current
    DESCRIPTION
        "(U//FUOUO) Objects for the Core document(s).
         This group is only relevant if both extensions are supported"
    ::= { haipeV040101Groups 2 }

--
-- Conformance levels required by the Core IS
--
hCoreCapabilityCompliance MODULE-COMPLIANCE
    STATUS    current
    DESCRIPTION
        "(U//FOUO) Compliance levels for objects required by the
         Core document(s)."
    MODULE -- this module
    MANDATORY-GROUPS { hCoreCapabilityGroup }

    OBJECT     hManualSADTableCount
    MIN-ACCESS read-only
    DESCRIPTION
        "(U//FOUO) Implementation of this object can be as low
         as read-only depending on which
         IS Objective or MIB desired requirements are
         not being met by the implementation."

    OBJECT     hCIDRRouteTableLastChanged
    MIN-ACCESS read-only
    DESCRIPTION
        "(U//FOUO) Implementation of this object can be as low
         as read-only depending on which
         IS Objective or MIB desired requirements are
         not being met by the implementation."

    OBJECT     hManualSARowStatus
    MIN-ACCESS read-create
    DESCRIPTION
        "(U//FOUO) Implementation of this object can be as low
         as read-create depending on which
         IS Objective or MIB desired requirements are
         not being met by the implementation."

    OBJECT     hPolicyRemoteTSRowStatus
    MIN-ACCESS read-create
    DESCRIPTION
        "(U//FOUO) Implementation of this object can be as low
         as read-create depending on which
         IS Objective or MIB desired requirements are
         not being met by the implementation."

    OBJECT     hIPv6IfaceRouterSolicitSetting
    MIN-ACCESS read-write
    DESCRIPTION
        "(U//FOUO) Implementation of this object can be as low
         as read-write depending on which
         IS Objective or MIB desired requirements are
         not being met by the implementation."

    OBJECT     hIPv6IfaceTableCount
    MIN-ACCESS read-only
    DESCRIPTION
        "(U//FOUO) Implementation of this object can be as low
         as read-only depending on which
         IS Objective or MIB desired requirements are
         not being met by the implementation."

    OBJECT     hIPv4IfaceTableLastChanged
    MIN-ACCESS read-only
    DESCRIPTION
        "(U//FOUO) Implementation of this object can be as low
         as read-only depending on which
         IS Objective or MIB desired requirements are
         not being met by the implementation."

    OBJECT     hDefaultRouterTableCount
    MIN-ACCESS read-only
    DESCRIPTION
        "(U//FOUO) Implementation of this object can be as low
         as read-only depending on which
         IS Objective or MIB desired requirements are
         not being met by the implementation."

    OBJECT     hPolicyLocalTSRowStatus
    MIN-ACCESS read-create
    DESCRIPTION
        "(U//FOUO) Implementation of this object can be as low
         as read-create depending on which
         IS Objective or MIB desired requirements are
         not being met by the implementation."

    OBJECT     hIPv6IfaceDAD
    MIN-ACCESS read-write
    DESCRIPTION
        "(U//FOUO) Implementation of this object can be as low
         as read-write depending on which
         IS Objective or MIB desired requirements are
         not being met by the implementation."

    OBJECT     hManualSADFBitSetting
    MIN-ACCESS read-create
    DESCRIPTION
        "(U//FOUO) Implementation of this object can be as low
         as read-create depending on which
         IS Objective or MIB desired requirements are
         not being met by the implementation."

    OBJECT     hIPv4IfaceMTU
    MIN-ACCESS read-write
    DESCRIPTION
        "(U//FOUO) Implementation of this object can be as low
         as read-write depending on which
         IS Objective or MIB desired requirements are
         not being met by the implementation."

    OBJECT     hManSAKeyChainKeyIndex
    MIN-ACCESS read-create
    DESCRIPTION
        "(U//FOUO) Implementation of this object can be as low
         as read-create depending on which
         IS Objective or MIB desired requirements are
         not being met by the implementation."

    OBJECT     hIPv6IfaceStatus
    MIN-ACCESS read-write
    DESCRIPTION
        "(U//FOUO) Implementation of this object can be as low
         as read-write depending on which
         IS Objective or MIB desired requirements are
         not being met by the implementation."

    OBJECT     hPrePlacedKeyClassification
    MIN-ACCESS read-only
    DESCRIPTION
        "(U//FOUO) Implementation of this object can be as low
         as read-only depending on which
         IS Objective or MIB desired requirements are
         not being met by the implementation."

    OBJECT     hIPv6IfaceMTU
    MIN-ACCESS read-write
    DESCRIPTION
        "(U//FOUO) Implementation of this object can be as low
         as read-write depending on which
         IS Objective or MIB desired requirements are
         not being met by the implementation."

    OBJECT     hManualSASPI
    MIN-ACCESS read-create
    DESCRIPTION
        "(U//FOUO) Implementation of this object can be as low
         as read-create depending on which
         IS Objective or MIB desired requirements are
         not being met by the implementation."

    OBJECT     hEstLocalTSPortBegin
    MIN-ACCESS read-create
    DESCRIPTION
        "(U//FOUO) Implementation of this object can be as low
         as read-create depending on which
         IS Objective or MIB desired requirements are
         not being met by the implementation."

    OBJECT     hIPv4IfaceICMPEnable
    MIN-ACCESS read-write
    DESCRIPTION
        "(U//FOUO) Implementation of this object can be as low
         as read-write depending on which
         IS Objective or MIB desired requirements are
         not being met by the implementation."

    OBJECT     hManualSACtlPlaneSignalEnabled
    MIN-ACCESS read-create
    DESCRIPTION
        "(U//FOUO) Implementation of this object can be as low
         as read-create depending on which
         IS Objective or MIB desired requirements are
         not being met by the implementation."

    OBJECT     hPolicyRuleDSCPClassifier
    MIN-ACCESS read-create
    DESCRIPTION
        "(U//FOUO) Implementation of this object can be as low
         as read-create depending on which
         IS Objective or MIB desired requirements are
         not being met by the implementation."

    OBJECT     hPolicyRemoteTSPortBegin
    MIN-ACCESS read-create
    DESCRIPTION
        "(U//FOUO) Implementation of this object can be as low
         as read-create depending on which
         IS Objective or MIB desired requirements are
         not being met by the implementation."

    OBJECT     hLEPTRowStatus
    MIN-ACCESS read-create
    DESCRIPTION
        "(U//FOUO) Implementation of this object can be as low
         as read-create depending on which
         IS Objective or MIB desired requirements are
         not being met by the implementation."

    OBJECT     hManSAKeyChainRowStatus
    MIN-ACCESS read-create
    DESCRIPTION
        "(U//FOUO) Implementation of this object can be as low
         as read-create depending on which
         IS Objective or MIB desired requirements are
         not being met by the implementation."

    OBJECT     hManualSAPHRDLimit
    MIN-ACCESS read-create
    DESCRIPTION
        "(U//FOUO) Implementation of this object can be as low
         as read-create depending on which
         IS Objective or MIB desired requirements are
         not being met by the implementation."

    OBJECT     hTFCConfigTransmissionRate
    MIN-ACCESS read-create
    DESCRIPTION
        "(U//FOUO) Implementation of this object can be as low
         as read-create depending on which
         IS Objective or MIB desired requirements are
         not being met by the implementation."

    OBJECT     hManualSAEstTrafficSelectorName
    MIN-ACCESS read-create
    DESCRIPTION
        "(U//FOUO) Implementation of this object can be as low
         as read-create depending on which
         IS Objective or MIB desired requirements are
         not being met by the implementation."

    OBJECT     hCIDRRouteType
    MIN-ACCESS read-create
    DESCRIPTION
        "(U//FOUO) Implementation of this object can be as low
         as read-create depending on which
         IS Objective or MIB desired requirements are
         not being met by the implementation."

    OBJECT     hPolicyRuleTableCount
    MIN-ACCESS read-only
    DESCRIPTION
        "(U//FOUO) Implementation of this object can be as low
         as read-only depending on which
         IS Objective or MIB desired requirements are
         not being met by the implementation."

    OBJECT     hManSAKeyChainTableCount
    MIN-ACCESS read-only
    DESCRIPTION
        "(U//FOUO) Implementation of this object can be as low
         as read-only depending on which
         IS Objective or MIB desired requirements are
         not being met by the implementation."

    OBJECT     hManualSATFCConfigName
    MIN-ACCESS read-create
    DESCRIPTION
        "(U//FOUO) Implementation of this object can be as low
         as read-create depending on which
         IS Objective or MIB desired requirements are
         not being met by the implementation."

    OBJECT     hIPv6IfaceHopLimit
    MIN-ACCESS read-write
    DESCRIPTION
        "(U//FOUO) Implementation of this object can be as low
         as read-write depending on which
         IS Objective or MIB desired requirements are
         not being met by the implementation."

    OBJECT     hSystemDate
    MIN-ACCESS read-write
    DESCRIPTION
        "(U//FOUO) Implementation of this object can be as low
         as read-write depending on which
         IS Objective or MIB desired requirements are
         not being met by the implementation."

    OBJECT     hEstLocalTSTableLastChanged
    MIN-ACCESS read-only
    DESCRIPTION
        "(U//FOUO) Implementation of this object can be as low
         as read-only depending on which
         IS Objective or MIB desired requirements are
         not being met by the implementation."

    OBJECT     hManualSASPIChainRowStatus
    MIN-ACCESS read-create
    DESCRIPTION
        "(U//FOUO) Implementation of this object can be as low
         as read-create depending on which
         IS Objective or MIB desired requirements are
         not being met by the implementation."

    OBJECT     hManualSATransformSuite
    MIN-ACCESS read-create
    DESCRIPTION
        "(U//FOUO) Implementation of this object can be as low
         as read-create depending on which
         IS Objective or MIB desired requirements are
         not being met by the implementation."

    OBJECT     hPrePlacedKeyisAuthenticated
    MIN-ACCESS read-only
    DESCRIPTION
        "(U//FOUO) Implementation of this object can be as low
         as read-only depending on which
         IS Objective or MIB desired requirements are
         not being met by the implementation."

    OBJECT     hPrePlacedKeyIBKTDisable
    MIN-ACCESS read-write
    DESCRIPTION
        "(U//FOUO) Implementation of this object can be as low
         as read-write depending on which
         IS Objective or MIB desired requirements are
         not being met by the implementation."

    OBJECT     hPolicyRemoteTSProtocol
    MIN-ACCESS read-create
    DESCRIPTION
        "(U//FOUO) Implementation of this object can be as low
         as read-create depending on which
         IS Objective or MIB desired requirements are
         not being met by the implementation."

    OBJECT     hPolicyRemoteTSPTAddrEnd
    MIN-ACCESS read-create
    DESCRIPTION
        "(U//FOUO) Implementation of this object can be as low
         as read-create depending on which
         IS Objective or MIB desired requirements are
         not being met by the implementation."

    OBJECT     hEstLocalTSTableCount
    MIN-ACCESS read-only
    DESCRIPTION
        "(U//FOUO) Implementation of this object can be as low
         as read-only depending on which
         IS Objective or MIB desired requirements are
         not being met by the implementation."

    OBJECT     hPrefixOnLinkFlag
    MIN-ACCESS read-only
    DESCRIPTION
        "(U//FOUO) Implementation of this object can be as low
         as read-only depending on which
         IS Objective or MIB desired requirements are
         not being met by the implementation."

    OBJECT     hTFCConfigPacketSize
    MIN-ACCESS read-create
    DESCRIPTION
        "(U//FOUO) Implementation of this object can be as low
         as read-create depending on which
         IS Objective or MIB desired requirements are
         not being met by the implementation."

    OBJECT     hManualSAProfileTableCount
    MIN-ACCESS read-only
    DESCRIPTION
        "(U//FOUO) Implementation of this object can be as low
         as read-only depending on which
         IS Objective or MIB desired requirements are
         not being met by the implementation."

    OBJECT     hEstLocalTSPTAddrBegin
    MIN-ACCESS read-create
    DESCRIPTION
        "(U//FOUO) Implementation of this object can be as low
         as read-create depending on which
         IS Objective or MIB desired requirements are
         not being met by the implementation."

    OBJECT     hIPv4IfaceSide
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hEstLocalTSRowStatus
    MIN-ACCESS read-create
    DESCRIPTION
        "(U//FOUO) Implementation of this object can be as low
         as read-create depending on which
         IS Objective or MIB desired requirements are
         not being met by the implementation."

    OBJECT     hManSAKeyChainTableLastChanged
    MIN-ACCESS read-only
    DESCRIPTION
        "(U//FOUO) Implementation of this object can be as low
         as read-only depending on which
         IS Objective or MIB desired requirements are
         not being met by the implementation."

    OBJECT     hManualSADTableLastChanged
    MIN-ACCESS read-only
    DESCRIPTION
        "(U//FOUO) Implementation of this object can be as low
         as read-only depending on which
         IS Objective or MIB desired requirements are
         not being met by the implementation."

    OBJECT     hPolicyRemoteTSPTAddrBegin
    MIN-ACCESS read-create
    DESCRIPTION
        "(U//FOUO) Implementation of this object can be as low
         as read-create depending on which
         IS Objective or MIB desired requirements are
         not being met by the implementation."

    OBJECT     hLEPTTableLastChanged
    MIN-ACCESS read-only
    DESCRIPTION
        "(U//FOUO) Implementation of this object can be as low
         as read-only depending on which
         IS Objective or MIB desired requirements are
         not being met by the implementation."

    OBJECT     hDvRowStatus
    MIN-ACCESS read-only
    DESCRIPTION
        "(U//FOUO) Implementation of this object can be as low
         as read-only depending on which
         IS Objective or MIB desired requirements are
         not being met by the implementation."

    OBJECT     hPrePlacedKeyTableCount
    MIN-ACCESS read-only
    DESCRIPTION
        "(U//FOUO) Implementation of this object can be as low
         as read-only depending on which
         IS Objective or MIB desired requirements are
         not being met by the implementation."

    OBJECT     hManualSACTFlowLabelValue
    MIN-ACCESS read-create
    DESCRIPTION
        "(U//FOUO) Implementation of this object can be as low
         as read-create depending on which
         IS Objective or MIB desired requirements are
         not being met by the implementation."

    OBJECT     hKTAuthCtrlsRowStatus
    MIN-ACCESS read-create
    DESCRIPTION
        "(U//FOUO) Implementation of this object can be as low
         as read-create depending on which
         IS Objective or MIB desired requirements are
         not being met by the implementation."

    OBJECT     hManSAKeyChainKeyEffectiveDate
    MIN-ACCESS read-create
    DESCRIPTION
        "(U//FOUO) Implementation of this object can be as low
         as read-create depending on which
         IS Objective or MIB desired requirements are
         not being met by the implementation."

    OBJECT     hEstRemoteTSPortEnd
    MIN-ACCESS read-create
    DESCRIPTION
        "(U//FOUO) Implementation of this object can be as low
         as read-create depending on which
         IS Objective or MIB desired requirements are
         not being met by the implementation."

    OBJECT     hLEPTAdminCost
    MIN-ACCESS read-create
    DESCRIPTION
        "(U//FOUO) Implementation of this object can be as low
         as read-create depending on which
         IS Objective or MIB desired requirements are
         not being met by the implementation."

    OBJECT     hPolicyRemoteTSTableLastChanged
    MIN-ACCESS read-only
    DESCRIPTION
        "(U//FOUO) Implementation of this object can be as low
         as read-only depending on which
         IS Objective or MIB desired requirements are
         not being met by the implementation."

    OBJECT     hPrefixTableLastChanged
    MIN-ACCESS read-only
    DESCRIPTION
        "(U//FOUO) Implementation of this object can be as low
         as read-only depending on which
         IS Objective or MIB desired requirements are
         not being met by the implementation."

    OBJECT     hPolicyRemoteTSTableCount
    MIN-ACCESS read-only
    DESCRIPTION
        "(U//FOUO) Implementation of this object can be as low
         as read-only depending on which
         IS Objective or MIB desired requirements are
         not being met by the implementation."

    OBJECT     hEstLocalTSPortEnd
    MIN-ACCESS read-create
    DESCRIPTION
        "(U//FOUO) Implementation of this object can be as low
         as read-create depending on which
         IS Objective or MIB desired requirements are
         not being met by the implementation."

    OBJECT     hLEPTTableCount
    MIN-ACCESS read-only
    DESCRIPTION
        "(U//FOUO) Implementation of this object can be as low
         as read-only depending on which
         IS Objective or MIB desired requirements are
         not being met by the implementation."

    OBJECT     hTFCConfigPacketSizeList
    MIN-ACCESS read-create
    DESCRIPTION
        "(U//FOUO) Implementation of this object can be as low
         as read-create depending on which
         IS Objective or MIB desired requirements are
         not being met by the implementation."

    OBJECT     hIPv6IfaceAutoAddrConfig
    MIN-ACCESS read-write
    DESCRIPTION
        "(U//FOUO) Implementation of this object can be as low
         as read-write depending on which
         IS Objective or MIB desired requirements are
         not being met by the implementation."

    OBJECT     hIPv4IfaceTableCount
    MIN-ACCESS read-only
    DESCRIPTION
        "(U//FOUO) Implementation of this object can be as low
         as read-only depending on which
         IS Objective or MIB desired requirements are
         not being met by the implementation."

    OBJECT     hEstRemoteTSPTAddrEnd
    MIN-ACCESS read-create
    DESCRIPTION
        "(U//FOUO) Implementation of this object can be as low
         as read-create depending on which
         IS Objective or MIB desired requirements are
         not being met by the implementation."

    OBJECT     hEstRemoteTSRowStatus
    MIN-ACCESS read-create
    DESCRIPTION
        "(U//FOUO) Implementation of this object can be as low
         as read-create depending on which
         IS Objective or MIB desired requirements are
         not being met by the implementation."

    OBJECT     hPolicyLocalTSPTAddrType
    MIN-ACCESS read-create
    DESCRIPTION
        "(U//FOUO) Implementation of this object can be as low
         as read-create depending on which
         IS Objective or MIB desired requirements are
         not being met by the implementation."

    OBJECT     hIPv4IfaceStatus
    MIN-ACCESS read-write
    DESCRIPTION
        "(U//FOUO) Implementation of this object can be as low
         as read-write depending on which
         IS Objective or MIB desired requirements are
         not being met by the implementation."

    OBJECT     hAddressAssignPrefixLength
    MIN-ACCESS read-create
    DESCRIPTION
        "(U//FOUO) Implementation of this object can be as low
         as read-create depending on which
         IS Objective or MIB desired requirements are
         not being met by the implementation."

    OBJECT     hPrePlacedKeyUsageType
    MIN-ACCESS read-write
    DESCRIPTION
        "(U//FOUO) Implementation of this object can be as low
         as read-write depending on which
         IS Objective or MIB desired requirements are
         not being met by the implementation."

    OBJECT     hIPv6IfaceTableLastChanged
    MIN-ACCESS read-only
    DESCRIPTION
        "(U//FOUO) Implementation of this object can be as low
         as read-only depending on which
         IS Objective or MIB desired requirements are
         not being met by the implementation."

    OBJECT     hEstLocalTSPTAddrEnd
    MIN-ACCESS read-create
    DESCRIPTION
        "(U//FOUO) Implementation of this object can be as low
         as read-create depending on which
         IS Objective or MIB desired requirements are
         not being met by the implementation."

    OBJECT     hSystemUpTime
    MIN-ACCESS read-only
    DESCRIPTION
        "(U//FOUO) Implementation of this object can be as low
         as read-only depending on which
         IS Objective or MIB desired requirements are
         not being met by the implementation."

    OBJECT     hDeviceVersTableCount
    MIN-ACCESS read-only
    DESCRIPTION
        "(U//FOUO) Implementation of this object can be as low
         as read-only depending on which
         IS Objective or MIB desired requirements are
         not being met by the implementation."

    OBJECT     hIPv4IfaceTTL
    MIN-ACCESS read-write
    DESCRIPTION
        "(U//FOUO) Implementation of this object can be as low
         as read-write depending on which
         IS Objective or MIB desired requirements are
         not being met by the implementation."

    OBJECT     hManualSecAttrsProfileRowStatus
    MIN-ACCESS read-create
    DESCRIPTION
        "(U//FOUO) Implementation of this object can be as low
         as read-create depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."

    OBJECT     hIPv6IfaceIdentifier
    MIN-ACCESS read-write
    DESCRIPTION
        "(U//FOUO) Implementation of this object can be as low
         as read-write depending on which
         IS Objective or MIB desired requirements are
         not being met by the implementation."

    OBJECT     hPEPTTableCount
    MIN-ACCESS read-only
    DESCRIPTION
        "(U//FOUO) Implementation of this object can be as low
         as read-only depending on which
         IS Objective or MIB desired requirements are
         not being met by the implementation."

    OBJECT     hPrefixAutoAddrConfigFlag
    MIN-ACCESS read-only
    DESCRIPTION
        "(U//FOUO) Implementation of this object can be as low
         as read-only depending on which
         IS Objective or MIB desired requirements are
         not being met by the implementation."

    OBJECT     hManualSADirection
    MIN-ACCESS read-create
    DESCRIPTION
        "(U//FOUO) Implementation of this object can be as low
         as read-create depending on which
         IS Objective or MIB desired requirements are
         not being met by the implementation."

    OBJECT     hDefaultRouterTableLastChanged
    MIN-ACCESS read-only
    DESCRIPTION
        "(U//FOUO) Implementation of this object can be as low
         as read-only depending on which
         IS Objective or MIB desired requirements are
         not being met by the implementation."

    OBJECT     hDefaultRouterLifetime
    MIN-ACCESS read-only
    DESCRIPTION
        "(U//FOUO) Implementation of this object can be as low
         as read-only depending on which
         IS Objective or MIB desired requirements are
         not being met by the implementation."

    OBJECT     hObjectLastChanged
    MIN-ACCESS read-only
    DESCRIPTION
        "(U//FOUO) Implementation of this object can be as low
         as read-only depending on which
         IS Objective or MIB desired requirements are
         not being met by the implementation."

    OBJECT     hManualSAAddressType
    MIN-ACCESS read-create
    DESCRIPTION
        "(U//FOUO) Implementation of this object can be as low
         as read-create depending on which
         IS Objective or MIB desired requirements are
         not being met by the implementation."

    OBJECT     hEstRemoteTSProtocol
    MIN-ACCESS read-create
    DESCRIPTION
        "(U//FOUO) Implementation of this object can be as low
         as read-create depending on which
         IS Objective or MIB desired requirements are
         not being met by the implementation."

    OBJECT     hEstRemoteTSTableLastChanged
    MIN-ACCESS read-only
    DESCRIPTION
        "(U//FOUO) Implementation of this object can be as low
         as read-only depending on which
         IS Objective or MIB desired requirements are
         not being met by the implementation."

    OBJECT     hDeviceVersTableLastChanged
    MIN-ACCESS read-only
    DESCRIPTION
        "(U//FOUO) Implementation of this object can be as low
         as read-only depending on which
         IS Objective or MIB desired requirements are
         not being met by the implementation."

    OBJECT     hManualSASPIChainTableCount
    MIN-ACCESS read-only
    DESCRIPTION
        "(U//FOUO) Implementation of this object can be as low
         as read-only depending on which
         IS Objective or MIB desired requirements are
         not being met by the implementation."

    OBJECT     hManualSAPHRDRate
    MIN-ACCESS read-create
    DESCRIPTION
        "(U//FOUO) Implementation of this object can be as low
         as read-create depending on which
         IS Objective or MIB desired requirements are
         not being met by the implementation."

    OBJECT     hLEPTRowLifetime
    MIN-ACCESS read-create
    DESCRIPTION
        "(U//FOUO) Implementation of this object can be as low
         as read-create depending on which
         IS Objective or MIB desired requirements are
         not being met by the implementation."

    OBJECT     hKTAuthCtrlsTableLastChanged
    MIN-ACCESS read-only
    DESCRIPTION
        "(U//FOUO) Implementation of this object can be as low
         as read-only depending on which
         IS Objective or MIB desired requirements are
         not being met by the implementation."

    OBJECT     hPolicyLocalTSTableLastChanged
    MIN-ACCESS read-only
    DESCRIPTION
        "(U//FOUO) Implementation of this object can be as low
         as read-only depending on which
         IS Objective or MIB desired requirements are
         not being met by the implementation."

    OBJECT     hIPv6IfaceICMPv6Enable
    MIN-ACCESS read-write
    DESCRIPTION
        "(U//FOUO) Implementation of this object can be as low
         as read-write depending on which
         IS Objective or MIB desired requirements are
         not being met by the implementation."

    OBJECT     hPolicyLocalTSProtocol
    MIN-ACCESS read-create
    DESCRIPTION
        "(U//FOUO) Implementation of this object can be as low
         as read-create depending on which
         IS Objective or MIB desired requirements are
         not being met by the implementation."

    OBJECT     hManualSALocalPTAddress
    MIN-ACCESS read-create
    DESCRIPTION
        "(U//FOUO) Implementation of this object can be as low
         as read-create depending on which
         IS Objective or MIB desired requirements are
         not being met by the implementation."

    OBJECT     hPolicyLocalTSPTAddrEnd
    MIN-ACCESS read-create
    DESCRIPTION
        "(U//FOUO) Implementation of this object can be as low
         as read-create depending on which
         IS Objective or MIB desired requirements are
         not being met by the implementation."

    OBJECT     hTFCConfigPacketSizeType
    MIN-ACCESS read-create
    DESCRIPTION
        "(U//FOUO) Implementation of this object can be as low
         as read-create depending on which
         IS Objective or MIB desired requirements are
         not being met by the implementation."

    OBJECT     hCIDRRouteRowStatus
    MIN-ACCESS read-create
    DESCRIPTION
        "(U//FOUO) Implementation of this object can be as low
         as read-create depending on which
         IS Objective or MIB desired requirements are
         not being met by the implementation."

    OBJECT     hPolicyLocalTSTableCount
    MIN-ACCESS read-only
    DESCRIPTION
        "(U//FOUO) Implementation of this object can be as low
         as read-only depending on which
         IS Objective or MIB desired requirements are
         not being met by the implementation."

    OBJECT     hPrefixValidLifetime
    MIN-ACCESS read-only
    DESCRIPTION
        "(U//FOUO) Implementation of this object can be as low
         as read-only depending on which
         IS Objective or MIB desired requirements are
         not being met by the implementation."

    OBJECT     hEstLocalTSProtocol
    MIN-ACCESS read-create
    DESCRIPTION
        "(U//FOUO) Implementation of this object can be as low
         as read-create depending on which
         IS Objective or MIB desired requirements are
         not being met by the implementation."

    OBJECT     hPrePlacedKeyTableLastChanged
    MIN-ACCESS read-only
    DESCRIPTION
        "(U//FOUO) Implementation of this object can be as low
         as read-only depending on which
         IS Objective or MIB desired requirements are
         not being met by the implementation."

    OBJECT     hPolicyRuleTableLastChanged
    MIN-ACCESS read-only
    DESCRIPTION
        "(U//FOUO) Implementation of this object can be as low
         as read-only depending on which
         IS Objective or MIB desired requirements are
         not being met by the implementation."

    OBJECT     hEstRemoteTSPortBegin
    MIN-ACCESS read-create
    DESCRIPTION
        "(U//FOUO) Implementation of this object can be as low
         as read-create depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hAddressAssignTableLastChanged
    MIN-ACCESS read-only
    DESCRIPTION
        "(U//FOUO) Implementation of this object can be as low
         as read-only depending on which
         IS Objective or MIB desired requirements are
         not being met by the implementation."

    OBJECT     hManualSAReachabilityStatus
    MIN-ACCESS read-only
    DESCRIPTION
        "(U//FOUO) Implementation of this object can be as low
         as read-only depending on which
         IS Objective or MIB desired requirements are
         not being met by the implementation."

    OBJECT     hPEPTAdminCost
    MIN-ACCESS read-create
    DESCRIPTION
        "(U//FOUO) Implementation of this object can be as low
         as read-create depending on which
         IS Objective or MIB desired requirements are
         not being met by the implementation."

    OBJECT     hKTAuthCtrlsTableCount
    MIN-ACCESS read-only
    DESCRIPTION
        "(U//FOUO) Implementation of this object can be as low
         as read-only depending on which
         IS Objective or MIB desired requirements are
         not being met by the implementation."

    OBJECT     hManualProfileTransformSuite
    MIN-ACCESS read-create
    DESCRIPTION
        "(U//FOUO) Implementation of this object can be as low
         as read-create depending on which
         IS Objective or MIB desired requirements are
         not being met by the implementation."

    OBJECT     hPEPTTableLastChanged
    MIN-ACCESS read-only
    DESCRIPTION
        "(U//FOUO) Implementation of this object can be as low
         as read-only depending on which
         IS Objective or MIB desired requirements are
         not being met by the implementation."

    OBJECT     hManualSASPIChainTableLastChanged
    MIN-ACCESS read-only
    DESCRIPTION
        "(U//FOUO) Implementation of this object can be as low
         as read-only depending on which
         IS Objective or MIB desired requirements are
         not being met by the implementation."

    OBJECT     hPolicyRemoteTSPTAddrType
    MIN-ACCESS read-create
    DESCRIPTION
        "(U//FOUO) Implementation of this object can be as low
         as read-create depending on which
         IS Objective or MIB desired requirements are
         not being met by the implementation."

    OBJECT     hCIDRRouteMetric
    MIN-ACCESS read-create
    DESCRIPTION
        "(U//FOUO) Implementation of this object can be as low
         as read-create depending on which
         IS Objective or MIB desired requirements are
         not being met by the implementation."

    OBJECT     hPrePlacedKeyRowStatus
    MIN-ACCESS read-write
    DESCRIPTION
        "(U//FOUO) Implementation of this object can be as low
         as read-write depending on which
         IS Objective or MIB desired requirements are
         not being met by the implementation."

    OBJECT     hAddressAssignRowStatus
    MIN-ACCESS read-create
    DESCRIPTION
        "(U//FOUO) Implementation of this object can be as low
         as read-create depending on which
         IS Objective or MIB desired requirements are
         not being met by the implementation."

    OBJECT     hTFCConfigTableCount
    MIN-ACCESS read-only
    DESCRIPTION
        "(U//FOUO) Implementation of this object can be as low
         as read-only depending on which
         IS Objective or MIB desired requirements are
         not being met by the implementation."

    OBJECT     hPolicyLocalTSPTAddrBegin
    MIN-ACCESS read-create
    DESCRIPTION
        "(U//FOUO) Implementation of this object can be as low
         as read-create depending on which
         IS Objective or MIB desired requirements are
         not being met by the implementation."

    OBJECT     hLEPTRowConfigMethod
    MIN-ACCESS read-only
    DESCRIPTION
        "(U//FOUO) Implementation of this object can be as low
         as read-only depending on which
         IS Objective or MIB desired requirements are
         not being met by the implementation."

    OBJECT     hManualSADSCPClassifier
    MIN-ACCESS read-create
    DESCRIPTION
        "(U//FOUO) Implementation of this object can be as low
         as read-create depending on which
         IS Objective or MIB desired requirements are
         not being met by the implementation."

    OBJECT     hEstRemoteTSPTAddrBegin
    MIN-ACCESS read-create
    DESCRIPTION
        "(U//FOUO) Implementation of this object can be as low
         as read-create depending on which
         IS Objective or MIB desired requirements are
         not being met by the implementation."

    OBJECT     hPrefixPreferredLifetime
    MIN-ACCESS read-only
    DESCRIPTION
        "(U//FOUO) Implementation of this object can be as low
         as read-only depending on which
         IS Objective or MIB desired requirements are
         not being met by the implementation."

    OBJECT     hPrefixOrigin
    MIN-ACCESS read-only
    DESCRIPTION
        "(U//FOUO) Implementation of this object can be as low
         as read-only depending on which
         IS Objective or MIB desired requirements are
         not being met by the implementation."

    OBJECT     hKTAuthCtrlsAddress
    MIN-ACCESS read-create
    DESCRIPTION
        "(U//FOUO) Implementation of this object can be as low
         as read-create depending on which
         IS Objective or MIB desired requirements are
         not being met by the implementation."

    OBJECT     hPolicyRuleTrafficSelectorName
    MIN-ACCESS read-create
    DESCRIPTION
        "(U//FOUO) Implementation of this object can be as low
         as read-create depending on which
         IS Objective or MIB desired requirements are
         not being met by the implementation."

    OBJECT     hCIDRRouteIfIndex
    MIN-ACCESS read-create
    DESCRIPTION
        "(U//FOUO) Implementation of this object can be as low
         as read-create depending on which
         IS Objective or MIB desired requirements are
         not being met by the implementation."

    OBJECT     hManualSARemoteCTAddress
    MIN-ACCESS read-create
    DESCRIPTION
        "(U//FOUO) Implementation of this object can be as low
         as read-create depending on which
         IS Objective or MIB desired requirements are
         not being met by the implementation."

    OBJECT     hTFCConfigRowStatus
    MIN-ACCESS read-create
    DESCRIPTION
        "(U//FOUO) Implementation of this object can be as low
         as read-create depending on which
         IS Objective or MIB desired requirements are
         not being met by the implementation."

    OBJECT     hTFCConfigTableLastChanged
    MIN-ACCESS read-only
    DESCRIPTION
        "(U//FOUO) Implementation of this object can be as low
         as read-only depending on which
         IS Objective or MIB desired requirements are
         not being met by the implementation."

    OBJECT     hKTAuthCtrlsAddressType
    MIN-ACCESS read-create
    DESCRIPTION
        "(U//FOUO) Implementation of this object can be as low
         as read-create depending on which
         IS Objective or MIB desired requirements are
         not being met by the implementation."

    OBJECT     hPolicyRuleAction
    MIN-ACCESS read-create
    DESCRIPTION
        "(U//FOUO) Implementation of this object can be as low
         as read-create depending on which
         IS Objective or MIB desired requirements are
         not being met by the implementation."

    OBJECT     hManualSAKeyChainName
    MIN-ACCESS read-create
    DESCRIPTION
        "(U//FOUO) Implementation of this object can be as low
         as read-create depending on which
         IS Objective or MIB desired requirements are
         not being met by the implementation."

    OBJECT     hPEPTRowStatus
    MIN-ACCESS read-create
    DESCRIPTION
        "(U//FOUO) Implementation of this object can be as low
         as read-create depending on which
         IS Objective or MIB desired requirements are
         not being met by the implementation."

    OBJECT     hIPv6IfaceSide
    MIN-ACCESS read-only
    DESCRIPTION
        "(U//FOUO) Implementation of this object can be as low
         as read-only depending on which
         IS Objective or MIB desired requirements are
         not being met by the implementation."

    OBJECT     hPolicyLocalTSPortEnd
    MIN-ACCESS read-create
    DESCRIPTION
        "(U//FOUO) Implementation of this object can be as low
         as read-create depending on which
         IS Objective or MIB desired requirements are
         not being met by the implementation."

    OBJECT     hEstRemoteTSPTAddrType
    MIN-ACCESS read-create
    DESCRIPTION
        "(U//FOUO) Implementation of this object can be as low
         as read-create depending on which
         IS Objective or MIB desired requirements are
         not being met by the implementation."

    OBJECT     hManualSALocalCTAddress
    MIN-ACCESS read-create
    DESCRIPTION
        "(U//FOUO) Implementation of this object can be as low
         as read-create depending on which
         IS Objective or MIB desired requirements are
         not being met by the implementation."

    OBJECT     hManualSAStartTime
    MIN-ACCESS read-create
    DESCRIPTION
        "(U//FOUO) Implementation of this object can be as low
         as read-create depending on which
         IS Objective or MIB desired requirements are
         not being met by the implementation."

    OBJECT     hPolicyRemoteTSPortEnd
    MIN-ACCESS read-create
    DESCRIPTION
        "(U//FOUO) Implementation of this object can be as low
         as read-create depending on which
         IS Objective or MIB desired requirements are
         not being met by the implementation."

    OBJECT     hManualSARemotePTAddress
    MIN-ACCESS read-create
    DESCRIPTION
        "(U//FOUO) Implementation of this object can be as low
         as read-create depending on which
         IS Objective or MIB desired requirements are
         not being met by the implementation."

    OBJECT     hAddressAssignTableCount
    MIN-ACCESS read-only
    DESCRIPTION
        "(U//FOUO) Implementation of this object can be as low
         as read-only depending on which
         IS Objective or MIB desired requirements are
         not being met by the implementation."

    OBJECT     hPolicyLocalTSPortBegin
    MIN-ACCESS read-create
    DESCRIPTION
        "(U//FOUO) Implementation of this object can be as low
         as read-create depending on which
         IS Objective or MIB desired requirements are
         not being met by the implementation."

    OBJECT     hManualSAFlowLabelSetting
    MIN-ACCESS read-create
    DESCRIPTION
        "(U//FOUO) Implementation of this object can be as low
         as read-create depending on which
         IS Objective or MIB desired requirements are
         not being met by the implementation."

    OBJECT     hDefaultRouterPreference
    MIN-ACCESS read-only
    DESCRIPTION
        "(U//FOUO) Implementation of this object can be as low
         as read-only depending on which
         IS Objective or MIB desired requirements are
         not being met by the implementation."

    OBJECT     hManualSAProfileTableLastChanged
    MIN-ACCESS read-only
    DESCRIPTION
        "(U//FOUO) Implementation of this object can be as low
         as read-only depending on which
         IS Objective or MIB desired requirements are
         not being met by the implementation."

    OBJECT     hEstLocalTSPTAddrType
    MIN-ACCESS read-create
    DESCRIPTION
        "(U//FOUO) Implementation of this object can be as low
         as read-create depending on which
         IS Objective or MIB desired requirements are
         not being met by the implementation."

    OBJECT     hPrefixTableCount
    MIN-ACCESS read-only
    DESCRIPTION
        "(U//FOUO) Implementation of this object can be as low
         as read-only depending on which
         IS Objective or MIB desired requirements are
         not being met by the implementation."

    OBJECT     hCIDRRouteProtocol
    MIN-ACCESS read-only
    DESCRIPTION
        "(U//FOUO) Implementation of this object can be as low
         as read-only depending on which
         IS Objective or MIB desired requirements are
         not being met by the implementation."

    OBJECT     hManualSASPIChainReference
    MIN-ACCESS read-create
    DESCRIPTION
        "(U//FOUO) Implementation of this object can be as low
         as read-create depending on which
         IS Objective or MIB desired requirements are
         not being met by the implementation."

    OBJECT     hEstRemoteTSTableCount
    MIN-ACCESS read-only
    DESCRIPTION
        "(U//FOUO) Implementation of this object can be as low
         as read-only depending on which
         IS Objective or MIB desired requirements are
         not being met by the implementation."

    OBJECT     hCIDRRouteTableCount
    MIN-ACCESS read-only
    DESCRIPTION
        "(U//FOUO) Implementation of this object can be as low
         as read-only depending on which
         IS Objective or MIB desired requirements are
         not being met by the implementation."

    OBJECT     hStationIdentifier
    MIN-ACCESS read-only
    DESCRIPTION
        "(U//FOUO) Implementation of this object can be as low
         as read-only depending on which
         IS Objective or MIB desired requirements are
         not being met by the implementation."
::= { haipeV040101Conformance 2 }

--
-- Objects referenced by the Bandwidth Management IS
--
hBandwidthManagementCapabilityGroup OBJECT-GROUP
    OBJECTS {
                hEstMRCBMValue,
                hEstBMParamRowStatus,
                hManualSARowStatus,
                hEstBMParamTableCount,
                hManualSAEstBMParamsIndex,
                hEstBMParamTableLastChanged
            }
    STATUS    current
    DESCRIPTION
        "(U//FUOUO) Objects for the Bandwidth Management document(s).
         This group is only relevant if both extensions are supported"
    ::= { haipeV040101Groups 3 }

--
-- Conformance levels required by the Bandwidth Management IS
--
hBandwidthManagementCapabilityCompliance MODULE-COMPLIANCE
    STATUS    current
    DESCRIPTION
        "(U//FOUO) Compliance levels for objects required by the
         Bandwidth Management document(s)."
    MODULE -- this module
    MANDATORY-GROUPS { hBandwidthManagementCapabilityGroup }

    OBJECT     hEstMRCBMValue
    MIN-ACCESS read-create
    DESCRIPTION
        "(U//FOUO) Implementation of this object can be as low
         as read-create depending on which
         IS Objective or MIB desired requirements are
         not being met by the implementation."

    OBJECT     hEstBMParamRowStatus
    MIN-ACCESS read-create
    DESCRIPTION
        "(U//FOUO) Implementation of this object can be as low
         as read-create depending on which
         IS Objective or MIB desired requirements are
         not being met by the implementation."

    OBJECT     hManualSARowStatus
    MIN-ACCESS read-create
    DESCRIPTION
        "(U//FOUO) Implementation of this object can be as low
         as read-create depending on which
         IS Objective or MIB desired requirements are
         not being met by the implementation."

    OBJECT     hEstBMParamTableCount
    MIN-ACCESS read-only
    DESCRIPTION
        "(U//FOUO) Implementation of this object can be as low
         as read-only depending on which
         IS Objective or MIB desired requirements are
         not being met by the implementation."

    OBJECT     hManualSAEstBMParamsIndex
    MIN-ACCESS read-create
    DESCRIPTION
        "(U//FOUO) Implementation of this object can be as low
         as read-create depending on which
         IS Objective or MIB desired requirements are
         not being met by the implementation."

    OBJECT     hEstBMParamTableLastChanged
    MIN-ACCESS read-only
    DESCRIPTION
        "(U//FOUO) Implementation of this object can be as low
         as read-only depending on which
         IS Objective or MIB desired requirements are
         not being met by the implementation."
::= { haipeV040101Conformance 3 }

--
-- Objects referenced by the Remote Provisioning Authority IS
--
hRemoteProvisioningAuthorityCapabilityGroup OBJECT-GROUP
    OBJECTS {
                hLoadedKeyTableLastChanged,
                hLoadedKeyTableCount,
                hOOBKTKeyFileTableLastChanged,
                hOOBKTClientsTableLastChanged,
                hIBKTClientsTransRetryPeriod,
                hLoadedKeyClassification,
                hOOBKTClientsTableCount,
                hOOBKTAddress,
                hIBKTClientsTransferRetries,
                hOOBKTKeyFileLoadedKey,
                hOOBKTKeyFileTableCount,
                hIBKTClientsRowStatus,
                hOOBKTKeyFiles,
                hIBKTClientsLoadedKey,
                hTFTPDesiredBlkSize,
                hTFTPDesiredTimeout,
                hIBKTClientsTransferTime,
                hOOBKTClientPushKey,
                hOOBKTKeyFileRowStatus,
                hIBKTClientsEffectiveDate,
                hOOBKTClientPath,
                hLoadedKeyAction,
                hOOBKTClientRowStatus,
                hLoadedKeyUse,
                hLoadedKeyText,
                hLoadedKeyRowStatus,
                hIBKTClientsTableCount,
                hIBKTClientsManSAChainName,
                hIBKTClientsTableLastChanged,
                hOOBKTAddressType
            }
    STATUS    current
    DESCRIPTION
        "(U//FUOUO) Objects for the Remote Provisioning Authority document(s).
         This group is only relevant if both extensions are supported"
    ::= { haipeV040101Groups 4 }

--
-- Conformance levels required by the Remote Provisioning Authority IS
--
hRemoteProvisioningAuthorityCapabilityCompliance MODULE-COMPLIANCE
    STATUS    current
    DESCRIPTION
        "(U//FOUO) Compliance levels for objects required by the
         Remote Provisioning Authority document(s)."
    MODULE -- this module
    MANDATORY-GROUPS { hRemoteProvisioningAuthorityCapabilityGroup }

    OBJECT     hLoadedKeyTableLastChanged
    MIN-ACCESS read-only
    DESCRIPTION
        "(U//FOUO) Implementation of this object can be as low
         as read-only depending on which
         IS Objective or MIB desired requirements are
         not being met by the implementation."

    OBJECT     hLoadedKeyTableCount
    MIN-ACCESS read-only
    DESCRIPTION
        "(U//FOUO) Implementation of this object can be as low
         as read-only depending on which
         IS Objective or MIB desired requirements are
         not being met by the implementation."

    OBJECT     hOOBKTKeyFileTableLastChanged
    MIN-ACCESS read-only
    DESCRIPTION
        "(U//FOUO) Implementation of this object can be as low
         as read-only depending on which
         IS Objective or MIB desired requirements are
         not being met by the implementation."

    OBJECT     hOOBKTClientsTableLastChanged
    MIN-ACCESS read-only
    DESCRIPTION
        "(U//FOUO) Implementation of this object can be as low
         as read-only depending on which
         IS Objective or MIB desired requirements are
         not being met by the implementation."

    OBJECT     hIBKTClientsTransRetryPeriod
    MIN-ACCESS read-create
    DESCRIPTION
        "(U//FOUO) Implementation of this object can be as low
         as read-create depending on which
         IS Objective or MIB desired requirements are
         not being met by the implementation."

    OBJECT     hLoadedKeyClassification
    MIN-ACCESS read-only
    DESCRIPTION
        "(U//FOUO) Implementation of this object can be as low
         as read-only depending on which
         IS Objective or MIB desired requirements are
         not being met by the implementation."

    OBJECT     hOOBKTClientsTableCount
    MIN-ACCESS read-only
    DESCRIPTION
        "(U//FOUO) Implementation of this object can be as low
         as read-only depending on which
         IS Objective or MIB desired requirements are
         not being met by the implementation."

    OBJECT     hOOBKTAddress
    MIN-ACCESS read-create
    DESCRIPTION
        "(U//FOUO) Implementation of this object can be as low
         as read-create depending on which
         IS Objective or MIB desired requirements are
         not being met by the implementation."

    OBJECT     hIBKTClientsTransferRetries
    MIN-ACCESS read-create
    DESCRIPTION
        "(U//FOUO) Implementation of this object can be as low
         as read-create depending on which
         IS Objective or MIB desired requirements are
         not being met by the implementation."

    OBJECT     hOOBKTKeyFileLoadedKey
    MIN-ACCESS read-create
    DESCRIPTION
        "(U//FOUO) Implementation of this object can be as low
         as read-create depending on which
         IS Objective or MIB desired requirements are
         not being met by the implementation."

    OBJECT     hOOBKTKeyFileTableCount
    MIN-ACCESS read-only
    DESCRIPTION
        "(U//FOUO) Implementation of this object can be as low
         as read-only depending on which
         IS Objective or MIB desired requirements are
         not being met by the implementation."

    OBJECT     hIBKTClientsRowStatus
    MIN-ACCESS read-create
    DESCRIPTION
        "(U//FOUO) Implementation of this object can be as low
         as read-create depending on which
         IS Objective or MIB desired requirements are
         not being met by the implementation."

    OBJECT     hOOBKTKeyFiles
    MIN-ACCESS read-create
    DESCRIPTION
        "(U//FOUO) Implementation of this object can be as low
         as read-create depending on which
         IS Objective or MIB desired requirements are
         not being met by the implementation."

    OBJECT     hIBKTClientsLoadedKey
    MIN-ACCESS read-create
    DESCRIPTION
        "(U//FOUO) Implementation of this object can be as low
         as read-create depending on which
         IS Objective or MIB desired requirements are
         not being met by the implementation."

    OBJECT     hTFTPDesiredBlkSize
    MIN-ACCESS read-write
    DESCRIPTION
        "(U//FOUO) Implementation of this object can be as low
         as read-write depending on which
         IS Objective or MIB desired requirements are
         not being met by the implementation."

    OBJECT     hTFTPDesiredTimeout
    MIN-ACCESS read-write
    DESCRIPTION
        "(U//FOUO) Implementation of this object can be as low
         as read-write depending on which
         IS Objective or MIB desired requirements are
         not being met by the implementation."

    OBJECT     hIBKTClientsTransferTime
    MIN-ACCESS read-create
    DESCRIPTION
        "(U//FOUO) Implementation of this object can be as low
         as read-create depending on which
         IS Objective or MIB desired requirements are
         not being met by the implementation."

    OBJECT     hOOBKTClientPushKey
    MIN-ACCESS read-create
    DESCRIPTION
        "(U//FOUO) Implementation of this object can be as low
         as read-create depending on which
         IS Objective or MIB desired requirements are
         not being met by the implementation."

    OBJECT     hOOBKTKeyFileRowStatus
    MIN-ACCESS read-create
    DESCRIPTION
        "(U//FOUO) Implementation of this object can be as low
         as read-create depending on which
         IS Objective or MIB desired requirements are
         not being met by the implementation."

    OBJECT     hIBKTClientsEffectiveDate
    MIN-ACCESS read-create
    DESCRIPTION
        "(U//FOUO) Implementation of this object can be as low
         as read-create depending on which
         IS Objective or MIB desired requirements are
         not being met by the implementation."

    OBJECT     hOOBKTClientPath
    MIN-ACCESS read-create
    DESCRIPTION
        "(U//FOUO) Implementation of this object can be as low
         as read-create depending on which
         IS Objective or MIB desired requirements are
         not being met by the implementation."

    OBJECT     hLoadedKeyAction
    MIN-ACCESS read-only
    DESCRIPTION
        "(U//FOUO) Implementation of this object can be as low
         as read-only depending on which
         IS Objective or MIB desired requirements are
         not being met by the implementation."

    OBJECT     hOOBKTClientRowStatus
    MIN-ACCESS read-create
    DESCRIPTION
        "(U//FOUO) Implementation of this object can be as low
         as read-create depending on which
         IS Objective or MIB desired requirements are
         not being met by the implementation."

    OBJECT     hLoadedKeyUse
    MIN-ACCESS read-only
    DESCRIPTION
        "(U//FOUO) Implementation of this object can be as low
         as read-only depending on which
         IS Objective or MIB desired requirements are
         not being met by the implementation."

    OBJECT     hLoadedKeyText
    MIN-ACCESS read-only
    DESCRIPTION
        "(U//FOUO) Implementation of this object can be as low
         as read-only depending on which
         IS Objective or MIB desired requirements are
         not being met by the implementation."

    OBJECT     hLoadedKeyRowStatus
    MIN-ACCESS read-only
    DESCRIPTION
        "(U//FOUO) Implementation of this object can be as low
         as read-only depending on which
         IS Objective or MIB desired requirements are
         not being met by the implementation."

    OBJECT     hIBKTClientsTableCount
    MIN-ACCESS read-only
    DESCRIPTION
        "(U//FOUO) Implementation of this object can be as low
         as read-only depending on which
         IS Objective or MIB desired requirements are
         not being met by the implementation."

    OBJECT     hIBKTClientsManSAChainName
    MIN-ACCESS read-create
    DESCRIPTION
        "(U//FOUO) Implementation of this object can be as low
         as read-create depending on which
         IS Objective or MIB desired requirements are
         not being met by the implementation."

    OBJECT     hIBKTClientsTableLastChanged
    MIN-ACCESS read-only
    DESCRIPTION
        "(U//FOUO) Implementation of this object can be as low
         as read-only depending on which
         IS Objective or MIB desired requirements are
         not being met by the implementation."

    OBJECT     hOOBKTAddressType
    MIN-ACCESS read-create
    DESCRIPTION
        "(U//FOUO) Implementation of this object can be as low
         as read-create depending on which
         IS Objective or MIB desired requirements are
         not being met by the implementation."
::= { haipeV040101Conformance 4 }

--
-- Objects referenced by the Automated Security Association and Gateway IS
--
hAutomatedSAANDGatewayCapabilityGroup OBJECT-GROUP
    OBJECTS {
                hIKEv1ProfileECNSetting,
                hIKEv1SAFlowLabelSetting,
                hIKEv1SACTDSCPValue,
                hIKEv1ProfileDSCPSetting,
                hIKEv1SACTFlowLabelValue,
                hIKEv1ProfileDFBitSetting,
                hIKEv1ProfileNtwkParamsRef,
                hIKEv1SARowStatus,
                hIKEv1ProfileFlowLabelSetting,
                hIKEv1ProfileDSCPValue,
                hIKEv1SACTDSCPSetting,
                hPolicyRuleRowStatus,
                hIKEv1SADFBitSetting,
                hIKEv1SecAttrsProfileRowStatus,
                hIKEv1ProfileFlowLabelValue,
                hIKEv1SAECNSetting,
                hIKEv1NtwkParamsProfileRowStatus,
                hPolicyRuleSecAttrsProfileName
            }
    STATUS    current
    DESCRIPTION
        "(U//FUOUO) Objects for the Automated Security Association and Gateway document(s).
         This group is only relevant if the extension is supported"
    ::= { haipeV040101Groups 5 }

--
-- Conformance levels required by the Automated Security Association and Gateway IS
--
hAutomatedSAANDGatewayCapabilityCompliance MODULE-COMPLIANCE
    STATUS    current
    DESCRIPTION
        "(U//FOUO) Compliance levels for objects required by the
         Automated Security Association and Gateway document(s)."
    MODULE -- this module
    MANDATORY-GROUPS { hAutomatedSAANDGatewayCapabilityGroup }

    OBJECT     hIKEv1ProfileECNSetting
    MIN-ACCESS read-create
    DESCRIPTION
        "(U//FOUO) Implementation of this object can be as low
         as read-create depending on which
         IS Objective or MIB desired requirements are
         not being met by the implementation."

    OBJECT     hIKEv1SAFlowLabelSetting
    MIN-ACCESS read-only
    DESCRIPTION
        "(U//FOUO) Implementation of this object can be as low
         as read-only depending on which
         IS Objective or MIB desired requirements are
         not being met by the implementation."

    OBJECT     hIKEv1SACTDSCPValue
    MIN-ACCESS read-only
    DESCRIPTION
        "(U//FOUO) Implementation of this object can be as low
         as read-only depending on which
         IS Objective or MIB desired requirements are
         not being met by the implementation."

    OBJECT     hIKEv1ProfileDSCPSetting
    MIN-ACCESS read-create
    DESCRIPTION
        "(U//FOUO) Implementation of this object can be as low
         as read-create depending on which
         IS Objective or MIB desired requirements are
         not being met by the implementation."

    OBJECT     hIKEv1SACTFlowLabelValue
    MIN-ACCESS read-only
    DESCRIPTION
        "(U//FOUO) Implementation of this object can be as low
         as read-only depending on which
         IS Objective or MIB desired requirements are
         not being met by the implementation."

    OBJECT     hIKEv1ProfileDFBitSetting
    MIN-ACCESS read-create
    DESCRIPTION
        "(U//FOUO) Implementation of this object can be as low
         as read-create depending on which
         IS Objective or MIB desired requirements are
         not being met by the implementation."

    OBJECT     hIKEv1ProfileNtwkParamsRef
    MIN-ACCESS read-create
    DESCRIPTION
        "(U//FOUO) Implementation of this object can be as low
         as read-create depending on which
         IS Objective or MIB desired requirements are
         not being met by the implementation."

    OBJECT     hIKEv1SARowStatus
    MIN-ACCESS read-only
    DESCRIPTION
        "(U//FOUO) Implementation of this object can be as low
         as read-only depending on which
         IS Objective or MIB desired requirements are
         not being met by the implementation."

    OBJECT     hIKEv1ProfileFlowLabelSetting
    MIN-ACCESS read-create
    DESCRIPTION
        "(U//FOUO) Implementation of this object can be as low
         as read-create depending on which
         IS Objective or MIB desired requirements are
         not being met by the implementation."

    OBJECT     hIKEv1ProfileDSCPValue
    MIN-ACCESS read-create
    DESCRIPTION
        "(U//FOUO) Implementation of this object can be as low
         as read-create depending on which
         IS Objective or MIB desired requirements are
         not being met by the implementation."

    OBJECT     hIKEv1SACTDSCPSetting
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv1SADFBitSetting
    MIN-ACCESS read-only
    DESCRIPTION
        "(U//FOUO) Implementation of this object can be as low
         as read-only depending on which
         IS Objective or MIB desired requirements are
         not being met by the implementation."

    OBJECT     hIKEv1SecAttrsProfileRowStatus
    MIN-ACCESS read-create
    DESCRIPTION
        "(U//FOUO) Implementation of this object can be as low
         as read-create depending on which
         IS Objective or MIB desired requirements are
         not being met by the implementation."

    OBJECT     hIKEv1ProfileFlowLabelValue
    MIN-ACCESS read-create
    DESCRIPTION
        "(U//FOUO) Implementation of this object can be as low
         as read-create depending on which
         IS Objective or MIB desired requirements are
         not being met by the implementation."

    OBJECT     hIKEv1SAECNSetting
    MIN-ACCESS read-only
    DESCRIPTION
        "(U//FOUO) Implementation of this object can be as low
         as read-only depending on which
         IS Objective or MIB desired requirements are
         not being met by the implementation."

    OBJECT     hIKEv1NtwkParamsProfileRowStatus
    MIN-ACCESS read-create
    DESCRIPTION
        "(U//FOUO) Implementation of this object can be as low
         as read-create depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 5 }

--
-- Objects referenced by the Header Compression IS
--
hHeaderCompressionCapabilityGroup OBJECT-GROUP
    OBJECTS {
                hManualSAEstROHCParamsIndex,
                hEstROHCRepeatIR,
                hManualSARowStatus,
                hEstROHCCompressionProfiles,
                hEstROHCMAXCID,
                hEstROHCFeedbackChannel,
                hEstROHCTimeout,
                hEstROHCParamTableCount,
                hEstROHCParamTableLastChanged,
                hEstROHCRowStatus
            }
    STATUS    current
    DESCRIPTION
        "(U//FUOUO) Objects for the Header Compression document(s).
         This group is only relevant if both extensions are supported"
    ::= { haipeV040101Groups 6 }

--
-- Conformance levels required by the Header Compression IS
--
hHeaderCompressionCapabilityCompliance MODULE-COMPLIANCE
    STATUS    current
    DESCRIPTION
        "(U//FOUO) Compliance levels for objects required by the
         Header Compression document(s)."
    MODULE -- this module
    MANDATORY-GROUPS { hHeaderCompressionCapabilityGroup }

    OBJECT     hManualSAEstROHCParamsIndex
    MIN-ACCESS read-create
    DESCRIPTION
        "(U//FOUO) Implementation of this object can be as low
         as read-create depending on which
         IS Objective or MIB desired requirements are
         not being met by the implementation."

    OBJECT     hEstROHCRepeatIR
    MIN-ACCESS read-create
    DESCRIPTION
        "(U//FOUO) Implementation of this object can be as low
         as read-create depending on which
         IS Objective or MIB desired requirements are
         not being met by the implementation."

    OBJECT     hManualSARowStatus
    MIN-ACCESS read-create
    DESCRIPTION
        "(U//FOUO) Implementation of this object can be as low
         as read-create depending on which
         IS Objective or MIB desired requirements are
         not being met by the implementation."

    OBJECT     hEstROHCCompressionProfiles
    MIN-ACCESS read-create
    DESCRIPTION
        "(U//FOUO) Implementation of this object can be as low
         as read-create depending on which
         IS Objective or MIB desired requirements are
         not being met by the implementation."

    OBJECT     hEstROHCMAXCID
    MIN-ACCESS read-create
    DESCRIPTION
        "(U//FOUO) Implementation of this object can be as low
         as read-create depending on which
         IS Objective or MIB desired requirements are
         not being met by the implementation."

    OBJECT     hEstROHCFeedbackChannel
    MIN-ACCESS read-create
    DESCRIPTION
        "(U//FOUO) Implementation of this object can be as low
         as read-create depending on which
         IS Objective or MIB desired requirements are
         not being met by the implementation."

    OBJECT     hEstROHCTimeout
    MIN-ACCESS read-create
    DESCRIPTION
        "(U//FOUO) Implementation of this object can be as low
         as read-create depending on which
         IS Objective or MIB desired requirements are
         not being met by the implementation."

    OBJECT     hEstROHCParamTableCount
    MIN-ACCESS read-only
    DESCRIPTION
        "(U//FOUO) Implementation of this object can be as low
         as read-only depending on which
         IS Objective or MIB desired requirements are
         not being met by the implementation."

    OBJECT     hEstROHCParamTableLastChanged
    MIN-ACCESS read-only
    DESCRIPTION
        "(U//FOUO) Implementation of this object can be as low
         as read-only depending on which
         IS Objective or MIB desired requirements are
         not being met by the implementation."

    OBJECT     hEstROHCRowStatus
    MIN-ACCESS read-create
    DESCRIPTION
        "(U//FOUO) Implementation of this object can be as low
         as read-create depending on which
         IS Objective or MIB desired requirements are
         not being met by the implementation."
::= { haipeV040101Conformance 6 }

--
-- Objects referenced by the Automated Security Association - IKEv2 and Generic Discovery Client IS
--
hAutomatedSAIKEv2ANDGenericDiscoveryClientCapabilityGroup OBJECT-GROUP
    OBJECTS {
                hIKEv2CHLDSecAttrsProfRowStatus,
                hIKEv2CHLDNPPRowStatus,
                hIKEv2CHLDProfileNtwkParamsRef,
                hIKEv2CHILDSARowStatus,
                hPolicyRuleRowStatus,
                hIKEv2CHLDNPPPDUNEnabled,
                hIKEv2CHILDSAPDUNEnabled,
                hPolicyRuleSecAttrsProfileName
            }
    STATUS    current
    DESCRIPTION
        "(U//FUOUO) Objects for the Automated Security Association - IKEv2 and Generic Discovery Client document(s).
         This group is only relevant if the extension is supported"
    ::= { haipeV040101Groups 7 }

--
-- Conformance levels required by the Automated Security Association - IKEv2 and Generic Discovery Client IS
--
hAutomatedSAIKEv2ANDGenericDiscoveryClientCapabilityCompliance MODULE-COMPLIANCE
    STATUS    current
    DESCRIPTION
        "(U//FOUO) Compliance levels for objects required by the
         Automated Security Association - IKEv2 and Generic Discovery Client document(s)."
    MODULE -- this module
    MANDATORY-GROUPS { hAutomatedSAIKEv2ANDGenericDiscoveryClientCapabilityGroup }

    OBJECT     hIKEv2CHLDSecAttrsProfRowStatus
    MIN-ACCESS read-create
    DESCRIPTION
        "(U//FOUO) Implementation of this object can be as low
         as read-create depending on which
         IS Objective or MIB desired requirements are
         not being met by the implementation."

    OBJECT     hIKEv2CHLDNPPRowStatus
    MIN-ACCESS read-create
    DESCRIPTION
        "(U//FOUO) Implementation of this object can be as low
         as read-create depending on which
         IS Objective or MIB desired requirements are
         not being met by the implementation."

    OBJECT     hIKEv2CHLDProfileNtwkParamsRef
    MIN-ACCESS read-create
    DESCRIPTION
        "(U//FOUO) Implementation of this object can be as low
         as read-create depending on which
         IS Objective or MIB desired requirements are
         not being met by the implementation."

    OBJECT     hIKEv2CHILDSARowStatus
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv2CHLDNPPPDUNEnabled
    MIN-ACCESS read-create
    DESCRIPTION
        "(U//FOUO) Implementation of this object can be as low
         as read-create depending on which
         IS Objective or MIB desired requirements are
         not being met by the implementation."

    OBJECT     hIKEv2CHILDSAPDUNEnabled
    MIN-ACCESS read-only
    DESCRIPTION
        "(U//FOUO) Implementation of this object can be as low
         as read-only depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 7 }

--
-- Objects referenced by the Automated Security Association - IKEv2 and Header Compression IS
--
hAutomatedSAIKEv2ANDHeaderCompressionCapabilityGroup OBJECT-GROUP
    OBJECTS {
                hPolicyRuleUseROHC,
                hEstROHCRepeatIR,
                hIKEv2CHILDSARowStatus,
                hEstROHCCompressionProfiles,
                hPolicyRuleRowStatus,
                hEstROHCFeedbackChannel,
                hEstROHCTimeout,
                hIKEv2CHILDSAEstROHCParamsIndex,
                hEstROHCMAXCID,
                hEstROHCRowStatus
            }
    STATUS    current
    DESCRIPTION
        "(U//FUOUO) Objects for the Automated Security Association - IKEv2 and Header Compression document(s).
         This group is only relevant if the extension is supported"
    ::= { haipeV040101Groups 8 }

--
-- Conformance levels required by the Automated Security Association - IKEv2 and Header Compression IS
--
hAutomatedSAIKEv2ANDHeaderCompressionCapabilityCompliance MODULE-COMPLIANCE
    STATUS    current
    DESCRIPTION
        "(U//FOUO) Compliance levels for objects required by the
         Automated Security Association - IKEv2 and Header Compression document(s)."
    MODULE -- this module
    MANDATORY-GROUPS { hAutomatedSAIKEv2ANDHeaderCompressionCapabilityGroup }

    OBJECT     hPolicyRuleUseROHC
    MIN-ACCESS read-create
    DESCRIPTION
        "(U//FOUO) Implementation of this object can be as low
         as read-create depending on which
         IS Objective or MIB desired requirements are
         not being met by the implementation."

    OBJECT     hEstROHCRepeatIR
    MIN-ACCESS read-only
    DESCRIPTION
        "(U//FOUO) Implementation of this object can be as low
         as read-only depending on which
         IS Objective or MIB desired requirements are
         not being met by the implementation."

    OBJECT     hIKEv2CHILDSARowStatus
    MIN-ACCESS read-only
    DESCRIPTION
        "(U//FOUO) Implementation of this object can be as low
         as read-only depending on which
         IS Objective or MIB desired requirements are
         not being met by the implementation."

    OBJECT     hEstROHCCompressionProfiles
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hEstROHCFeedbackChannel
    MIN-ACCESS read-only
    DESCRIPTION
        "(U//FOUO) Implementation of this object can be as low
         as read-only depending on which
         IS Objective or MIB desired requirements are
         not being met by the implementation."

    OBJECT     hEstROHCTimeout
    MIN-ACCESS read-only
    DESCRIPTION
        "(U//FOUO) Implementation of this object can be as low
         as read-only depending on which
         IS Objective or MIB desired requirements are
         not being met by the implementation."

    OBJECT     hIKEv2CHILDSAEstROHCParamsIndex
    MIN-ACCESS read-only
    DESCRIPTION
        "(U//FOUO) Implementation of this object can be as low
         as read-only depending on which
         IS Objective or MIB desired requirements are
         not being met by the implementation."

    OBJECT     hEstROHCMAXCID
    MIN-ACCESS read-only
    DESCRIPTION
        "(U//FOUO) Implementation of this object can be as low
         as read-only depending on which
         IS Objective or MIB desired requirements are
         not being met by the implementation."

    OBJECT     hEstROHCRowStatus
    MIN-ACCESS read-only
    DESCRIPTION
        "(U//FOUO) Implementation of this object can be as low
         as read-only depending on which
         IS Objective or MIB desired requirements are
         not being met by the implementation."
::= { haipeV040101Conformance 8 }

--
-- Objects referenced by the Automated Security Association - IKEv2 and Bandwidth Management IS
--
hAutomatedSAIKEv2ANDBandwidthManagementCapabilityGroup OBJECT-GROUP
    OBJECTS {
                hEstMRCBMValue,
                hBMParamsProfileTableLastChanged,
                hIKEv2CHILDSAEstBMParamsIndex,
                hBMProfileRowStatus,
                hEstRRBucketRate,
                hBMProfileRRBucketSize,
                hIKEv2CHILDSARowStatus,
                hEstBMParamRowStatus,
                hPolicyRuleUseBM,
                hBMProfileRRBMValue,
                hEstRRTimer,
                hEstRRBMValue,
                hBMProfileMRCBMValue,
                hEstRRBucketSize,
                hPolicyRuleRowStatus,
                hBMParamsProfileTableCount,
                hBMProfileRRTimer,
                hBMProfileRRBucketRate
            }
    STATUS    current
    DESCRIPTION
        "(U//FUOUO) Objects for the Automated Security Association - IKEv2 and Bandwidth Management document(s).
         This group is only relevant if the extension is supported"
    ::= { haipeV040101Groups 9 }

--
-- Conformance levels required by the Automated Security Association - IKEv2 and Bandwidth Management IS
--
hAutomatedSAIKEv2ANDBandwidthManagementCapabilityCompliance MODULE-COMPLIANCE
    STATUS    current
    DESCRIPTION
        "(U//FOUO) Compliance levels for objects required by the
         Automated Security Association - IKEv2 and Bandwidth Management document(s)."
    MODULE -- this module
    MANDATORY-GROUPS { hAutomatedSAIKEv2ANDBandwidthManagementCapabilityGroup }

    OBJECT     hEstMRCBMValue
    MIN-ACCESS read-only
    DESCRIPTION
        "(U//FOUO) Implementation of this object can be as low
         as read-only depending on which
         IS Objective or MIB desired requirements are
         not being met by the implementation."

    OBJECT     hBMParamsProfileTableLastChanged
    MIN-ACCESS read-only
    DESCRIPTION
        "(U//FOUO) Implementation of this object can be as low
         as read-only depending on which
         IS Objective or MIB desired requirements are
         not being met by the implementation."

    OBJECT     hIKEv2CHILDSAEstBMParamsIndex
    MIN-ACCESS read-only
    DESCRIPTION
        "(U//FOUO) Implementation of this object can be as low
         as read-only depending on which
         IS Objective or MIB desired requirements are
         not being met by the implementation."

    OBJECT     hBMProfileRowStatus
    MIN-ACCESS read-create
    DESCRIPTION
        "(U//FOUO) Implementation of this object can be as low
         as read-create depending on which
         IS Objective or MIB desired requirements are
         not being met by the implementation."

    OBJECT     hEstRRBucketRate
    MIN-ACCESS read-only
    DESCRIPTION
        "(U//FOUO) Implementation of this object can be as low
         as read-only depending on which
         IS Objective or MIB desired requirements are
         not being met by the implementation."

    OBJECT     hBMProfileRRBucketSize
    MIN-ACCESS read-create
    DESCRIPTION
        "(U//FOUO) Implementation of this object can be as low
         as read-create depending on which
         IS Objective or MIB desired requirements are
         not being met by the implementation."

    OBJECT     hIKEv2CHILDSARowStatus
    MIN-ACCESS read-only
    DESCRIPTION
        "(U//FOUO) Implementation of this object can be as low
         as read-only depending on which
         IS Objective or MIB desired requirements are
         not being met by the implementation."

    OBJECT     hEstBMParamRowStatus
    MIN-ACCESS read-only
    DESCRIPTION
        "(U//FOUO) Implementation of this object can be as low
         as read-only depending on which
         IS Objective or MIB desired requirements are
         not being met by the implementation."

    OBJECT     hPolicyRuleUseBM
    MIN-ACCESS read-create
    DESCRIPTION
        "(U//FOUO) Implementation of this object can be as low
         as read-create depending on which
         IS Objective or MIB desired requirements are
         not being met by the implementation."

    OBJECT     hBMProfileRRBMValue
    MIN-ACCESS read-create
    DESCRIPTION
        "(U//FOUO) Implementation of this object can be as low
         as read-create depending on which
         IS Objective or MIB desired requirements are
         not being met by the implementation."

    OBJECT     hEstRRTimer
    MIN-ACCESS read-only
    DESCRIPTION
        "(U//FOUO) Implementation of this object can be as low
         as read-only depending on which
         IS Objective or MIB desired requirements are
         not being met by the implementation."

    OBJECT     hEstRRBMValue
    MIN-ACCESS read-only
    DESCRIPTION
        "(U//FOUO) Implementation of this object can be as low
         as read-only depending on which
         IS Objective or MIB desired requirements are
         not being met by the implementation."

    OBJECT     hBMProfileMRCBMValue
    MIN-ACCESS read-create
    DESCRIPTION
        "(U//FOUO) Implementation of this object can be as low
         as read-create depending on which
         IS Objective or MIB desired requirements are
         not being met by the implementation."

    OBJECT     hEstRRBucketSize
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hBMParamsProfileTableCount
    MIN-ACCESS read-only
    DESCRIPTION
        "(U//FOUO) Implementation of this object can be as low
         as read-only depending on which
         IS Objective or MIB desired requirements are
         not being met by the implementation."

    OBJECT     hBMProfileRRTimer
    MIN-ACCESS read-create
    DESCRIPTION
        "(U//FOUO) Implementation of this object can be as low
         as read-create depending on which
         IS Objective or MIB desired requirements are
         not being met by the implementation."

    OBJECT     hBMProfileRRBucketRate
    MIN-ACCESS read-create
    DESCRIPTION
        "(U//FOUO) Implementation of this object can be as low
         as read-create depending on which
         IS Objective or MIB desired requirements are
         not being met by the implementation."
::= { haipeV040101Conformance 9 }

--
-- Objects referenced by the Automated Security Association IS
--
hAutomatedSACapabilityGroup OBJECT-GROUP
    OBJECTS {
                hIKEv1ProfileDFBitSetting,
                hIKEv1SADirection,
                hFireFlyRowStatus,
                hEKTableLastChanged,
                hEKKeyIndex,
                hIKEv1SAProfileTableCount,
                hIKEv1ProfileFlowLabelSetting,
                hFireFlyisTestKey,
                hEKType,
                hPolicyRuleRowStatus,
                hIKEv1SAAddressType,
                hIKEv1SADTableLastChanged,
                hIKEv1SARemoteCTAddress,
                hIKEv1NPProfileTableCount,
                hEKGroupName,
                hIKEv1ProfileNtwkParamsRef,
                hIKEv1SAPHRDRate,
                hPEPTRowStatus,
                hIKEv1SADTableCount,
                hFireFlyNationalShortTitle,
                hEKTableCount,
                hIKEv1SARemoteNATDestinationPort,
                hIKEv1SADFBitSetting,
                hEKUniversalID,
                hIKEv1SARowStatus,
                hFireFlyExpirationDate,
                hFireFlyKeyType,
                hIKEv1ProfilePHRDRate,
                hIKEv1SASPI,
                hFireFlyClassification,
                hIKEv1SACTFlowLabelValue,
                hPEPTNATAddress,
                hIKEv1SAPHRDLimit,
                hEKRowStatus,
                hIKEv1SALocalPTAddress,
                hIKEv1SALocalCTAddress,
                hEKEffectiveDate,
                hFireFlyTableCount,
                hIKEv1ProfileFlowLabelValue,
                hIPv4IfaceNATTEnable,
                hFireFlyMaterialType,
                hPEPTRowConfigMethod,
                hIKEv1NtwkParamsProfileRowStatus,
                hFireFlyPartitionCode,
                hIKEv1SAReachabilityStatus,
                hIKEv1SAFlowLabelSetting,
                hIKEv1SAEstTrafficSelectorName,
                hIKEv1ProfilePHRDLimit,
                hPEPTNATPort,
                hIKEv1ProfileTransformSuite,
                hIKEv1NPProfileTableLastChanged,
                hIKEv1SATFCConfigName,
                hIKEv1SARemoteNATAddress,
                hIKEv1SAProfileTableLastChanged,
                hFireFlyTableLastChanged,
                hIPv6IfaceNATTEnable,
                hPrePlacedKeyUsageType,
                hIKEv1SARemotePTAddress,
                hIKEv1SecAttrsProfileRowStatus,
                hPrePlacedKeyRowStatus,
                hIKEv1SADSCPClassifiers,
                hIKEv1SATransformSuite,
                hIKEv1ProfileTFCConfigName,
                hPolicyRuleSecAttrsProfileName
            }
    STATUS    current
    DESCRIPTION
        "(U//FUOUO) Objects for the Automated Security Association document(s).
         This group is only relevant if both extensions are supported"
    ::= { haipeV040101Groups 10 }

--
-- Conformance levels required by the Automated Security Association IS
--
hAutomatedSACapabilityCompliance MODULE-COMPLIANCE
    STATUS    current
    DESCRIPTION
        "(U//FOUO) Compliance levels for objects required by the
         Automated Security Association document(s)."
    MODULE -- this module
    MANDATORY-GROUPS { hAutomatedSACapabilityGroup }

    OBJECT     hIKEv1ProfileDFBitSetting
    MIN-ACCESS read-create
    DESCRIPTION
        "(U//FOUO) Implementation of this object can be as low
         as read-create depending on which
         IS Objective or MIB desired requirements are
         not being met by the implementation."

    OBJECT     hIKEv1SADirection
    MIN-ACCESS read-only
    DESCRIPTION
        "(U//FOUO) Implementation of this object can be as low
         as read-only depending on which
         IS Objective or MIB desired requirements are
         not being met by the implementation."

    OBJECT     hFireFlyRowStatus
    MIN-ACCESS read-write
    DESCRIPTION
        "(U//FOUO) Implementation of this object can be as low
         as read-write depending on which
         IS Objective or MIB desired requirements are
         not being met by the implementation."

    OBJECT     hEKTableLastChanged
    MIN-ACCESS read-only
    DESCRIPTION
        "(U//FOUO) Implementation of this object can be as low
         as read-only depending on which
         IS Objective or MIB desired requirements are
         not being met by the implementation."

    OBJECT     hEKKeyIndex
    MIN-ACCESS read-create
    DESCRIPTION
        "(U//FOUO) Implementation of this object can be as low
         as read-create depending on which
         IS Objective or MIB desired requirements are
         not being met by the implementation."

    OBJECT     hIKEv1SAProfileTableCount
    MIN-ACCESS read-only
    DESCRIPTION
        "(U//FOUO) Implementation of this object can be as low
         as read-only depending on which
         IS Objective or MIB desired requirements are
         not being met by the implementation."

    OBJECT     hIKEv1ProfileFlowLabelSetting
    MIN-ACCESS read-create
    DESCRIPTION
        "(U//FOUO) Implementation of this object can be as low
         as read-create depending on which
         IS Objective or MIB desired requirements are
         not being met by the implementation."

    OBJECT     hFireFlyisTestKey
    MIN-ACCESS read-only
    DESCRIPTION
        "(U//FOUO) Implementation of this object can be as low
         as read-only depending on which
         IS Objective or MIB desired requirements are
         not being met by the implementation."

    OBJECT     hEKType
    MIN-ACCESS read-create
    DESCRIPTION
        "(U//FOUO) Implementation of this object can be as low
         as read-create depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv1SAAddressType
    MIN-ACCESS read-only
    DESCRIPTION
        "(U//FOUO) Implementation of this object can be as low
         as read-only depending on which
         IS Objective or MIB desired requirements are
         not being met by the implementation."

    OBJECT     hIKEv1SADTableLastChanged
    MIN-ACCESS read-only
    DESCRIPTION
        "(U//FOUO) Implementation of this object can be as low
         as read-only depending on which
         IS Objective or MIB desired requirements are
         not being met by the implementation."

    OBJECT     hIKEv1SARemoteCTAddress
    MIN-ACCESS read-only
    DESCRIPTION
        "(U//FOUO) Implementation of this object can be as low
         as read-only depending on which
         IS Objective or MIB desired requirements are
         not being met by the implementation."

    OBJECT     hIKEv1NPProfileTableCount
    MIN-ACCESS read-only
    DESCRIPTION
        "(U//FOUO) Implementation of this object can be as low
         as read-only depending on which
         IS Objective or MIB desired requirements are
         not being met by the implementation."

    OBJECT     hEKGroupName
    MIN-ACCESS read-create
    DESCRIPTION
        "(U//FOUO) Implementation of this object can be as low
         as read-create depending on which
         IS Objective or MIB desired requirements are
         not being met by the implementation."

    OBJECT     hIKEv1ProfileNtwkParamsRef
    MIN-ACCESS read-create
    DESCRIPTION
        "(U//FOUO) Implementation of this object can be as low
         as read-create depending on which
         IS Objective or MIB desired requirements are
         not being met by the implementation."

    OBJECT     hIKEv1SAPHRDRate
    MIN-ACCESS read-only
    DESCRIPTION
        "(U//FOUO) Implementation of this object can be as low
         as read-only depending on which
         IS Objective or MIB desired requirements are
         not being met by the implementation."

    OBJECT     hPEPTRowStatus
    MIN-ACCESS read-only
    DESCRIPTION
        "(U//FOUO) Implementation of this object can be as low
         as read-only depending on which
         IS Objective or MIB desired requirements are
         not being met by the implementation."

    OBJECT     hIKEv1SADTableCount
    MIN-ACCESS read-only
    DESCRIPTION
        "(U//FOUO) Implementation of this object can be as low
         as read-only depending on which
         IS Objective or MIB desired requirements are
         not being met by the implementation."

    OBJECT     hFireFlyNationalShortTitle
    MIN-ACCESS read-only
    DESCRIPTION
        "(U//FOUO) Implementation of this object can be as low
         as read-only depending on which
         IS Objective or MIB desired requirements are
         not being met by the implementation."

    OBJECT     hEKTableCount
    MIN-ACCESS read-only
    DESCRIPTION
        "(U//FOUO) Implementation of this object can be as low
         as read-only depending on which
         IS Objective or MIB desired requirements are
         not being met by the implementation."

    OBJECT     hIKEv1SARemoteNATDestinationPort
    MIN-ACCESS read-only
    DESCRIPTION
        "(U//FOUO) Implementation of this object can be as low
         as read-only depending on which
         IS Objective or MIB desired requirements are
         not being met by the implementation."

    OBJECT     hIKEv1SADFBitSetting
    MIN-ACCESS read-only
    DESCRIPTION
        "(U//FOUO) Implementation of this object can be as low
         as read-only depending on which
         IS Objective or MIB desired requirements are
         not being met by the implementation."

    OBJECT     hEKUniversalID
    MIN-ACCESS read-create
    DESCRIPTION
        "(U//FOUO) Implementation of this object can be as low
         as read-create depending on which
         IS Objective or MIB desired requirements are
         not being met by the implementation."

    OBJECT     hIKEv1SARowStatus
    MIN-ACCESS read-write
    DESCRIPTION
        "(U//FOUO) Implementation of this object can be as low
         as read-write depending on which
         IS Objective or MIB desired requirements are
         not being met by the implementation."

    OBJECT     hFireFlyExpirationDate
    MIN-ACCESS read-only
    DESCRIPTION
        "(U//FOUO) Implementation of this object can be as low
         as read-only depending on which
         IS Objective or MIB desired requirements are
         not being met by the implementation."

    OBJECT     hFireFlyKeyType
    MIN-ACCESS read-only
    DESCRIPTION
        "(U//FOUO) Implementation of this object can be as low
         as read-only depending on which
         IS Objective or MIB desired requirements are
         not being met by the implementation."

    OBJECT     hIKEv1ProfilePHRDRate
    MIN-ACCESS read-create
    DESCRIPTION
        "(U//FOUO) Implementation of this object can be as low
         as read-create depending on which
         IS Objective or MIB desired requirements are
         not being met by the implementation."

    OBJECT     hIKEv1SASPI
    MIN-ACCESS read-only
    DESCRIPTION
        "(U//FOUO) Implementation of this object can be as low
         as read-only depending on which
         IS Objective or MIB desired requirements are
         not being met by the implementation."

    OBJECT     hFireFlyClassification
    MIN-ACCESS read-only
    DESCRIPTION
        "(U//FOUO) Implementation of this object can be as low
         as read-only depending on which
         IS Objective or MIB desired requirements are
         not being met by the implementation."

    OBJECT     hIKEv1SACTFlowLabelValue
    MIN-ACCESS read-only
    DESCRIPTION
        "(U//FOUO) Implementation of this object can be as low
         as read-only depending on which
         IS Objective or MIB desired requirements are
         not being met by the implementation."

    OBJECT     hPEPTNATAddress
    MIN-ACCESS read-only
    DESCRIPTION
        "(U//FOUO) Implementation of this object can be as low
         as read-only depending on which
         IS Objective or MIB desired requirements are
         not being met by the implementation."

    OBJECT     hIKEv1SAPHRDLimit
    MIN-ACCESS read-only
    DESCRIPTION
        "(U//FOUO) Implementation of this object can be as low
         as read-only depending on which
         IS Objective or MIB desired requirements are
         not being met by the implementation."

    OBJECT     hEKRowStatus
    MIN-ACCESS read-create
    DESCRIPTION
        "(U//FOUO) Implementation of this object can be as low
         as read-create depending on which
         IS Objective or MIB desired requirements are
         not being met by the implementation."

    OBJECT     hIKEv1SALocalPTAddress
    MIN-ACCESS read-only
    DESCRIPTION
        "(U//FOUO) Implementation of this object can be as low
         as read-only depending on which
         IS Objective or MIB desired requirements are
         not being met by the implementation."

    OBJECT     hIKEv1SALocalCTAddress
    MIN-ACCESS read-only
    DESCRIPTION
        "(U//FOUO) Implementation of this object can be as low
         as read-only depending on which
         IS Objective or MIB desired requirements are
         not being met by the implementation."

    OBJECT     hEKEffectiveDate
    MIN-ACCESS read-create
    DESCRIPTION
        "(U//FOUO) Implementation of this object can be as low
         as read-create depending on which
         IS Objective or MIB desired requirements are
         not being met by the implementation."

    OBJECT     hFireFlyTableCount
    MIN-ACCESS read-only
    DESCRIPTION
        "(U//FOUO) Implementation of this object can be as low
         as read-only depending on which
         IS Objective or MIB desired requirements are
         not being met by the implementation."

    OBJECT     hIKEv1ProfileFlowLabelValue
    MIN-ACCESS read-create
    DESCRIPTION
        "(U//FOUO) Implementation of this object can be as low
         as read-create depending on which
         IS Objective or MIB desired requirements are
         not being met by the implementation."

    OBJECT     hIPv4IfaceNATTEnable
    MIN-ACCESS read-write
    DESCRIPTION
        "(U//FOUO) Implementation of this object can be as low
         as read-write depending on which
         IS Objective or MIB desired requirements are
         not being met by the implementation."

    OBJECT     hFireFlyMaterialType
    MIN-ACCESS read-only
    DESCRIPTION
        "(U//FOUO) Implementation of this object can be as low
         as read-only depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hIKEv1NtwkParamsProfileRowStatus
    MIN-ACCESS read-create
    DESCRIPTION
        "(U//FOUO) Implementation of this object can be as low
         as read-create depending on which
         IS Objective or MIB desired requirements are
         not being met by the implementation."

    OBJECT     hFireFlyPartitionCode
    MIN-ACCESS read-only
    DESCRIPTION
        "(U//FOUO) Implementation of this object can be as low
         as read-only depending on which
         IS Objective or MIB desired requirements are
         not being met by the implementation."

    OBJECT     hIKEv1SAReachabilityStatus
    MIN-ACCESS read-only
    DESCRIPTION
        "(U//FOUO) Implementation of this object can be as low
         as read-only depending on which
         IS Objective or MIB desired requirements are
         not being met by the implementation."

    OBJECT     hIKEv1SAFlowLabelSetting
    MIN-ACCESS read-only
    DESCRIPTION
        "(U//FOUO) Implementation of this object can be as low
         as read-only depending on which
         IS Objective or MIB desired requirements are
         not being met by the implementation."

    OBJECT     hIKEv1SAEstTrafficSelectorName
    MIN-ACCESS read-only
    DESCRIPTION
        "(U//FOUO) Implementation of this object can be as low
         as read-only depending on which
         IS Objective or MIB desired requirements are
         not being met by the implementation."

    OBJECT     hIKEv1ProfilePHRDLimit
    MIN-ACCESS read-create
    DESCRIPTION
        "(U//FOUO) Implementation of this object can be as low
         as read-create depending on which
         IS Objective or MIB desired requirements are
         not being met by the implementation."

    OBJECT     hPEPTNATPort
    MIN-ACCESS read-only
    DESCRIPTION
        "(U//FOUO) Implementation of this object can be as low
         as read-only depending on which
         IS Objective or MIB desired requirements are
         not being met by the implementation."

    OBJECT     hIKEv1ProfileTransformSuite
    MIN-ACCESS read-create
    DESCRIPTION
        "(U//FOUO) Implementation of this object can be as low
         as read-create depending on which
         IS Objective or MIB desired requirements are
         not being met by the implementation."

    OBJECT     hIKEv1NPProfileTableLastChanged
    MIN-ACCESS read-only
    DESCRIPTION
        "(U//FOUO) Implementation of this object can be as low
         as read-only depending on which
         IS Objective or MIB desired requirements are
         not being met by the implementation."

    OBJECT     hIKEv1SATFCConfigName
    MIN-ACCESS read-only
    DESCRIPTION
        "(U//FOUO) Implementation of this object can be as low
         as read-only depending on which
         IS Objective or MIB desired requirements are
         not being met by the implementation."

    OBJECT     hIKEv1SARemoteNATAddress
    MIN-ACCESS read-only
    DESCRIPTION
        "(U//FOUO) Implementation of this object can be as low
         as read-only depending on which
         IS Objective or MIB desired requirements are
         not being met by the implementation."

    OBJECT     hIKEv1SAProfileTableLastChanged
    MIN-ACCESS read-only
    DESCRIPTION
        "(U//FOUO) Implementation of this object can be as low
         as read-only depending on which
         IS Objective or MIB desired requirements are
         not being met by the implementation."

    OBJECT     hFireFlyTableLastChanged
    MIN-ACCESS read-only
    DESCRIPTION
        "(U//FOUO) Implementation of this object can be as low
         as read-only depending on which
         IS Objective or MIB desired requirements are
         not being met by the implementation."

    OBJECT     hIPv6IfaceNATTEnable
    MIN-ACCESS read-write
    DESCRIPTION
        "(U//FOUO) Implementation of this object can be as low
         as read-write depending on which
         IS Objective or MIB desired requirements are
         not being met by the implementation."

    OBJECT     hPrePlacedKeyUsageType
    MIN-ACCESS read-write
    DESCRIPTION
        "(U//FOUO) Implementation of this object can be as low
         as read-write depending on which
         IS Objective or MIB desired requirements are
         not being met by the implementation."

    OBJECT     hIKEv1SARemotePTAddress
    MIN-ACCESS read-only
    DESCRIPTION
        "(U//FOUO) Implementation of this object can be as low
         as read-only depending on which
         IS Objective or MIB desired requirements are
         not being met by the implementation."

    OBJECT     hIKEv1SecAttrsProfileRowStatus
    MIN-ACCESS read-create
    DESCRIPTION
        "(U//FOUO) Implementation of this object can be as low
         as read-create depending on which
         IS Objective or MIB desired requirements are
         not being met by the implementation."

    OBJECT     hPrePlacedKeyRowStatus
    MIN-ACCESS read-write
    DESCRIPTION
        "(U//FOUO) Implementation of this object can be as low
         as read-write depending on which
         IS Objective or MIB desired requirements are
         not being met by the implementation."

    OBJECT     hIKEv1SADSCPClassifiers
    MIN-ACCESS read-only
    DESCRIPTION
        "(U//FOUO) Implementation of this object can be as low
         as read-only depending on which
         IS Objective or MIB desired requirements are
         not being met by the implementation."

    OBJECT     hIKEv1SATransformSuite
    MIN-ACCESS read-only
    DESCRIPTION
        "(U//FOUO) Implementation of this object can be as low
         as read-only depending on which
         IS Objective or MIB desired requirements are
         not being met by the implementation."

    OBJECT     hIKEv1ProfileTFCConfigName
    MIN-ACCESS read-create
    DESCRIPTION
        "(U//FOUO) Implementation of this object can be as low
         as read-create depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 10 }

--
-- Objects referenced by the Automated Security Association - IKEv2 and Gateway IS
--
hAutomatedSAIKEv2ANDGatewayCapabilityGroup OBJECT-GROUP
    OBJECTS {
                hIKEv2CHILDSAECNSetting,
                hIKEv2CHILDSADFBitSetting,
                hIKEv2CHLDNPPRowStatus,
                hIKEv2CHLDProfileNtwkParamsRef,
                hIKEv2CHILDSARowStatus,
                hIKEv2CHILDSACTDSCPSetting,
                hIKEv2CHILDSACTFlowLabelValue,
                hIKEv2CHILDSAFlowLabelSetting,
                hIKEv2CHLDNPPECNSetting,
                hPolicyRuleRowStatus,
                hIKEv2CHLDNPPFlowLabelSetting,
                hIKEv2CHLDNPPDSCPValue,
                hIKEv2CHLDSecAttrsProfRowStatus,
                hIKEv2CHLDNPPFlowLabelValue,
                hIKEv2CHLDNPPDFBitSetting,
                hIKEv2CHILDSACTDSCPValue,
                hIKEv2CHLDNPPDSCPSetting,
                hPolicyRuleSecAttrsProfileName
            }
    STATUS    current
    DESCRIPTION
        "(U//FUOUO) Objects for the Automated Security Association - IKEv2 and Gateway document(s).
         This group is only relevant if the extension is supported"
    ::= { haipeV040101Groups 11 }

--
-- Conformance levels required by the Automated Security Association - IKEv2 and Gateway IS
--
hAutomatedSAIKEv2ANDGatewayCapabilityCompliance MODULE-COMPLIANCE
    STATUS    current
    DESCRIPTION
        "(U//FOUO) Compliance levels for objects required by the
         Automated Security Association - IKEv2 and Gateway document(s)."
    MODULE -- this module
    MANDATORY-GROUPS { hAutomatedSAIKEv2ANDGatewayCapabilityGroup }

    OBJECT     hIKEv2CHILDSAECNSetting
    MIN-ACCESS read-only
    DESCRIPTION
        "(U//FOUO) Implementation of this object can be as low
         as read-only depending on which
         IS Objective or MIB desired requirements are
         not being met by the implementation."

    OBJECT     hIKEv2CHILDSADFBitSetting
    MIN-ACCESS read-only
    DESCRIPTION
        "(U//FOUO) Implementation of this object can be as low
         as read-only depending on which
         IS Objective or MIB desired requirements are
         not being met by the implementation."

    OBJECT     hIKEv2CHLDNPPRowStatus
    MIN-ACCESS read-create
    DESCRIPTION
        "(U//FOUO) Implementation of this object can be as low
         as read-create depending on which
         IS Objective or MIB desired requirements are
         not being met by the implementation."

    OBJECT     hIKEv2CHLDProfileNtwkParamsRef
    MIN-ACCESS read-create
    DESCRIPTION
        "(U//FOUO) Implementation of this object can be as low
         as read-create depending on which
         IS Objective or MIB desired requirements are
         not being met by the implementation."

    OBJECT     hIKEv2CHILDSARowStatus
    MIN-ACCESS read-only
    DESCRIPTION
        "(U//FOUO) Implementation of this object can be as low
         as read-only depending on which
         IS Objective or MIB desired requirements are
         not being met by the implementation."

    OBJECT     hIKEv2CHILDSACTDSCPSetting
    MIN-ACCESS read-only
    DESCRIPTION
        "(U//FOUO) Implementation of this object can be as low
         as read-only depending on which
         IS Objective or MIB desired requirements are
         not being met by the implementation."

    OBJECT     hIKEv2CHILDSACTFlowLabelValue
    MIN-ACCESS read-only
    DESCRIPTION
        "(U//FOUO) Implementation of this object can be as low
         as read-only depending on which
         IS Objective or MIB desired requirements are
         not being met by the implementation."

    OBJECT     hIKEv2CHILDSAFlowLabelSetting
    MIN-ACCESS read-only
    DESCRIPTION
        "(U//FOUO) Implementation of this object can be as low
         as read-only depending on which
         IS Objective or MIB desired requirements are
         not being met by the implementation."

    OBJECT     hIKEv2CHLDNPPECNSetting
    MIN-ACCESS read-create
    DESCRIPTION
        "(U//FOUO) Implementation of this object can be as low
         as read-create depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv2CHLDNPPFlowLabelSetting
    MIN-ACCESS read-create
    DESCRIPTION
        "(U//FOUO) Implementation of this object can be as low
         as read-create depending on which
         IS Objective or MIB desired requirements are
         not being met by the implementation."

    OBJECT     hIKEv2CHLDNPPDSCPValue
    MIN-ACCESS read-create
    DESCRIPTION
        "(U//FOUO) Implementation of this object can be as low
         as read-create depending on which
         IS Objective or MIB desired requirements are
         not being met by the implementation."

    OBJECT     hIKEv2CHLDSecAttrsProfRowStatus
    MIN-ACCESS read-create
    DESCRIPTION
        "(U//FOUO) Implementation of this object can be as low
         as read-create depending on which
         IS Objective or MIB desired requirements are
         not being met by the implementation."

    OBJECT     hIKEv2CHLDNPPFlowLabelValue
    MIN-ACCESS read-create
    DESCRIPTION
        "(U//FOUO) Implementation of this object can be as low
         as read-create depending on which
         IS Objective or MIB desired requirements are
         not being met by the implementation."

    OBJECT     hIKEv2CHLDNPPDFBitSetting
    MIN-ACCESS read-create
    DESCRIPTION
        "(U//FOUO) Implementation of this object can be as low
         as read-create depending on which
         IS Objective or MIB desired requirements are
         not being met by the implementation."

    OBJECT     hIKEv2CHILDSACTDSCPValue
    MIN-ACCESS read-only
    DESCRIPTION
        "(U//FOUO) Implementation of this object can be as low
         as read-only depending on which
         IS Objective or MIB desired requirements are
         not being met by the implementation."

    OBJECT     hIKEv2CHLDNPPDSCPSetting
    MIN-ACCESS read-create
    DESCRIPTION
        "(U//FOUO) Implementation of this object can be as low
         as read-create depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 11 }

--
-- Objects referenced by the Automated Security Association and Generic Discovery Client IS
--
hAutomatedSAANDGenericDiscoveryClientCapabilityGroup OBJECT-GROUP
    OBJECTS {
                hIKEv1SAPDUNEnabled,
                hIKEv1ProfileNtwkParamsRef,
                hIKEv1SARowStatus,
                hPolicyRuleRowStatus,
                hIKEv1ProfilePDUNEnabled,
                hIKEv1SecAttrsProfileRowStatus,
                hIKEv1NtwkParamsProfileRowStatus,
                hPolicyRuleSecAttrsProfileName
            }
    STATUS    current
    DESCRIPTION
        "(U//FUOUO) Objects for the Automated Security Association and Generic Discovery Client document(s).
         This group is only relevant if the extension is supported"
    ::= { haipeV040101Groups 12 }

--
-- Conformance levels required by the Automated Security Association and Generic Discovery Client IS
--
hAutomatedSAANDGenericDiscoveryClientCapabilityCompliance MODULE-COMPLIANCE
    STATUS    current
    DESCRIPTION
        "(U//FOUO) Compliance levels for objects required by the
         Automated Security Association and Generic Discovery Client document(s)."
    MODULE -- this module
    MANDATORY-GROUPS { hAutomatedSAANDGenericDiscoveryClientCapabilityGroup }

    OBJECT     hIKEv1SAPDUNEnabled
    MIN-ACCESS read-only
    DESCRIPTION
        "(U//FOUO) Implementation of this object can be as low
         as read-only depending on which
         IS Objective or MIB desired requirements are
         not being met by the implementation."

    OBJECT     hIKEv1ProfileNtwkParamsRef
    MIN-ACCESS read-create
    DESCRIPTION
        "(U//FOUO) Implementation of this object can be as low
         as read-create depending on which
         IS Objective or MIB desired requirements are
         not being met by the implementation."

    OBJECT     hIKEv1SARowStatus
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv1ProfilePDUNEnabled
    MIN-ACCESS read-create
    DESCRIPTION
        "(U//FOUO) Implementation of this object can be as low
         as read-create depending on which
         IS Objective or MIB desired requirements are
         not being met by the implementation."

    OBJECT     hIKEv1SecAttrsProfileRowStatus
    MIN-ACCESS read-create
    DESCRIPTION
        "(U//FOUO) Implementation of this object can be as low
         as read-create depending on which
         IS Objective or MIB desired requirements are
         not being met by the implementation."

    OBJECT     hIKEv1NtwkParamsProfileRowStatus
    MIN-ACCESS read-create
    DESCRIPTION
        "(U//FOUO) Implementation of this object can be as low
         as read-create depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 12 }

--
-- Objects referenced by the Reachability IS
--
hReachabilityCapabilityGroup OBJECT-GROUP
    OBJECTS {
                hLearnedLocalPrefixAdminCost,
                hRIPRowStatus,
                hLEPTRowConfigMethod,
                hRIPTableCount,
                hRIPAdvertisementRouteTag,
                hRIPTableLastChanged,
                hRIPDefaultRouteMetric,
                hLEPTRowStatus,
                hRIPSpeakerSetting,
                hRIPAdvertisementRouteMetric,
                hRIPListenerSetting,
                hRIPDefaultRouteAdMode
            }
    STATUS    current
    DESCRIPTION
        "(U//FUOUO) Objects for the Reachability document(s).
         This group is only relevant if both extensions are supported"
    ::= { haipeV040101Groups 13 }

--
-- Conformance levels required by the Reachability IS
--
hReachabilityCapabilityCompliance MODULE-COMPLIANCE
    STATUS    current
    DESCRIPTION
        "(U//FOUO) Compliance levels for objects required by the
         Reachability document(s)."
    MODULE -- this module
    MANDATORY-GROUPS { hReachabilityCapabilityGroup }

    OBJECT     hLearnedLocalPrefixAdminCost
    MIN-ACCESS read-write
    DESCRIPTION
        "(U//FOUO) Implementation of this object can be as low
         as read-write depending on which
         IS Objective or MIB desired requirements are
         not being met by the implementation."

    OBJECT     hRIPRowStatus
    MIN-ACCESS read-create
    DESCRIPTION
        "(U//FOUO) Implementation of this object can be as low
         as read-create depending on which
         IS Objective or MIB desired requirements are
         not being met by the implementation."

    OBJECT     hLEPTRowConfigMethod
    MIN-ACCESS read-only
    DESCRIPTION
        "(U//FOUO) Implementation of this object can be as low
         as read-only depending on which
         IS Objective or MIB desired requirements are
         not being met by the implementation."

    OBJECT     hRIPTableCount
    MIN-ACCESS read-only
    DESCRIPTION
        "(U//FOUO) Implementation of this object can be as low
         as read-only depending on which
         IS Objective or MIB desired requirements are
         not being met by the implementation."

    OBJECT     hRIPAdvertisementRouteTag
    MIN-ACCESS read-create
    DESCRIPTION
        "(U//FOUO) Implementation of this object can be as low
         as read-create depending on which
         IS Objective or MIB desired requirements are
         not being met by the implementation."

    OBJECT     hRIPTableLastChanged
    MIN-ACCESS read-only
    DESCRIPTION
        "(U//FOUO) Implementation of this object can be as low
         as read-only depending on which
         IS Objective or MIB desired requirements are
         not being met by the implementation."

    OBJECT     hRIPDefaultRouteMetric
    MIN-ACCESS read-create
    DESCRIPTION
        "(U//FOUO) Implementation of this object can be as low
         as read-create depending on which
         IS Objective or MIB desired requirements are
         not being met by the implementation."

    OBJECT     hLEPTRowStatus
    MIN-ACCESS read-only
    DESCRIPTION
        "(U//FOUO) Implementation of this object can be as low
         as read-only depending on which
         IS Objective or MIB desired requirements are
         not being met by the implementation."

    OBJECT     hRIPSpeakerSetting
    MIN-ACCESS read-create
    DESCRIPTION
        "(U//FOUO) Implementation of this object can be as low
         as read-create depending on which
         IS Objective or MIB desired requirements are
         not being met by the implementation."

    OBJECT     hRIPAdvertisementRouteMetric
    MIN-ACCESS read-create
    DESCRIPTION
        "(U//FOUO) Implementation of this object can be as low
         as read-create depending on which
         IS Objective or MIB desired requirements are
         not being met by the implementation."

    OBJECT     hRIPListenerSetting
    MIN-ACCESS read-create
    DESCRIPTION
        "(U//FOUO) Implementation of this object can be as low
         as read-create depending on which
         IS Objective or MIB desired requirements are
         not being met by the implementation."

    OBJECT     hRIPDefaultRouteAdMode
    MIN-ACCESS read-create
    DESCRIPTION
        "(U//FOUO) Implementation of this object can be as low
         as read-create depending on which
         IS Objective or MIB desired requirements are
         not being met by the implementation."
::= { haipeV040101Conformance 13 }

--
-- Objects referenced by the Dynamic Multicast Discovery And Keying IS
--
hDMDKCapabilityGroup OBJECT-GROUP
    OBJECTS {
                hDMDKInfoMcastPTIPAddressEnd,
                hDMDKInformationTableCount,
                hDMDKMcastQueryTimeout,
                hDMDKInfoRowStatus,
                hDMDKMcastRegistrationTimeout,
                hDMDKInformationTableLastChanged,
                hDMDKInfoMcastCTIPAddress,
                hDMDKIBKTRequestRetries,
                hDMDKInfoMcastPTIPAddressStart,
                hDMDKInfoGroupLeaderPTIPAddress,
                hDMDKInfoGroupLeaderIPAddrType,
                hDMDKInfoGroupLeaderCTIPAddress,
                hDMDKInfoMcastIPAddrType,
                hDMDKEnableGroupLeadership,
                hDMDKServerPTIPAddress,
                hDMDKMcastRegistrationRetries,
                hDMDKInfoManualSAIndex,
                hDMDKServerPTIPAddrType,
                hDMDKServerPTPort,
                hDMDKMcastQueryRetries,
                hDMDKServerTableLastChanged,
                hDMDKIBKTRequestTimeout,
                hDMDKServerTableCount,
                hDMDKServerRowStatus
            }
    STATUS    current
    DESCRIPTION
        "(U//FUOUO) Objects for the Dynamic Multicast Discovery And Keying document(s).
         This group is only relevant if both extensions are supported"
    ::= { haipeV040101Groups 14 }

--
-- Conformance levels required by the Dynamic Multicast Discovery And Keying IS
--
hDMDKCapabilityCompliance MODULE-COMPLIANCE
    STATUS    current
    DESCRIPTION
        "(U//FOUO) Compliance levels for objects required by the
         Dynamic Multicast Discovery And Keying document(s)."
    MODULE -- this module
    MANDATORY-GROUPS { hDMDKCapabilityGroup }

    OBJECT     hDMDKInfoMcastPTIPAddressEnd
    MIN-ACCESS read-create
    DESCRIPTION
        "(U//FOUO) Implementation of this object can be as low
         as read-create depending on which
         IS Objective or MIB desired requirements are
         not being met by the implementation."

    OBJECT     hDMDKInformationTableCount
    MIN-ACCESS not-accessible
    DESCRIPTION
        "(U//FOUO) Implementation of this object can be as low
         as not-accessible depending on which
         IS Objective or MIB desired requirements are
         not being met by the implementation."

    OBJECT     hDMDKMcastQueryTimeout
    MIN-ACCESS read-write
    DESCRIPTION
        "(U//FOUO) Implementation of this object can be as low
         as read-write depending on which
         IS Objective or MIB desired requirements are
         not being met by the implementation."

    OBJECT     hDMDKInfoRowStatus
    MIN-ACCESS read-create
    DESCRIPTION
        "(U//FOUO) Implementation of this object can be as low
         as read-create depending on which
         IS Objective or MIB desired requirements are
         not being met by the implementation."

    OBJECT     hDMDKMcastRegistrationTimeout
    MIN-ACCESS read-write
    DESCRIPTION
        "(U//FOUO) Implementation of this object can be as low
         as read-write depending on which
         IS Objective or MIB desired requirements are
         not being met by the implementation."

    OBJECT     hDMDKInformationTableLastChanged
    MIN-ACCESS not-accessible
    DESCRIPTION
        "(U//FOUO) Implementation of this object can be as low
         as not-accessible depending on which
         IS Objective or MIB desired requirements are
         not being met by the implementation."

    OBJECT     hDMDKInfoMcastCTIPAddress
    MIN-ACCESS read-create
    DESCRIPTION
        "(U//FOUO) Implementation of this object can be as low
         as read-create depending on which
         IS Objective or MIB desired requirements are
         not being met by the implementation."

    OBJECT     hDMDKIBKTRequestRetries
    MIN-ACCESS read-write
    DESCRIPTION
        "(U//FOUO) Implementation of this object can be as low
         as read-write depending on which
         IS Objective or MIB desired requirements are
         not being met by the implementation."

    OBJECT     hDMDKInfoMcastPTIPAddressStart
    MIN-ACCESS read-create
    DESCRIPTION
        "(U//FOUO) Implementation of this object can be as low
         as read-create depending on which
         IS Objective or MIB desired requirements are
         not being met by the implementation."

    OBJECT     hDMDKInfoGroupLeaderPTIPAddress
    MIN-ACCESS read-create
    DESCRIPTION
        "(U//FOUO) Implementation of this object can be as low
         as read-create depending on which
         IS Objective or MIB desired requirements are
         not being met by the implementation."

    OBJECT     hDMDKInfoGroupLeaderIPAddrType
    MIN-ACCESS read-create
    DESCRIPTION
        "(U//FOUO) Implementation of this object can be as low
         as read-create depending on which
         IS Objective or MIB desired requirements are
         not being met by the implementation."

    OBJECT     hDMDKInfoGroupLeaderCTIPAddress
    MIN-ACCESS read-create
    DESCRIPTION
        "(U//FOUO) Implementation of this object can be as low
         as read-create depending on which
         IS Objective or MIB desired requirements are
         not being met by the implementation."

    OBJECT     hDMDKInfoMcastIPAddrType
    MIN-ACCESS read-create
    DESCRIPTION
        "(U//FOUO) Implementation of this object can be as low
         as read-create depending on which
         IS Objective or MIB desired requirements are
         not being met by the implementation."

    OBJECT     hDMDKEnableGroupLeadership
    MIN-ACCESS read-write
    DESCRIPTION
        "(U//FOUO) Implementation of this object can be as low
         as read-write depending on which
         IS Objective or MIB desired requirements are
         not being met by the implementation."

    OBJECT     hDMDKServerPTIPAddress
    MIN-ACCESS read-create
    DESCRIPTION
        "(U//FOUO) Implementation of this object can be as low
         as read-create depending on which
         IS Objective or MIB desired requirements are
         not being met by the implementation."

    OBJECT     hDMDKMcastRegistrationRetries
    MIN-ACCESS read-write
    DESCRIPTION
        "(U//FOUO) Implementation of this object can be as low
         as read-write depending on which
         IS Objective or MIB desired requirements are
         not being met by the implementation."

    OBJECT     hDMDKInfoManualSAIndex
    MIN-ACCESS read-create
    DESCRIPTION
        "(U//FOUO) Implementation of this object can be as low
         as read-create depending on which
         IS Objective or MIB desired requirements are
         not being met by the implementation."

    OBJECT     hDMDKServerPTIPAddrType
    MIN-ACCESS read-create
    DESCRIPTION
        "(U//FOUO) Implementation of this object can be as low
         as read-create depending on which
         IS Objective or MIB desired requirements are
         not being met by the implementation."

    OBJECT     hDMDKServerPTPort
    MIN-ACCESS read-create
    DESCRIPTION
        "(U//FOUO) Implementation of this object can be as low
         as read-create depending on which
         IS Objective or MIB desired requirements are
         not being met by the implementation."

    OBJECT     hDMDKMcastQueryRetries
    MIN-ACCESS read-write
    DESCRIPTION
        "(U//FOUO) Implementation of this object can be as low
         as read-write depending on which
         IS Objective or MIB desired requirements are
         not being met by the implementation."

    OBJECT     hDMDKServerTableLastChanged
    MIN-ACCESS not-accessible
    DESCRIPTION
        "(U//FOUO) Implementation of this object can be as low
         as not-accessible depending on which
         IS Objective or MIB desired requirements are
         not being met by the implementation."

    OBJECT     hDMDKIBKTRequestTimeout
    MIN-ACCESS read-write
    DESCRIPTION
        "(U//FOUO) Implementation of this object can be as low
         as read-write depending on which
         IS Objective or MIB desired requirements are
         not being met by the implementation."

    OBJECT     hDMDKServerTableCount
    MIN-ACCESS not-accessible
    DESCRIPTION
        "(U//FOUO) Implementation of this object can be as low
         as not-accessible depending on which
         IS Objective or MIB desired requirements are
         not being met by the implementation."

    OBJECT     hDMDKServerRowStatus
    MIN-ACCESS read-create
    DESCRIPTION
        "(U//FOUO) Implementation of this object can be as low
         as read-create depending on which
         IS Objective or MIB desired requirements are
         not being met by the implementation."
::= { haipeV040101Conformance 14 }

--
-- Objects referenced by the Automated Security Association - IKEv2 IS
--
hAutomatedSAIKEv2CapabilityGroup OBJECT-GROUP
    OBJECTS {
                hIKEv2CHILDSADFBitSetting,
                hIKEv2CHLDNPPDFBitSetting,
                hIKEv2CHILDSACTFlowLabelValue,
                hEKKeyIndex,
                hIKEv2CHILDSAFlowLabelSetting,
                hIKEv2CHILDSARemoteNATDestPort,
                hIKEv2CHLDNPPFlowLabelSetting,
                hIKEv2CHILDSAEstTrafficSelName,
                hIKEv2IKESAReachabilityStatus,
                hPolicyRuleRowStatus,
                hIKEv2IKESADTableLastChanged,
                hIKEv2CHILDSADSCPClassifiers,
                hIKEv2CHDSAtProfTableLastChanged,
                hIKEv2CHILDSADirection,
                hIKEv2IKESALocalCTAddress,
                hPEPTRowConfigMethod,
                hIKEv2IKESADTableCount,
                hEKGroupName,
                hIKEv2CHILDSASPI,
                hIKEv2IKESARowStatus,
                hIKEv2CHLDNPPRowStatus,
                hIKEv2CHILDSARowStatus,
                hIKEv2IKESAAddressType,
                hIKEv2CHILDSAReachabilityStatus,
                hPEPTRowStatus,
                hIKEv2CHILDSARemoteNATAddress,
                hIKEv2CHILDSAAddressType,
                hIKEv2CHDNPProfTableLastChanged,
                hIKEv2CHILDSADTableCount,
                hIKEv2IKESARemotePTAddress,
                hIKEv2CHDNPProfTableCount,
                hIKEv2CHLDSecAttrsProfRowStatus,
                hIKEv2IKENPProfTableCount,
                hIKEv2IKESALivenessTestRate,
                hIKEv2CHLDProfileNtwkParamsRef,
                hIKEv2CHLDProfileTransformSuite,
                hIKEv2CHLDProfileEncapMode,
                hEKRowStatus,
                hIKEv2CHLDNPIKENtwkParamsRef,
                hIKEv2CHILDSARemotePTAddress,
                hIKEv2CHLDNPPTFCConfigName,
                hIKEv2IKESATransformSuite,
                hIKEv2CHDSAtProfTableCount,
                hPEPTNATPort,
                hIKEv2CHLDNPPFlowLabelValue,
                hIKEv2IKENPProfTableLastChanged,
                hIKEv2IKESAInitiatorSPI,
                hIKEv2IKESALivenessTestLimit,
                hEKEffectiveDate,
                hIKEv2CHILDSAEncapsulationMode,
                hIKEv2IKENPPLivenessTestRate,
                hIKEv2IKESAResponderSPI,
                hPEPTNATAddress,
                hIKEv2CHILDSALocalCTAddress,
                hIKEv2CHILDSATFCConfigName,
                hPrePlacedKeyEffectiveDate,
                hIKEv2IKESARemoteCTAddress,
                hIKEv2CHILDSATransformSuite,
                hPrePlacedKeyUsageType,
                hIKEv2CHILDSALocalPTAddress,
                hIKEv2IKENPPLivenessTestLimit,
                hIKEv2IKENPPRowStatus,
                hIKEv2IKESALocalPTAddress,
                hIKEv2IKESARemoteNATDestPort,
                hEKType,
                hIKEv2CHILDSARemoteCTAddress,
                hPrePlacedKeyRowStatus,
                hIKEv2CHILDSADTableLastChanged,
                hIKEv2IKESARemoteNATAddress,
                hIKEv2CHILDSAIKESAIndex,
                hPolicyRuleSecAttrsProfileName
            }
    STATUS    current
    DESCRIPTION
        "(U//FUOUO) Objects for the Automated Security Association - IKEv2 document(s).
         This group is only relevant if both extensions are supported"
    ::= { haipeV040101Groups 15 }

--
-- Conformance levels required by the Automated Security Association - IKEv2 IS
--
hAutomatedSAIKEv2CapabilityCompliance MODULE-COMPLIANCE
    STATUS    current
    DESCRIPTION
        "(U//FOUO) Compliance levels for objects required by the
         Automated Security Association - IKEv2 document(s)."
    MODULE -- this module
    MANDATORY-GROUPS { hAutomatedSAIKEv2CapabilityGroup }

    OBJECT     hIKEv2CHILDSADFBitSetting
    MIN-ACCESS read-only
    DESCRIPTION
        "(U//FOUO) Implementation of this object can be as low
         as read-only depending on which
         IS Objective or MIB desired requirements are
         not being met by the implementation."

    OBJECT     hIKEv2CHLDNPPDFBitSetting
    MIN-ACCESS read-create
    DESCRIPTION
        "(U//FOUO) Implementation of this object can be as low
         as read-create depending on which
         IS Objective or MIB desired requirements are
         not being met by the implementation."

    OBJECT     hIKEv2CHILDSACTFlowLabelValue
    MIN-ACCESS read-only
    DESCRIPTION
        "(U//FOUO) Implementation of this object can be as low
         as read-only depending on which
         IS Objective or MIB desired requirements are
         not being met by the implementation."

    OBJECT     hEKKeyIndex
    MIN-ACCESS read-create
    DESCRIPTION
        "(U//FOUO) Implementation of this object can be as low
         as read-create depending on which
         IS Objective or MIB desired requirements are
         not being met by the implementation."

    OBJECT     hIKEv2CHILDSAFlowLabelSetting
    MIN-ACCESS read-only
    DESCRIPTION
        "(U//FOUO) Implementation of this object can be as low
         as read-only depending on which
         IS Objective or MIB desired requirements are
         not being met by the implementation."

    OBJECT     hIKEv2CHILDSARemoteNATDestPort
    MIN-ACCESS read-only
    DESCRIPTION
        "(U//FOUO) Implementation of this object can be as low
         as read-only depending on which
         IS Objective or MIB desired requirements are
         not being met by the implementation."

    OBJECT     hIKEv2CHLDNPPFlowLabelSetting
    MIN-ACCESS read-create
    DESCRIPTION
        "(U//FOUO) Implementation of this object can be as low
         as read-create depending on which
         IS Objective or MIB desired requirements are
         not being met by the implementation."

    OBJECT     hIKEv2CHILDSAEstTrafficSelName
    MIN-ACCESS read-only
    DESCRIPTION
        "(U//FOUO) Implementation of this object can be as low
         as read-only depending on which
         IS Objective or MIB desired requirements are
         not being met by the implementation."

    OBJECT     hIKEv2IKESAReachabilityStatus
    MIN-ACCESS read-only
    DESCRIPTION
        "(U//FOUO) Implementation of this object can be as low
         as read-only depending on which
         IS Objective or MIB desired requirements are
         not being met by the implementation."

    OBJECT     hPolicyRuleRowStatus
    MIN-ACCESS read-create
    DESCRIPTION
        "(U//FOUO) Implementation of this object can be as low
         as read-create depending on which
         IS Objective or MIB desired requirements are
         not being met by the implementation."

    OBJECT     hIKEv2IKESADTableLastChanged
    MIN-ACCESS read-only
    DESCRIPTION
        "(U//FOUO) Implementation of this object can be as low
         as read-only depending on which
         IS Objective or MIB desired requirements are
         not being met by the implementation."

    OBJECT     hIKEv2CHILDSADSCPClassifiers
    MIN-ACCESS read-only
    DESCRIPTION
        "(U//FOUO) Implementation of this object can be as low
         as read-only depending on which
         IS Objective or MIB desired requirements are
         not being met by the implementation."

    OBJECT     hIKEv2CHDSAtProfTableLastChanged
    MIN-ACCESS read-only
    DESCRIPTION
        "(U//FOUO) Implementation of this object can be as low
         as read-only depending on which
         IS Objective or MIB desired requirements are
         not being met by the implementation."

    OBJECT     hIKEv2CHILDSADirection
    MIN-ACCESS read-only
    DESCRIPTION
        "(U//FOUO) Implementation of this object can be as low
         as read-only depending on which
         IS Objective or MIB desired requirements are
         not being met by the implementation."

    OBJECT     hIKEv2IKESALocalCTAddress
    MIN-ACCESS read-only
    DESCRIPTION
        "(U//FOUO) Implementation of this object can be as low
         as read-only depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hIKEv2IKESADTableCount
    MIN-ACCESS read-only
    DESCRIPTION
        "(U//FOUO) Implementation of this object can be as low
         as read-only depending on which
         IS Objective or MIB desired requirements are
         not being met by the implementation."

    OBJECT     hEKGroupName
    MIN-ACCESS read-create
    DESCRIPTION
        "(U//FOUO) Implementation of this object can be as low
         as read-create depending on which
         IS Objective or MIB desired requirements are
         not being met by the implementation."

    OBJECT     hIKEv2CHILDSASPI
    MIN-ACCESS read-only
    DESCRIPTION
        "(U//FOUO) Implementation of this object can be as low
         as read-only depending on which
         IS Objective or MIB desired requirements are
         not being met by the implementation."

    OBJECT     hIKEv2IKESARowStatus
    MIN-ACCESS read-write
    DESCRIPTION
        "(U//FOUO) Implementation of this object can be as low
         as read-write depending on which
         IS Objective or MIB desired requirements are
         not being met by the implementation."

    OBJECT     hIKEv2CHLDNPPRowStatus
    MIN-ACCESS read-create
    DESCRIPTION
        "(U//FOUO) Implementation of this object can be as low
         as read-create depending on which
         IS Objective or MIB desired requirements are
         not being met by the implementation."

    OBJECT     hIKEv2CHILDSARowStatus
    MIN-ACCESS read-write
    DESCRIPTION
        "(U//FOUO) Implementation of this object can be as low
         as read-write depending on which
         IS Objective or MIB desired requirements are
         not being met by the implementation."

    OBJECT     hIKEv2IKESAAddressType
    MIN-ACCESS read-only
    DESCRIPTION
        "(U//FOUO) Implementation of this object can be as low
         as read-only depending on which
         IS Objective or MIB desired requirements are
         not being met by the implementation."

    OBJECT     hIKEv2CHILDSAReachabilityStatus
    MIN-ACCESS read-only
    DESCRIPTION
        "(U//FOUO) Implementation of this object can be as low
         as read-only depending on which
         IS Objective or MIB desired requirements are
         not being met by the implementation."

    OBJECT     hPEPTRowStatus
    MIN-ACCESS read-only
    DESCRIPTION
        "(U//FOUO) Implementation of this object can be as low
         as read-only depending on which
         IS Objective or MIB desired requirements are
         not being met by the implementation."

    OBJECT     hIKEv2CHILDSARemoteNATAddress
    MIN-ACCESS read-only
    DESCRIPTION
        "(U//FOUO) Implementation of this object can be as low
         as read-only depending on which
         IS Objective or MIB desired requirements are
         not being met by the implementation."

    OBJECT     hIKEv2CHILDSAAddressType
    MIN-ACCESS read-only
    DESCRIPTION
        "(U//FOUO) Implementation of this object can be as low
         as read-only depending on which
         IS Objective or MIB desired requirements are
         not being met by the implementation."

    OBJECT     hIKEv2CHDNPProfTableLastChanged
    MIN-ACCESS read-only
    DESCRIPTION
        "(U//FOUO) Implementation of this object can be as low
         as read-only depending on which
         IS Objective or MIB desired requirements are
         not being met by the implementation."

    OBJECT     hIKEv2CHILDSADTableCount
    MIN-ACCESS read-only
    DESCRIPTION
        "(U//FOUO) Implementation of this object can be as low
         as read-only depending on which
         IS Objective or MIB desired requirements are
         not being met by the implementation."

    OBJECT     hIKEv2IKESARemotePTAddress
    MIN-ACCESS read-only
    DESCRIPTION
        "(U//FOUO) Implementation of this object can be as low
         as read-only depending on which
         IS Objective or MIB desired requirements are
         not being met by the implementation."

    OBJECT     hIKEv2CHDNPProfTableCount
    MIN-ACCESS read-only
    DESCRIPTION
        "(U//FOUO) Implementation of this object can be as low
         as read-only depending on which
         IS Objective or MIB desired requirements are
         not being met by the implementation."

    OBJECT     hIKEv2CHLDSecAttrsProfRowStatus
    MIN-ACCESS read-create
    DESCRIPTION
        "(U//FOUO) Implementation of this object can be as low
         as read-create depending on which
         IS Objective or MIB desired requirements are
         not being met by the implementation."

    OBJECT     hIKEv2IKENPProfTableCount
    MIN-ACCESS read-only
    DESCRIPTION
        "(U//FOUO) Implementation of this object can be as low
         as read-only depending on which
         IS Objective or MIB desired requirements are
         not being met by the implementation."

    OBJECT     hIKEv2IKESALivenessTestRate
    MIN-ACCESS read-only
    DESCRIPTION
        "(U//FOUO) Implementation of this object can be as low
         as read-only depending on which
         IS Objective or MIB desired requirements are
         not being met by the implementation."

    OBJECT     hIKEv2CHLDProfileNtwkParamsRef
    MIN-ACCESS read-create
    DESCRIPTION
        "(U//FOUO) Implementation of this object can be as low
         as read-create depending on which
         IS Objective or MIB desired requirements are
         not being met by the implementation."

    OBJECT     hIKEv2CHLDProfileTransformSuite
    MIN-ACCESS read-create
    DESCRIPTION
        "(U//FOUO) Implementation of this object can be as low
         as read-create depending on which
         IS Objective or MIB desired requirements are
         not being met by the implementation."

    OBJECT     hIKEv2CHLDProfileEncapMode
    MIN-ACCESS read-create
    DESCRIPTION
        "(U//FOUO) Implementation of this object can be as low
         as read-create depending on which
         IS Objective or MIB desired requirements are
         not being met by the implementation."

    OBJECT     hEKRowStatus
    MIN-ACCESS read-create
    DESCRIPTION
        "(U//FOUO) Implementation of this object can be as low
         as read-create depending on which
         IS Objective or MIB desired requirements are
         not being met by the implementation."

    OBJECT     hIKEv2CHLDNPIKENtwkParamsRef
    MIN-ACCESS read-create
    DESCRIPTION
        "(U//FOUO) Implementation of this object can be as low
         as read-create depending on which
         IS Objective or MIB desired requirements are
         not being met by the implementation."

    OBJECT     hIKEv2CHILDSARemotePTAddress
    MIN-ACCESS read-only
    DESCRIPTION
        "(U//FOUO) Implementation of this object can be as low
         as read-only depending on which
         IS Objective or MIB desired requirements are
         not being met by the implementation."

    OBJECT     hIKEv2CHLDNPPTFCConfigName
    MIN-ACCESS read-create
    DESCRIPTION
        "(U//FOUO) Implementation of this object can be as low
         as read-create depending on which
         IS Objective or MIB desired requirements are
         not being met by the implementation."

    OBJECT     hIKEv2IKESATransformSuite
    MIN-ACCESS read-only
    DESCRIPTION
        "(U//FOUO) Implementation of this object can be as low
         as read-only depending on which
         IS Objective or MIB desired requirements are
         not being met by the implementation."

    OBJECT     hIKEv2CHDSAtProfTableCount
    MIN-ACCESS read-only
    DESCRIPTION
        "(U//FOUO) Implementation of this object can be as low
         as read-only depending on which
         IS Objective or MIB desired requirements are
         not being met by the implementation."

    OBJECT     hPEPTNATPort
    MIN-ACCESS read-only
    DESCRIPTION
        "(U//FOUO) Implementation of this object can be as low
         as read-only depending on which
         IS Objective or MIB desired requirements are
         not being met by the implementation."

    OBJECT     hIKEv2CHLDNPPFlowLabelValue
    MIN-ACCESS read-create
    DESCRIPTION
        "(U//FOUO) Implementation of this object can be as low
         as read-create depending on which
         IS Objective or MIB desired requirements are
         not being met by the implementation."

    OBJECT     hIKEv2IKENPProfTableLastChanged
    MIN-ACCESS read-only
    DESCRIPTION
        "(U//FOUO) Implementation of this object can be as low
         as read-only depending on which
         IS Objective or MIB desired requirements are
         not being met by the implementation."

    OBJECT     hIKEv2IKESAInitiatorSPI
    MIN-ACCESS read-only
    DESCRIPTION
        "(U//FOUO) Implementation of this object can be as low
         as read-only depending on which
         IS Objective or MIB desired requirements are
         not being met by the implementation."

    OBJECT     hIKEv2IKESALivenessTestLimit
    MIN-ACCESS read-only
    DESCRIPTION
        "(U//FOUO) Implementation of this object can be as low
         as read-only depending on which
         IS Objective or MIB desired requirements are
         not being met by the implementation."

    OBJECT     hEKEffectiveDate
    MIN-ACCESS read-create
    DESCRIPTION
        "(U//FOUO) Implementation of this object can be as low
         as read-create depending on which
         IS Objective or MIB desired requirements are
         not being met by the implementation."

    OBJECT     hIKEv2CHILDSAEncapsulationMode
    MIN-ACCESS read-only
    DESCRIPTION
        "(U//FOUO) Implementation of this object can be as low
         as read-only depending on which
         IS Objective or MIB desired requirements are
         not being met by the implementation."

    OBJECT     hIKEv2IKENPPLivenessTestRate
    MIN-ACCESS read-create
    DESCRIPTION
        "(U//FOUO) Implementation of this object can be as low
         as read-create depending on which
         IS Objective or MIB desired requirements are
         not being met by the implementation."

    OBJECT     hIKEv2IKESAResponderSPI
    MIN-ACCESS read-only
    DESCRIPTION
        "(U//FOUO) Implementation of this object can be as low
         as read-only depending on which
         IS Objective or MIB desired requirements are
         not being met by the implementation."

    OBJECT     hPEPTNATAddress
    MIN-ACCESS read-only
    DESCRIPTION
        "(U//FOUO) Implementation of this object can be as low
         as read-only depending on which
         IS Objective or MIB desired requirements are
         not being met by the implementation."

    OBJECT     hIKEv2CHILDSALocalCTAddress
    MIN-ACCESS read-only
    DESCRIPTION
        "(U//FOUO) Implementation of this object can be as low
         as read-only depending on which
         IS Objective or MIB desired requirements are
         not being met by the implementation."

    OBJECT     hIKEv2CHILDSATFCConfigName
    MIN-ACCESS read-only
    DESCRIPTION
        "(U//FOUO) Implementation of this object can be as low
         as read-only depending on which
         IS Objective or MIB desired requirements are
         not being met by the implementation."

    OBJECT     hPrePlacedKeyEffectiveDate
    MIN-ACCESS read-write
    DESCRIPTION
        "(U//FOUO) Implementation of this object can be as low
         as read-write depending on which
         IS Objective or MIB desired requirements are
         not being met by the implementation."

    OBJECT     hIKEv2IKESARemoteCTAddress
    MIN-ACCESS read-only
    DESCRIPTION
        "(U//FOUO) Implementation of this object can be as low
         as read-only depending on which
         IS Objective or MIB desired requirements are
         not being met by the implementation."

    OBJECT     hIKEv2CHILDSATransformSuite
    MIN-ACCESS read-only
    DESCRIPTION
        "(U//FOUO) Implementation of this object can be as low
         as read-only depending on which
         IS Objective or MIB desired requirements are
         not being met by the implementation."

    OBJECT     hPrePlacedKeyUsageType
    MIN-ACCESS read-write
    DESCRIPTION
        "(U//FOUO) Implementation of this object can be as low
         as read-write depending on which
         IS Objective or MIB desired requirements are
         not being met by the implementation."

    OBJECT     hIKEv2CHILDSALocalPTAddress
    MIN-ACCESS read-only
    DESCRIPTION
        "(U//FOUO) Implementation of this object can be as low
         as read-only depending on which
         IS Objective or MIB desired requirements are
         not being met by the implementation."

    OBJECT     hIKEv2IKENPPLivenessTestLimit
    MIN-ACCESS read-create
    DESCRIPTION
        "(U//FOUO) Implementation of this object can be as low
         as read-create depending on which
         IS Objective or MIB desired requirements are
         not being met by the implementation."

    OBJECT     hIKEv2IKENPPRowStatus
    MIN-ACCESS read-create
    DESCRIPTION
        "(U//FOUO) Implementation of this object can be as low
         as read-create depending on which
         IS Objective or MIB desired requirements are
         not being met by the implementation."

    OBJECT     hIKEv2IKESALocalPTAddress
    MIN-ACCESS read-only
    DESCRIPTION
        "(U//FOUO) Implementation of this object can be as low
         as read-only depending on which
         IS Objective or MIB desired requirements are
         not being met by the implementation."

    OBJECT     hIKEv2IKESARemoteNATDestPort
    MIN-ACCESS read-only
    DESCRIPTION
        "(U//FOUO) Implementation of this object can be as low
         as read-only depending on which
         IS Objective or MIB desired requirements are
         not being met by the implementation."

    OBJECT     hEKType
    MIN-ACCESS read-create
    DESCRIPTION
        "(U//FOUO) Implementation of this object can be as low
         as read-create depending on which
         IS Objective or MIB desired requirements are
         not being met by the implementation."

    OBJECT     hIKEv2CHILDSARemoteCTAddress
    MIN-ACCESS read-only
    DESCRIPTION
        "(U//FOUO) Implementation of this object can be as low
         as read-only depending on which
         IS Objective or MIB desired requirements are
         not being met by the implementation."

    OBJECT     hPrePlacedKeyRowStatus
    MIN-ACCESS read-write
    DESCRIPTION
        "(U//FOUO) Implementation of this object can be as low
         as read-write depending on which
         IS Objective or MIB desired requirements are
         not being met by the implementation."

    OBJECT     hIKEv2CHILDSADTableLastChanged
    MIN-ACCESS read-only
    DESCRIPTION
        "(U//FOUO) Implementation of this object can be as low
         as read-only depending on which
         IS Objective or MIB desired requirements are
         not being met by the implementation."

    OBJECT     hIKEv2IKESARemoteNATAddress
    MIN-ACCESS read-only
    DESCRIPTION
        "(U//FOUO) Implementation of this object can be as low
         as read-only depending on which
         IS Objective or MIB desired requirements are
         not being met by the implementation."

    OBJECT     hIKEv2CHILDSAIKESAIndex
    MIN-ACCESS read-only
    DESCRIPTION
        "(U//FOUO) Implementation of this object can be as low
         as read-only depending on which
         IS Objective or MIB desired requirements are
         not being met by the implementation."

    OBJECT     hPolicyRuleSecAttrsProfileName
    MIN-ACCESS read-create
    DESCRIPTION
        "(U//FOUO) Implementation of this object can be as low
         as read-create depending on which
         IS Objective or MIB desired requirements are
         not being met by the implementation."
::= { haipeV040101Conformance 15 }

--
-- Objects referenced by the Implicit Peer Enclave Prefix Discovery IS
--
hImplicitPeerEnclavePrefixDiscoveryCapabilityGroup OBJECT-GROUP
    OBJECTS {
                hIMPEPDifPTtoInterfaceMapping,
                hPEPTRowStatus,
                hIMPEPDifTableCount,
                hIMPEPDifPTSubIdentifier,
                hIMPEPDifRowStatus,
                hIMPEPDifCTtoInterfaceMapping,
                hIMPEPDTableCount,
                hIMPEPDifCTSubIdentifier,
                hIMPEPDifTableLastChanged,
                hIMPEPDTableLastChanged,
                hPEPTRowConfigMethod,
                hIMPEPDifSegmentedCore,
                hIMPEPDRowStatus
            }
    STATUS    current
    DESCRIPTION
        "(U//FUOUO) Objects for the Implicit Peer Enclave Prefix Discovery document(s).
         This group is only relevant if both extensions are supported"
    ::= { haipeV040101Groups 16 }

--
-- Conformance levels required by the Implicit Peer Enclave Prefix Discovery IS
--
hImplicitPeerEnclavePrefixDiscoveryCapabilityCompliance MODULE-COMPLIANCE
    STATUS    current
    DESCRIPTION
        "(U//FOUO) Compliance levels for objects required by the
         Implicit Peer Enclave Prefix Discovery document(s)."
    MODULE -- this module
    MANDATORY-GROUPS { hImplicitPeerEnclavePrefixDiscoveryCapabilityGroup }

    OBJECT     hIMPEPDifPTtoInterfaceMapping
    MIN-ACCESS read-create
    DESCRIPTION
        "(U//FOUO) Implementation of this object can be as low
         as read-create depending on which
         IS Objective or MIB desired requirements are
         not being met by the implementation."

    OBJECT     hPEPTRowStatus
    MIN-ACCESS read-only
    DESCRIPTION
        "(U//FOUO) Implementation of this object can be as low
         as read-only depending on which
         IS Objective or MIB desired requirements are
         not being met by the implementation."

    OBJECT     hIMPEPDifTableCount
    MIN-ACCESS read-only
    DESCRIPTION
        "(U//FOUO) Implementation of this object can be as low
         as read-only depending on which
         IS Objective or MIB desired requirements are
         not being met by the implementation."

    OBJECT     hIMPEPDifPTSubIdentifier
    MIN-ACCESS read-create
    DESCRIPTION
        "(U//FOUO) Implementation of this object can be as low
         as read-create depending on which
         IS Objective or MIB desired requirements are
         not being met by the implementation."

    OBJECT     hIMPEPDifRowStatus
    MIN-ACCESS read-create
    DESCRIPTION
        "(U//FOUO) Implementation of this object can be as low
         as read-create depending on which
         IS Objective or MIB desired requirements are
         not being met by the implementation."

    OBJECT     hIMPEPDifCTtoInterfaceMapping
    MIN-ACCESS read-create
    DESCRIPTION
        "(U//FOUO) Implementation of this object can be as low
         as read-create depending on which
         IS Objective or MIB desired requirements are
         not being met by the implementation."

    OBJECT     hIMPEPDTableCount
    MIN-ACCESS read-only
    DESCRIPTION
        "(U//FOUO) Implementation of this object can be as low
         as read-only depending on which
         IS Objective or MIB desired requirements are
         not being met by the implementation."

    OBJECT     hIMPEPDifCTSubIdentifier
    MIN-ACCESS read-create
    DESCRIPTION
        "(U//FOUO) Implementation of this object can be as low
         as read-create depending on which
         IS Objective or MIB desired requirements are
         not being met by the implementation."

    OBJECT     hIMPEPDifTableLastChanged
    MIN-ACCESS read-only
    DESCRIPTION
        "(U//FOUO) Implementation of this object can be as low
         as read-only depending on which
         IS Objective or MIB desired requirements are
         not being met by the implementation."

    OBJECT     hIMPEPDTableLastChanged
    MIN-ACCESS read-only
    DESCRIPTION
        "(U//FOUO) Implementation of this object can be as low
         as read-only depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hIMPEPDifSegmentedCore
    MIN-ACCESS read-create
    DESCRIPTION
        "(U//FOUO) Implementation of this object can be as low
         as read-create depending on which
         IS Objective or MIB desired requirements are
         not being met by the implementation."

    OBJECT     hIMPEPDRowStatus
    MIN-ACCESS read-create
    DESCRIPTION
        "(U//FOUO) Implementation of this object can be as low
         as read-create depending on which
         IS Objective or MIB desired requirements are
         not being met by the implementation."
::= { haipeV040101Conformance 16 }

--
-- Objects referenced by the Remote Provisioning Authority IS
--
hRemoteProvisioningCapabilityGroup OBJECT-GROUP
    OBJECTS {
                hFirmwareDwnldAdminStatus,
                hFwDwnldServerTableCount,
                hKTAuthCtrlsAddressType,
                hLoadedKeyTableLastChanged,
                hTFTPDesiredBlkSize,
                hFirmwareDwnldStatus,
                hFwDwnldServerRowStatus,
                hLoadedKeyText,
                hFwDwnldServerURI,
                hTFTPDesiredTimeout,
                hFwDwnldServerSide,
                hLoadedKeyUse,
                hLoadedKeyTableCount,
                hKTAuthCtrlsRowStatus,
                hFwDwnldServerTableLastChanged,
                hLoadedKeyAction,
                hLoadedKeyClassification,
                hLoadedKeyRowStatus,
                hKTAuthCtrlsAddress
            }
    STATUS    current
    DESCRIPTION
        "(U//FUOUO) Objects for the Remote Provisioning Authority document(s).
         This group is only relevant if both extensions are supported"
    ::= { haipeV040101Groups 17 }

--
-- Conformance levels required by the Remote Provisioning Authority IS
--
hRemoteProvisioningCapabilityCompliance MODULE-COMPLIANCE
    STATUS    current
    DESCRIPTION
        "(U//FOUO) Compliance levels for objects required by the
         Remote Provisioning Authority document(s)."
    MODULE -- this module
    MANDATORY-GROUPS { hRemoteProvisioningCapabilityGroup }

    OBJECT     hFirmwareDwnldAdminStatus
    MIN-ACCESS read-write
    DESCRIPTION
        "(U//FOUO) Implementation of this object can be as low
         as read-write depending on which
         IS Objective or MIB desired requirements are
         not being met by the implementation."

    OBJECT     hFwDwnldServerTableCount
    MIN-ACCESS read-only
    DESCRIPTION
        "(U//FOUO) Implementation of this object can be as low
         as read-only depending on which
         IS Objective or MIB desired requirements are
         not being met by the implementation."

    OBJECT     hKTAuthCtrlsAddressType
    MIN-ACCESS read-create
    DESCRIPTION
        "(U//FOUO) Implementation of this object can be as low
         as read-create depending on which
         IS Objective or MIB desired requirements are
         not being met by the implementation."

    OBJECT     hLoadedKeyTableLastChanged
    MIN-ACCESS read-only
    DESCRIPTION
        "(U//FOUO) Implementation of this object can be as low
         as read-only depending on which
         IS Objective or MIB desired requirements are
         not being met by the implementation."

    OBJECT     hTFTPDesiredBlkSize
    MIN-ACCESS read-write
    DESCRIPTION
        "(U//FOUO) Implementation of this object can be as low
         as read-write depending on which
         IS Objective or MIB desired requirements are
         not being met by the implementation."

    OBJECT     hFirmwareDwnldStatus
    MIN-ACCESS read-only
    DESCRIPTION
        "(U//FOUO) Implementation of this object can be as low
         as read-only depending on which
         IS Objective or MIB desired requirements are
         not being met by the implementation."

    OBJECT     hFwDwnldServerRowStatus
    MIN-ACCESS read-create
    DESCRIPTION
        "(U//FOUO) Implementation of this object can be as low
         as read-create depending on which
         IS Objective or MIB desired requirements are
         not being met by the implementation."

    OBJECT     hLoadedKeyText
    MIN-ACCESS read-only
    DESCRIPTION
        "(U//FOUO) Implementation of this object can be as low
         as read-only depending on which
         IS Objective or MIB desired requirements are
         not being met by the implementation."

    OBJECT     hFwDwnldServerURI
    MIN-ACCESS read-create
    DESCRIPTION
        "(U//FOUO) Implementation of this object can be as low
         as read-create depending on which
         IS Objective or MIB desired requirements are
         not being met by the implementation."

    OBJECT     hTFTPDesiredTimeout
    MIN-ACCESS read-write
    DESCRIPTION
        "(U//FOUO) Implementation of this object can be as low
         as read-write depending on which
         IS Objective or MIB desired requirements are
         not being met by the implementation."

    OBJECT     hFwDwnldServerSide
    MIN-ACCESS read-create
    DESCRIPTION
        "(U//FOUO) Implementation of this object can be as low
         as read-create depending on which
         IS Objective or MIB desired requirements are
         not being met by the implementation."

    OBJECT     hLoadedKeyUse
    MIN-ACCESS read-only
    DESCRIPTION
        "(U//FOUO) Implementation of this object can be as low
         as read-only depending on which
         IS Objective or MIB desired requirements are
         not being met by the implementation."

    OBJECT     hLoadedKeyTableCount
    MIN-ACCESS read-only
    DESCRIPTION
        "(U//FOUO) Implementation of this object can be as low
         as read-only depending on which
         IS Objective or MIB desired requirements are
         not being met by the implementation."

    OBJECT     hKTAuthCtrlsRowStatus
    MIN-ACCESS read-create
    DESCRIPTION
        "(U//FOUO) Implementation of this object can be as low
         as read-create depending on which
         IS Objective or MIB desired requirements are
         not being met by the implementation."

    OBJECT     hFwDwnldServerTableLastChanged
    MIN-ACCESS read-only
    DESCRIPTION
        "(U//FOUO) Implementation of this object can be as low
         as read-only depending on which
         IS Objective or MIB desired requirements are
         not being met by the implementation."

    OBJECT     hLoadedKeyAction
    MIN-ACCESS read-write
    DESCRIPTION
        "(U//FOUO) Implementation of this object can be as low
         as read-write depending on which
         IS Objective or MIB desired requirements are
         not being met by the implementation."

    OBJECT     hLoadedKeyClassification
    MIN-ACCESS read-only
    DESCRIPTION
        "(U//FOUO) Implementation of this object can be as low
         as read-only depending on which
         IS Objective or MIB desired requirements are
         not being met by the implementation."

    OBJECT     hLoadedKeyRowStatus
    MIN-ACCESS read-only
    DESCRIPTION
        "(U//FOUO) Implementation of this object can be as low
         as read-only depending on which
         IS Objective or MIB desired requirements are
         not being met by the implementation."

    OBJECT     hKTAuthCtrlsAddress
    MIN-ACCESS read-create
    DESCRIPTION
        "(U//FOUO) Implementation of this object can be as low
         as read-create depending on which
         IS Objective or MIB desired requirements are
         not being met by the implementation."
::= { haipeV040101Conformance 17 }

--
-- Objects referenced by the Generic Discovery Client IS
--
hGenericDiscoveryClientCapabilityGroup OBJECT-GROUP
    OBJECTS {
                hManualSARowStatus,
                hGDCReceptionTableCount,
                hGDCSolicitDelivDestPTPort,
                hGDCReceptionRowStatus,
                hGDCSolicitDelivRetryCount,
                hPEPTRowConfigMethod,
                hGDCRegistrationRetryCount,
                hLEPTRowLifetime,
                hGDCSolicitDelivTableLastChanged,
                hGDCSolicitDelivRowStatus,
                hLEPTAdminCost,
                hGDCSolicitDelivDestPTAddress,
                hPEPTRowStatus,
                hGDCReceptionTableLastChanged,
                hLEPTRowStatus,
                hGDCSolicitDelivTimeout,
                hPEPTPrefixLifetime,
                hGDCSolicitDelivDestPTAddrType,
                hGDCRegistrationTableCount,
                hPEPTAdminCost,
                hGDCRegistrationTableLastChanged,
                hManualSAPDUNEnabled,
                hGDCRegistrationTimeout,
                hGDCSolicitDelivTableCount,
                hGDCRegistrationRowStatus
            }
    STATUS    current
    DESCRIPTION
        "(U//FUOUO) Objects for the Generic Discovery Client document(s).
         This group is only relevant if both extensions are supported"
    ::= { haipeV040101Groups 18 }

--
-- Conformance levels required by the Generic Discovery Client IS
--
hGenericDiscoveryClientCapabilityCompliance MODULE-COMPLIANCE
    STATUS    current
    DESCRIPTION
        "(U//FOUO) Compliance levels for objects required by the
         Generic Discovery Client document(s)."
    MODULE -- this module
    MANDATORY-GROUPS { hGenericDiscoveryClientCapabilityGroup }

    OBJECT     hManualSARowStatus
    MIN-ACCESS read-create
    DESCRIPTION
        "(U//FOUO) Implementation of this object can be as low
         as read-create depending on which
         IS Objective or MIB desired requirements are
         not being met by the implementation."

    OBJECT     hGDCReceptionTableCount
    MIN-ACCESS read-only
    DESCRIPTION
        "(U//FOUO) Implementation of this object can be as low
         as read-only depending on which
         IS Objective or MIB desired requirements are
         not being met by the implementation."

    OBJECT     hGDCSolicitDelivDestPTPort
    MIN-ACCESS read-create
    DESCRIPTION
        "(U//FOUO) Implementation of this object can be as low
         as read-create depending on which
         IS Objective or MIB desired requirements are
         not being met by the implementation."

    OBJECT     hGDCReceptionRowStatus
    MIN-ACCESS read-create
    DESCRIPTION
        "(U//FOUO) Implementation of this object can be as low
         as read-create depending on which
         IS Objective or MIB desired requirements are
         not being met by the implementation."

    OBJECT     hGDCSolicitDelivRetryCount
    MIN-ACCESS read-write
    DESCRIPTION
        "(U//FOUO) Implementation of this object can be as low
         as read-write depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hGDCRegistrationRetryCount
    MIN-ACCESS read-write
    DESCRIPTION
        "(U//FOUO) Implementation of this object can be as low
         as read-write depending on which
         IS Objective or MIB desired requirements are
         not being met by the implementation."

    OBJECT     hLEPTRowLifetime
    MIN-ACCESS read-only
    DESCRIPTION
        "(U//FOUO) Implementation of this object can be as low
         as read-only depending on which
         IS Objective or MIB desired requirements are
         not being met by the implementation."

    OBJECT     hGDCSolicitDelivTableLastChanged
    MIN-ACCESS read-only
    DESCRIPTION
        "(U//FOUO) Implementation of this object can be as low
         as read-only depending on which
         IS Objective or MIB desired requirements are
         not being met by the implementation."

    OBJECT     hGDCSolicitDelivRowStatus
    MIN-ACCESS read-create
    DESCRIPTION
        "(U//FOUO) Implementation of this object can be as low
         as read-create depending on which
         IS Objective or MIB desired requirements are
         not being met by the implementation."

    OBJECT     hLEPTAdminCost
    MIN-ACCESS read-only
    DESCRIPTION
        "(U//FOUO) Implementation of this object can be as low
         as read-only depending on which
         IS Objective or MIB desired requirements are
         not being met by the implementation."

    OBJECT     hGDCSolicitDelivDestPTAddress
    MIN-ACCESS read-create
    DESCRIPTION
        "(U//FOUO) Implementation of this object can be as low
         as read-create depending on which
         IS Objective or MIB desired requirements are
         not being met by the implementation."

    OBJECT     hPEPTRowStatus
    MIN-ACCESS read-create
    DESCRIPTION
        "(U//FOUO) Implementation of this object can be as low
         as read-create depending on which
         IS Objective or MIB desired requirements are
         not being met by the implementation."

    OBJECT     hGDCReceptionTableLastChanged
    MIN-ACCESS read-only
    DESCRIPTION
        "(U//FOUO) Implementation of this object can be as low
         as read-only depending on which
         IS Objective or MIB desired requirements are
         not being met by the implementation."

    OBJECT     hLEPTRowStatus
    MIN-ACCESS read-only
    DESCRIPTION
        "(U//FOUO) Implementation of this object can be as low
         as read-only depending on which
         IS Objective or MIB desired requirements are
         not being met by the implementation."

    OBJECT     hGDCSolicitDelivTimeout
    MIN-ACCESS read-write
    DESCRIPTION
        "(U//FOUO) Implementation of this object can be as low
         as read-write depending on which
         IS Objective or MIB desired requirements are
         not being met by the implementation."

    OBJECT     hPEPTPrefixLifetime
    MIN-ACCESS read-only
    DESCRIPTION
        "(U//FOUO) Implementation of this object can be as low
         as read-only depending on which
         IS Objective or MIB desired requirements are
         not being met by the implementation."

    OBJECT     hGDCSolicitDelivDestPTAddrType
    MIN-ACCESS read-create
    DESCRIPTION
        "(U//FOUO) Implementation of this object can be as low
         as read-create depending on which
         IS Objective or MIB desired requirements are
         not being met by the implementation."

    OBJECT     hGDCRegistrationTableCount
    MIN-ACCESS read-only
    DESCRIPTION
        "(U//FOUO) Implementation of this object can be as low
         as read-only depending on which
         IS Objective or MIB desired requirements are
         not being met by the implementation."

    OBJECT     hPEPTAdminCost
    MIN-ACCESS read-create
    DESCRIPTION
        "(U//FOUO) Implementation of this object can be as low
         as read-create depending on which
         IS Objective or MIB desired requirements are
         not being met by the implementation."

    OBJECT     hGDCRegistrationTableLastChanged
    MIN-ACCESS read-only
    DESCRIPTION
        "(U//FOUO) Implementation of this object can be as low
         as read-only depending on which
         IS Objective or MIB desired requirements are
         not being met by the implementation."

    OBJECT     hManualSAPDUNEnabled
    MIN-ACCESS read-create
    DESCRIPTION
        "(U//FOUO) Implementation of this object can be as low
         as read-create depending on which
         IS Objective or MIB desired requirements are
         not being met by the implementation."

    OBJECT     hGDCRegistrationTimeout
    MIN-ACCESS read-write
    DESCRIPTION
        "(U//FOUO) Implementation of this object can be as low
         as read-write depending on which
         IS Objective or MIB desired requirements are
         not being met by the implementation."

    OBJECT     hGDCSolicitDelivTableCount
    MIN-ACCESS read-only
    DESCRIPTION
        "(U//FOUO) Implementation of this object can be as low
         as read-only depending on which
         IS Objective or MIB desired requirements are
         not being met by the implementation."

    OBJECT     hGDCRegistrationRowStatus
    MIN-ACCESS read-create
    DESCRIPTION
        "(U//FOUO) Implementation of this object can be as low
         as read-create depending on which
         IS Objective or MIB desired requirements are
         not being met by the implementation."
::= { haipeV040101Conformance 18 }

--
-- Objects referenced by the Gateway IS
--
hGatewayCapabilityGroup OBJECT-GROUP
    OBJECTS {
                hManualSARowStatus,
                hIPv6RouterAdverEnable,
                hIGMPSupportMode,
                hIPv6RouterAdverDefLifetime,
                hCIDRRouteIfIndex,
                hManualSADFBitSetting,
                hIPv6RouterAdverRetransTime,
                hIPv6RouterAdverRowStatus,
                hCIDRRouteRowStatus,
                hIPv6RouterAdverHopLimit,
                hManualSACTDSCPValue,
                hManualSACTFlowLabelValue,
                hIPv6RouterAdverConfigFlag,
                hMLDSupportMode,
                hIPv6RouterAdverReachableTime,
                hIPv6RouterAdverTableCount,
                hIPv6RouterAdverMTU,
                hIPv6RouterAdverManagedFlag,
                hManualSAFlowLabelSetting,
                hManualSACTDSCPSetting,
                hCIDRRouteType,
                hIPv6RouterAdverTableLastChanged,
                hCIDRRouteProtocol,
                hCIDRRouteMetric,
                hManualSAECNSetting,
                hIPv6RouterAdverMaxInterval,
                hIPv6RouterAdverMinInterval
            }
    STATUS    current
    DESCRIPTION
        "(U//FUOUO) Objects for the Gateway document(s).
         This group is only relevant if both extensions are supported"
    ::= { haipeV040101Groups 19 }

--
-- Conformance levels required by the Gateway IS
--
hGatewayCapabilityCompliance MODULE-COMPLIANCE
    STATUS    current
    DESCRIPTION
        "(U//FOUO) Compliance levels for objects required by the
         Gateway document(s)."
    MODULE -- this module
    MANDATORY-GROUPS { hGatewayCapabilityGroup }

    OBJECT     hManualSARowStatus
    MIN-ACCESS read-create
    DESCRIPTION
        "(U//FOUO) Implementation of this object can be as low
         as read-create depending on which
         IS Objective or MIB desired requirements are
         not being met by the implementation."

    OBJECT     hIPv6RouterAdverEnable
    MIN-ACCESS read-create
    DESCRIPTION
        "(U//FOUO) Implementation of this object can be as low
         as read-create depending on which
         IS Objective or MIB desired requirements are
         not being met by the implementation."

    OBJECT     hIGMPSupportMode
    MIN-ACCESS read-write
    DESCRIPTION
        "(U//FOUO) Implementation of this object can be as low
         as read-write depending on which
         IS Objective or MIB desired requirements are
         not being met by the implementation."

    OBJECT     hIPv6RouterAdverDefLifetime
    MIN-ACCESS read-create
    DESCRIPTION
        "(U//FOUO) Implementation of this object can be as low
         as read-create depending on which
         IS Objective or MIB desired requirements are
         not being met by the implementation."

    OBJECT     hCIDRRouteIfIndex
    MIN-ACCESS read-create
    DESCRIPTION
        "(U//FOUO) Implementation of this object can be as low
         as read-create depending on which
         IS Objective or MIB desired requirements are
         not being met by the implementation."

    OBJECT     hManualSADFBitSetting
    MIN-ACCESS read-create
    DESCRIPTION
        "(U//FOUO) Implementation of this object can be as low
         as read-create depending on which
         IS Objective or MIB desired requirements are
         not being met by the implementation."

    OBJECT     hIPv6RouterAdverRetransTime
    MIN-ACCESS read-create
    DESCRIPTION
        "(U//FOUO) Implementation of this object can be as low
         as read-create depending on which
         IS Objective or MIB desired requirements are
         not being met by the implementation."

    OBJECT     hIPv6RouterAdverRowStatus
    MIN-ACCESS read-create
    DESCRIPTION
        "(U//FOUO) Implementation of this object can be as low
         as read-create depending on which
         IS Objective or MIB desired requirements are
         not being met by the implementation."

    OBJECT     hCIDRRouteRowStatus
    MIN-ACCESS read-create
    DESCRIPTION
        "(U//FOUO) Implementation of this object can be as low
         as read-create depending on which
         IS Objective or MIB desired requirements are
         not being met by the implementation."

    OBJECT     hIPv6RouterAdverHopLimit
    MIN-ACCESS read-create
    DESCRIPTION
        "(U//FOUO) Implementation of this object can be as low
         as read-create depending on which
         IS Objective or MIB desired requirements are
         not being met by the implementation."

    OBJECT     hManualSACTDSCPValue
    MIN-ACCESS read-create
    DESCRIPTION
        "(U//FOUO) Implementation of this object can be as low
         as read-create depending on which
         IS Objective or MIB desired requirements are
         not being met by the implementation."

    OBJECT     hManualSACTFlowLabelValue
    MIN-ACCESS read-create
    DESCRIPTION
        "(U//FOUO) Implementation of this object can be as low
         as read-create depending on which
         IS Objective or MIB desired requirements are
         not being met by the implementation."

    OBJECT     hIPv6RouterAdverConfigFlag
    MIN-ACCESS read-create
    DESCRIPTION
        "(U//FOUO) Implementation of this object can be as low
         as read-create depending on which
         IS Objective or MIB desired requirements are
         not being met by the implementation."

    OBJECT     hMLDSupportMode
    MIN-ACCESS read-write
    DESCRIPTION
        "(U//FOUO) Implementation of this object can be as low
         as read-write depending on which
         IS Objective or MIB desired requirements are
         not being met by the implementation."

    OBJECT     hIPv6RouterAdverReachableTime
    MIN-ACCESS read-create
    DESCRIPTION
        "(U//FOUO) Implementation of this object can be as low
         as read-create depending on which
         IS Objective or MIB desired requirements are
         not being met by the implementation."

    OBJECT     hIPv6RouterAdverTableCount
    MIN-ACCESS read-only
    DESCRIPTION
        "(U//FOUO) Implementation of this object can be as low
         as read-only depending on which
         IS Objective or MIB desired requirements are
         not being met by the implementation."

    OBJECT     hIPv6RouterAdverMTU
    MIN-ACCESS read-create
    DESCRIPTION
        "(U//FOUO) Implementation of this object can be as low
         as read-create depending on which
         IS Objective or MIB desired requirements are
         not being met by the implementation."

    OBJECT     hIPv6RouterAdverManagedFlag
    MIN-ACCESS read-create
    DESCRIPTION
        "(U//FOUO) Implementation of this object can be as low
         as read-create depending on which
         IS Objective or MIB desired requirements are
         not being met by the implementation."

    OBJECT     hManualSAFlowLabelSetting
    MIN-ACCESS read-create
    DESCRIPTION
        "(U//FOUO) Implementation of this object can be as low
         as read-create depending on which
         IS Objective or MIB desired requirements are
         not being met by the implementation."

    OBJECT     hManualSACTDSCPSetting
    MIN-ACCESS read-create
    DESCRIPTION
        "(U//FOUO) Implementation of this object can be as low
         as read-create depending on which
         IS Objective or MIB desired requirements are
         not being met by the implementation."

    OBJECT     hCIDRRouteType
    MIN-ACCESS read-create
    DESCRIPTION
        "(U//FOUO) Implementation of this object can be as low
         as read-create depending on which
         IS Objective or MIB desired requirements are
         not being met by the implementation."

    OBJECT     hIPv6RouterAdverTableLastChanged
    MIN-ACCESS read-only
    DESCRIPTION
        "(U//FOUO) Implementation of this object can be as low
         as read-only depending on which
         IS Objective or MIB desired requirements are
         not being met by the implementation."

    OBJECT     hCIDRRouteProtocol
    MIN-ACCESS read-only
    DESCRIPTION
        "(U//FOUO) Implementation of this object can be as low
         as read-only depending on which
         IS Objective or MIB desired requirements are
         not being met by the implementation."

    OBJECT     hCIDRRouteMetric
    MIN-ACCESS read-create
    DESCRIPTION
        "(U//FOUO) Implementation of this object can be as low
         as read-create depending on which
         IS Objective or MIB desired requirements are
         not being met by the implementation."

    OBJECT     hManualSAECNSetting
    MIN-ACCESS read-create
    DESCRIPTION
        "(U//FOUO) Implementation of this object can be as low
         as read-create depending on which
         IS Objective or MIB desired requirements are
         not being met by the implementation."

    OBJECT     hIPv6RouterAdverMaxInterval
    MIN-ACCESS read-create
    DESCRIPTION
        "(U//FOUO) Implementation of this object can be as low
         as read-create depending on which
         IS Objective or MIB desired requirements are
         not being met by the implementation."

    OBJECT     hIPv6RouterAdverMinInterval
    MIN-ACCESS read-create
    DESCRIPTION
        "(U//FOUO) Implementation of this object can be as low
         as read-create depending on which
         IS Objective or MIB desired requirements are
         not being met by the implementation."
::= { haipeV040101Conformance 19 }

--
-- Objects referenced by the KMI CI-2 3301 IS
--
hKMICapabilityGroup OBJECT-GROUP
    OBJECTS {
                hPDERetryDelay,
                hPKCNotBefore,
                hTAName,
                hPKCSubject,
                hPDEURI,
                hPKCTableCount,
                hPDEFromPAL,
                hCRLThisUpdate,
                hTATableLastChanged,
                hPDETLSEstablishmentMaxAttempts,
                hPKCIsCA,
                hPDEMappingRowStatus,
                hPDERetryMaxAttempts,
                hPDETLSEstablishmentRetryDelay,
                hPKCClearanceClassList,
                hPKCVersion,
                hPDEType,
                hCRLLastUpdate,
                hPDEMappingTableCount,
                hPDERequest,
                hPKCFromPDE,
                hPKCNotAfter,
                hCRLVersion,
                hPKCSignature,
                hPKCType,
                hCRLNextUpdate,
                hPDERowStatus,
                hTATableCount,
                hPDEMappingTableLastChanged,
                hPDEMappingHostname,
                hPDEMappingPTIPAddress,
                hPKCTableLastChanged,
                hPDERequestStatus,
                hTARowStatus,
                hPKCRowStatus,
                hPDEMappingPTIPAddressType,
                hCRLRowStatus,
                hTAVersion,
                hPDETableCount,
                hCRLTableCount,
                hTAKeyIdentifier,
                hPDETableLastChanged,
                hCRLFromPDE,
                hCRLTableLastChanged
            }
    STATUS    current
    DESCRIPTION
        "(U//FUOUO) Objects for the KMI CI-2 3301 document(s).
         This group is only relevant if both extensions are supported"
    ::= { haipeV040101Groups 20 }

--
-- Conformance levels required by the KMI CI-2 3301 IS
--
hKMICapabilityCompliance MODULE-COMPLIANCE
    STATUS    current
    DESCRIPTION
        "(U//FOUO) Compliance levels for objects required by the
         KMI CI-2 3301 document(s)."
    MODULE -- this module
    MANDATORY-GROUPS { hKMICapabilityGroup }

    OBJECT     hPDERetryDelay
    MIN-ACCESS read-write
    DESCRIPTION
        "(U//FOUO) Implementation of this object can be as low
         as read-write depending on which
         IS Objective or MIB desired requirements are
         not being met by the implementation."

    OBJECT     hPKCNotBefore
    MIN-ACCESS read-only
    DESCRIPTION
        "(U//FOUO) Implementation of this object can be as low
         as read-only depending on which
         IS Objective or MIB desired requirements are
         not being met by the implementation."

    OBJECT     hTAName
    MIN-ACCESS read-only
    DESCRIPTION
        "(U//FOUO) Implementation of this object can be as low
         as read-only depending on which
         IS Objective or MIB desired requirements are
         not being met by the implementation."

    OBJECT     hPKCSubject
    MIN-ACCESS read-only
    DESCRIPTION
        "(U//FOUO) Implementation of this object can be as low
         as read-only depending on which
         IS Objective or MIB desired requirements are
         not being met by the implementation."

    OBJECT     hPDEURI
    MIN-ACCESS read-create
    DESCRIPTION
        "(U//FOUO) Implementation of this object can be as low
         as read-create depending on which
         IS Objective or MIB desired requirements are
         not being met by the implementation."

    OBJECT     hPKCTableCount
    MIN-ACCESS read-only
    DESCRIPTION
        "(U//FOUO) Implementation of this object can be as low
         as read-only depending on which
         IS Objective or MIB desired requirements are
         not being met by the implementation."

    OBJECT     hPDEFromPAL
    MIN-ACCESS read-only
    DESCRIPTION
        "(U//FOUO) Implementation of this object can be as low
         as read-only depending on which
         IS Objective or MIB desired requirements are
         not being met by the implementation."

    OBJECT     hCRLThisUpdate
    MIN-ACCESS read-only
    DESCRIPTION
        "(U//FOUO) Implementation of this object can be as low
         as read-only depending on which
         IS Objective or MIB desired requirements are
         not being met by the implementation."

    OBJECT     hTATableLastChanged
    MIN-ACCESS read-only
    DESCRIPTION
        "(U//FOUO) Implementation of this object can be as low
         as read-only depending on which
         IS Objective or MIB desired requirements are
         not being met by the implementation."

    OBJECT     hPDETLSEstablishmentMaxAttempts
    MIN-ACCESS read-write
    DESCRIPTION
        "(U//FOUO) Implementation of this object can be as low
         as read-write depending on which
         IS Objective or MIB desired requirements are
         not being met by the implementation."

    OBJECT     hPKCIsCA
    MIN-ACCESS read-only
    DESCRIPTION
        "(U//FOUO) Implementation of this object can be as low
         as read-only depending on which
         IS Objective or MIB desired requirements are
         not being met by the implementation."

    OBJECT     hPDEMappingRowStatus
    MIN-ACCESS read-create
    DESCRIPTION
        "(U//FOUO) Implementation of this object can be as low
         as read-create depending on which
         IS Objective or MIB desired requirements are
         not being met by the implementation."

    OBJECT     hPDERetryMaxAttempts
    MIN-ACCESS read-write
    DESCRIPTION
        "(U//FOUO) Implementation of this object can be as low
         as read-write depending on which
         IS Objective or MIB desired requirements are
         not being met by the implementation."

    OBJECT     hPDETLSEstablishmentRetryDelay
    MIN-ACCESS read-write
    DESCRIPTION
        "(U//FOUO) Implementation of this object can be as low
         as read-write depending on which
         IS Objective or MIB desired requirements are
         not being met by the implementation."

    OBJECT     hPKCClearanceClassList
    MIN-ACCESS read-only
    DESCRIPTION
        "(U//FOUO) Implementation of this object can be as low
         as read-only depending on which
         IS Objective or MIB desired requirements are
         not being met by the implementation."

    OBJECT     hPKCVersion
    MIN-ACCESS read-only
    DESCRIPTION
        "(U//FOUO) Implementation of this object can be as low
         as read-only depending on which
         IS Objective or MIB desired requirements are
         not being met by the implementation."

    OBJECT     hPDEType
    MIN-ACCESS read-create
    DESCRIPTION
        "(U//FOUO) Implementation of this object can be as low
         as read-create depending on which
         IS Objective or MIB desired requirements are
         not being met by the implementation."

    OBJECT     hCRLLastUpdate
    MIN-ACCESS read-only
    DESCRIPTION
        "(U//FOUO) Implementation of this object can be as low
         as read-only depending on which
         IS Objective or MIB desired requirements are
         not being met by the implementation."

    OBJECT     hPDEMappingTableCount
    MIN-ACCESS read-only
    DESCRIPTION
        "(U//FOUO) Implementation of this object can be as low
         as read-only depending on which
         IS Objective or MIB desired requirements are
         not being met by the implementation."

    OBJECT     hPDERequest
    MIN-ACCESS read-create
    DESCRIPTION
        "(U//FOUO) Implementation of this object can be as low
         as read-create depending on which
         IS Objective or MIB desired requirements are
         not being met by the implementation."

    OBJECT     hPKCFromPDE
    MIN-ACCESS read-only
    DESCRIPTION
        "(U//FOUO) Implementation of this object can be as low
         as read-only depending on which
         IS Objective or MIB desired requirements are
         not being met by the implementation."

    OBJECT     hPKCNotAfter
    MIN-ACCESS read-only
    DESCRIPTION
        "(U//FOUO) Implementation of this object can be as low
         as read-only depending on which
         IS Objective or MIB desired requirements are
         not being met by the implementation."

    OBJECT     hCRLVersion
    MIN-ACCESS read-only
    DESCRIPTION
        "(U//FOUO) Implementation of this object can be as low
         as read-only depending on which
         IS Objective or MIB desired requirements are
         not being met by the implementation."

    OBJECT     hPKCSignature
    MIN-ACCESS read-only
    DESCRIPTION
        "(U//FOUO) Implementation of this object can be as low
         as read-only depending on which
         IS Objective or MIB desired requirements are
         not being met by the implementation."

    OBJECT     hPKCType
    MIN-ACCESS read-only
    DESCRIPTION
        "(U//FOUO) Implementation of this object can be as low
         as read-only depending on which
         IS Objective or MIB desired requirements are
         not being met by the implementation."

    OBJECT     hCRLNextUpdate
    MIN-ACCESS read-only
    DESCRIPTION
        "(U//FOUO) Implementation of this object can be as low
         as read-only depending on which
         IS Objective or MIB desired requirements are
         not being met by the implementation."

    OBJECT     hPDERowStatus
    MIN-ACCESS read-create
    DESCRIPTION
        "(U//FOUO) Implementation of this object can be as low
         as read-create depending on which
         IS Objective or MIB desired requirements are
         not being met by the implementation."

    OBJECT     hTATableCount
    MIN-ACCESS read-only
    DESCRIPTION
        "(U//FOUO) Implementation of this object can be as low
         as read-only depending on which
         IS Objective or MIB desired requirements are
         not being met by the implementation."

    OBJECT     hPDEMappingTableLastChanged
    MIN-ACCESS read-only
    DESCRIPTION
        "(U//FOUO) Implementation of this object can be as low
         as read-only depending on which
         IS Objective or MIB desired requirements are
         not being met by the implementation."

    OBJECT     hPDEMappingHostname
    MIN-ACCESS read-create
    DESCRIPTION
        "(U//FOUO) Implementation of this object can be as low
         as read-create depending on which
         IS Objective or MIB desired requirements are
         not being met by the implementation."

    OBJECT     hPDEMappingPTIPAddress
    MIN-ACCESS read-create
    DESCRIPTION
        "(U//FOUO) Implementation of this object can be as low
         as read-create depending on which
         IS Objective or MIB desired requirements are
         not being met by the implementation."

    OBJECT     hPKCTableLastChanged
    MIN-ACCESS read-only
    DESCRIPTION
        "(U//FOUO) Implementation of this object can be as low
         as read-only depending on which
         IS Objective or MIB desired requirements are
         not being met by the implementation."

    OBJECT     hPDERequestStatus
    MIN-ACCESS read-only
    DESCRIPTION
        "(U//FOUO) Implementation of this object can be as low
         as read-only depending on which
         IS Objective or MIB desired requirements are
         not being met by the implementation."

    OBJECT     hTARowStatus
    MIN-ACCESS read-write
    DESCRIPTION
        "(U//FOUO) Implementation of this object can be as low
         as read-write depending on which
         IS Objective or MIB desired requirements are
         not being met by the implementation."

    OBJECT     hPKCRowStatus
    MIN-ACCESS read-write
    DESCRIPTION
        "(U//FOUO) Implementation of this object can be as low
         as read-write depending on which
         IS Objective or MIB desired requirements are
         not being met by the implementation."

    OBJECT     hPDEMappingPTIPAddressType
    MIN-ACCESS read-create
    DESCRIPTION
        "(U//FOUO) Implementation of this object can be as low
         as read-create depending on which
         IS Objective or MIB desired requirements are
         not being met by the implementation."

    OBJECT     hCRLRowStatus
    MIN-ACCESS read-write
    DESCRIPTION
        "(U//FOUO) Implementation of this object can be as low
         as read-write depending on which
         IS Objective or MIB desired requirements are
         not being met by the implementation."

    OBJECT     hTAVersion
    MIN-ACCESS read-only
    DESCRIPTION
        "(U//FOUO) Implementation of this object can be as low
         as read-only depending on which
         IS Objective or MIB desired requirements are
         not being met by the implementation."

    OBJECT     hPDETableCount
    MIN-ACCESS read-only
    DESCRIPTION
        "(U//FOUO) Implementation of this object can be as low
         as read-only depending on which
         IS Objective or MIB desired requirements are
         not being met by the implementation."

    OBJECT     hCRLTableCount
    MIN-ACCESS read-only
    DESCRIPTION
        "(U//FOUO) Implementation of this object can be as low
         as read-only depending on which
         IS Objective or MIB desired requirements are
         not being met by the implementation."

    OBJECT     hTAKeyIdentifier
    MIN-ACCESS read-only
    DESCRIPTION
        "(U//FOUO) Implementation of this object can be as low
         as read-only depending on which
         IS Objective or MIB desired requirements are
         not being met by the implementation."

    OBJECT     hPDETableLastChanged
    MIN-ACCESS read-only
    DESCRIPTION
        "(U//FOUO) Implementation of this object can be as low
         as read-only depending on which
         IS Objective or MIB desired requirements are
         not being met by the implementation."

    OBJECT     hCRLFromPDE
    MIN-ACCESS read-only
    DESCRIPTION
        "(U//FOUO) Implementation of this object can be as low
         as read-only depending on which
         IS Objective or MIB desired requirements are
         not being met by the implementation."

    OBJECT     hCRLTableLastChanged
    MIN-ACCESS read-only
    DESCRIPTION
        "(U//FOUO) Implementation of this object can be as low
         as read-only depending on which
         IS Objective or MIB desired requirements are
         not being met by the implementation."
::= { haipeV040101Conformance 20 }

--
-- Objects referenced by the Legacy Discovery IS
--
hLegacyDiscoveryCapabilityGroup OBJECT-GROUP
    OBJECTS {
                hLegacyDeliveryTableCount,
                hPEPTRowConfigMethod,
                hLegacyDeliveryRowStatus,
                hLegacyDeliveryTableLastChanged,
                hPEPTRowStatus
            }
    STATUS    current
    DESCRIPTION
        "(U//FUOUO) Objects for the Legacy Discovery document(s).
         This group is only relevant if both extensions are supported"
    ::= { haipeV040101Groups 21 }

--
-- Conformance levels required by the Legacy Discovery IS
--
hLegacyDiscoveryCapabilityCompliance MODULE-COMPLIANCE
    STATUS    current
    DESCRIPTION
        "(U//FOUO) Compliance levels for objects required by the
         Legacy Discovery document(s)."
    MODULE -- this module
    MANDATORY-GROUPS { hLegacyDiscoveryCapabilityGroup }

    OBJECT     hLegacyDeliveryTableCount
    MIN-ACCESS read-only
    DESCRIPTION
        "(U//FOUO) Implementation of this object can be as low
         as read-only depending on which
         IS Objective or MIB desired requirements are
         not being met by the implementation."

    OBJECT     hPEPTRowConfigMethod
    MIN-ACCESS read-only
    DESCRIPTION
        "(U//FOUO) Implementation of this object can be as low
         as read-only depending on which
         IS Objective or MIB desired requirements are
         not being met by the implementation."

    OBJECT     hLegacyDeliveryRowStatus
    MIN-ACCESS read-create
    DESCRIPTION
        "(U//FOUO) Implementation of this object can be as low
         as read-create depending on which
         IS Objective or MIB desired requirements are
         not being met by the implementation."

    OBJECT     hLegacyDeliveryTableLastChanged
    MIN-ACCESS read-only
    DESCRIPTION
        "(U//FOUO) Implementation of this object can be as low
         as read-only depending on which
         IS Objective or MIB desired requirements are
         not being met by the implementation."

    OBJECT     hPEPTRowStatus
    MIN-ACCESS read-only
    DESCRIPTION
        "(U//FOUO) Implementation of this object can be as low
         as read-only depending on which
         IS Objective or MIB desired requirements are
         not being met by the implementation."
::= { haipeV040101Conformance 21 }

--
-- Objects referenced by the Legacy Encapsulated Security Payload IS
--
hLegacyESPCapabilityGroup OBJECT-GROUP
    OBJECTS {
                hManualSASPIChainReference,
                hManualSASPIChainRowStatus,
                hManualSARowStatus,
                hManualSASPI
            }
    STATUS    current
    DESCRIPTION
        "(U//FUOUO) Objects for the Legacy Encapsulated Security Payload document(s).
         This group is only relevant if both extensions are supported"
    ::= { haipeV040101Groups 22 }

--
-- Conformance levels required by the Legacy Encapsulated Security Payload IS
--
hLegacyESPCapabilityCompliance MODULE-COMPLIANCE
    STATUS    current
    DESCRIPTION
        "(U//FOUO) Compliance levels for objects required by the
         Legacy Encapsulated Security Payload document(s)."
    MODULE -- this module
    MANDATORY-GROUPS { hLegacyESPCapabilityGroup }

    OBJECT     hManualSASPIChainReference
    MIN-ACCESS read-create
    DESCRIPTION
        "(U//FOUO) Implementation of this object can be as low
         as read-create depending on which
         IS Objective or MIB desired requirements are
         not being met by the implementation."

    OBJECT     hManualSASPIChainRowStatus
    MIN-ACCESS read-create
    DESCRIPTION
        "(U//FOUO) Implementation of this object can be as low
         as read-create depending on which
         IS Objective or MIB desired requirements are
         not being met by the implementation."

    OBJECT     hManualSARowStatus
    MIN-ACCESS read-create
    DESCRIPTION
        "(U//FOUO) Implementation of this object can be as low
         as read-create depending on which
         IS Objective or MIB desired requirements are
         not being met by the implementation."

    OBJECT     hManualSASPI
    MIN-ACCESS read-create
    DESCRIPTION
        "(U//FOUO) Implementation of this object can be as low
         as read-create depending on which
         IS Objective or MIB desired requirements are
         not being met by the implementation."
::= { haipeV040101Conformance 22 }

--
-- Objects referenced by the DGSK IS
--
hDGSKCapabilityGroup OBJECT-GROUP
    OBJECTS {
                hDGSharedKeySuite,
                hDGSharedKeyLabel,
                hGenerateSharedKey,
                hDGSharedKeyMaterial,
                hDGSharedKeyEffectiveDate,
                hDGSharedKeyUsageType,
                hDGSharedKeyTableCount,
                hDGSharedKeyTableLastChanged,
                hDGSharedKeyRowStatus,
                hDGSharedKeyClassification,
                hDGSharedKeyShortTitle,
                hDGSharedKeyOrigin
            }
    STATUS    current
    DESCRIPTION
        "(U//FUOUO) Objects for the DGSK requirements.  This group is only 
        relevant if DGSKs are supported."
    ::= { haipeV040101Groups 23 }

--
-- Conformance levels required by the DGSK IS
--
hDGSKCapabilityCompliance MODULE-COMPLIANCE
    STATUS    current
    DESCRIPTION
        "(U//FOUO) Compliance levels for objects required by the
         DGSK requirements."
    MODULE -- this module
    MANDATORY-GROUPS { hDGSKCapabilityGroup }

    OBJECT     hDGSharedKeySuite
    MIN-ACCESS read-only
    DESCRIPTION
        "(U//FOUO) Implementation of this object can be as low
         as read-only depending on which
         IS Objective or MIB desired requirements are
         not being met by the implementation."

    OBJECT     hDGSharedKeyLabel
    MIN-ACCESS read-only
    DESCRIPTION
        "(U//FOUO) Implementation of this object can be as low
         as read-only depending on which
         IS Objective or MIB desired requirements are
         not being met by the implementation."

    OBJECT     hGenerateSharedKey
    MIN-ACCESS not-accessible
    DESCRIPTION
        "(U//FOUO) Implementation of this object can be as low
         as not-accessible depending on which
         IS Objective or MIB desired requirements are
         not being met by the implementation."

    OBJECT     hDGSharedKeyMaterial
    MIN-ACCESS read-only
    DESCRIPTION
        "(U//FOUO) Implementation of this object can be as low
         as read-only depending on which
         IS Objective or MIB desired requirements are
         not being met by the implementation."

    OBJECT     hDGSharedKeyEffectiveDate
    MIN-ACCESS read-only
    DESCRIPTION
        "(U//FOUO) Implementation of this object can be as low
         as read-only depending on which
         IS Objective or MIB desired requirements are
         not being met by the implementation."

    OBJECT     hDGSharedKeyUsageType
    MIN-ACCESS read-only
    DESCRIPTION
        "(U//FOUO) Implementation of this object can be as low
         as read-only depending on which
         IS Objective or MIB desired requirements are
         not being met by the implementation."

    OBJECT     hDGSharedKeyTableCount
    MIN-ACCESS read-only
    DESCRIPTION
        "(U//FOUO) Implementation of this object can be as low
         as read-only depending on which
         IS Objective or MIB desired requirements are
         not being met by the implementation."

    OBJECT     hDGSharedKeyTableLastChanged
    MIN-ACCESS read-only
    DESCRIPTION
        "(U//FOUO) Implementation of this object can be as low
         as read-only depending on which
         IS Objective or MIB desired requirements are
         not being met by the implementation."

    OBJECT     hDGSharedKeyRowStatus
    MIN-ACCESS read-only
    DESCRIPTION
        "(U//FOUO) Implementation of this object can be as low
         as read-only depending on which
         IS Objective or MIB desired requirements are
         not being met by the implementation."

    OBJECT     hDGSharedKeyClassification
    MIN-ACCESS read-only
    DESCRIPTION
        "(U//FOUO) Implementation of this object can be as low
         as read-only depending on which
         IS Objective or MIB desired requirements are
         not being met by the implementation."

    OBJECT     hDGSharedKeyShortTitle
    MIN-ACCESS read-only
    DESCRIPTION
        "(U//FOUO) Implementation of this object can be as low
         as read-only depending on which
         IS Objective or MIB desired requirements are
         not being met by the implementation."

    OBJECT     hDGSharedKeyOrigin
    MIN-ACCESS not-accessible
    DESCRIPTION
        "(U//FOUO) Implementation of this object can be as low
         as not-accessible depending on which
         IS Objective or MIB desired requirements are
         not being met by the implementation."
::= { haipeV040101Conformance 23 }

--
-- Objects referenced by the DGSK and Remote Provisioning Authority
--
hDGSKANDRemoteProvisioningAuthorityCapabilityGroup OBJECT-GROUP
    OBJECTS {
                hDGSharedKeyPushToLoadedKeyTable
            }
    STATUS    current
    DESCRIPTION
        "(U//FUOUO) Objects for the DGSK requirement(s).  This group is only 
         relevant if both DGSK requirements and the Remote Provisioning 
         Authority IS are supported"
    ::= { haipeV040101Groups 24 }

--
-- Conformance levels required by the DGSK and Remote Provisioning Authority IS
--
hDGSKANDRemoteProvisioningAuthorityCapabilityCompliance MODULE-COMPLIANCE
    STATUS    current
    DESCRIPTION
        "(U//FOUO) Compliance levels for objects required by the DGSK 
         requirements and the Remote Provisioning Authority IS."
    MODULE -- this module
    MANDATORY-GROUPS { hDGSKANDRemoteProvisioningAuthorityCapabilityGroup }

    OBJECT     hDGSharedKeyPushToLoadedKeyTable
    MIN-ACCESS read-write
    DESCRIPTION
        "(U//FOUO) Implementation of this object can be as low
         as read-write depending on which
         IS Objective or MIB desired requirements are
         not being met by the implementation."
::= { haipeV040101Conformance 24 }
END
