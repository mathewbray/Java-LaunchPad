HAIPE-V030102-MIB DEFINITIONS ::= BEGIN
-- ************************************************************
-- DO NOT EDIT - AUTOMATICALLY GENERATED FILE
-- ************************************************************
IMPORTS
    MODULE-IDENTITY                 FROM SNMPv2-SMI
    MODULE-COMPLIANCE, OBJECT-GROUP FROM SNMPv2-CONF
    haipeComplianceMIB              FROM HAIPE-COMPLIANCE-MIB
    snmpUsmAesMIB
      FROM SNMP-USM-AES-MIB
    ipv4InterfaceRetransmitTime, ipv6RouterAdvertRowStatus, ipv6ScopeZoneIndexAdminLocal, ipv6ScopeZoneIndex9, ipv6ScopeZoneIndex6, ipv6RouterAdvertMaxInterval, ipNetToPhysicalType, ipv6InterfaceEnableStatus, ipNetToPhysicalPhysAddress, ipv6RouterAdvertDefaultLifetime, ipv6RouterAdvertOtherConfigFlag, ipv6InterfaceTable, ipv6ScopeZoneIndexD, ipAddressPrefix, ipv6IpForwarding, ipAddressStorageType, ipv6RouterAdvertRetransmitTime, ipAddressStatus, ipv6RouterAdvertSendAdverts, ipv6ScopeZoneIndexSiteLocal, ipv6IpDefaultHopLimit, ipAddressCreated, ipv6InterfaceReasmMaxSize, ipv4InterfaceTable, ipv6RouterAdvertManagedFlag, ipv4InterfaceEnableStatus, ipNetToPhysicalState, ipv6RouterAdvertSpinLock, ipv6ScopeZoneIndexOrganizationLocal, ipv6ScopeZoneIndexA, ipForwarding, ipv6InterfaceForwarding, ipv6ScopeZoneIndexC, ipv6InterfaceRetransmitTime, ipAddressIfIndex, ipAddressOrigin, ipNetToPhysicalLastUpdated, ipv6ScopeZoneIndexB, ipNetToPhysicalRowStatus, ipv6ScopeZoneIndex7, ipAddressSpinLock, ipAddressLastChanged, ipAddressRowStatus, ipv6ScopeZoneIndexLinkLocal, ipAddressType, ipv6InterfaceIdentifier, ipv6RouterAdvertLinkMTU, ipReasmTimeout, ipv6RouterAdvertMinInterval, ipv6InterfaceReachableTime, ipv6RouterAdvertCurHopLimit, ipv4InterfaceReasmMaxSize, ipv6RouterAdvertReachableTime, ipv6ScopeZoneIndex3, ipDefaultTTL
      FROM IP-MIB
    hBatteryLevelPercentage, hFdsLoginName, hAudThrottleCfgRowStatus, hAudCfgNotifEnabled, hTFTPDesiredTimeoutInterval, hAudCfgThrottlingEnabled, hFirmwareDownloadAdminStatus, hAudNotificationLogWarning, hAudCfgLogThrottled, hGenericAuditNotification, hSecurityLevels, hBatteryTable, hAudNotificationLogFull, hAudCfgNotifThrottleCfg, hNotificationLogPartialReset, hFirmwareDownloadOperStatus, hBatteryOK, hAudCfgLogCount, hTFTPMaximumFileTransferSize, hAudThrottleCfgInterval, hAudThrottleConfigTableCount, hAudThrottleCfgThreshold, hdvName, hAudCfgNotifCount, hAudCfgNotifThrottled, hNotificationLogFullBehavior, hBatteryNumber, hHMISpinLock, hNotificationLogCapacityPercentage, hFirmwareInstallSucceeded, hAudCfgNotifThrottleStatus, hFdsPassword, hBatteryLevelWarningPercentage, hNotificationLogReset, hFdsRowStatus, hFdsPriority, hFdsLastChanged, hAudCfgLogThrottleCfg, hAudThrottleConfigTableLastChanged, hAudThrottleCfgLastChanged, hFdsURI, hBatteryOperStatus, hAudNotificationLogOk, hDeviceVersionTableCount, hFirmwareDownloadServersTableLastChanged, haipeSanitizeDevice, hFdsSide, hSpinLock, hDeviceVersionTableLastChanged, hLastChanged, hAudThrottleCfgName, hTFTPDesiredBlockSize, hAudCfgLogThrottleStatus, hAudCfgRowStatus, hAuditConfigTableCount, hFirmwareDownloadServersTableCount, hFdErrorCode, hFirmwareDownloadSuccess, hAuditConfigTableLastChanged, hStationID, hNotificationLogWarningPercentage, hAudCfgID, hdvVersion, hFirmwareInstallFailed, hBatteryLow, haipeResetDevice, hFirmwareDownloadError, hFdErrorDetail, hBatteryChangeDate
      FROM HAIPE-MANAGEMENT-MIB
    snmpUnknownSecurityModels, snmpUnknownPDUHandlers, snmpInvalidMsgs
      FROM SNMP-MPD-MIB
    hrSystemUptime, hrSystemDate
      FROM HOST-RESOURCES-MIB
    ifOperStatus, ifPhysAddress, ifMtu, ifHCOutUcastPkts, ifDescr, ifConnectorPresent, ifHCInMulticastPkts, ifAdminStatus, ifOutMulticastPkts, ifLastChange, ifIndex, ifLinkUpDownTrapEnable, ifHCOutBroadcastPkts, ifHighSpeed, ifHCOutOctets, ifHCInUcastPkts, ifInBroadcastPkts, ifSpeed, ifNumber, ifName, ifPromiscuousMode, ifOutBroadcastPkts, ifCounterDiscontinuityTime, ifHCInBroadcastPkts, ifAlias, ifInMulticastPkts, ifHCOutMulticastPkts, ifType, ifHCInOctets
      FROM IF-MIB
    hKTOOBClientsTableLastChanged, hKTOOBNotificationErrorCode, hKTOOBKeyFileSegment, hKTIBACAddress, hKTOOBKeyFileNum, hKTOOBControllerKeyFileMissingKeyError, hKTIBClientsTableLastChanged, hKTLoadedKeyEdition, hKTOOBACName, hKTOOBClientRowStatus, hKTIBClientTransferTime, hKTIBControllerMissingKeyError, hKTOOBControllerTFTPErrorReceived, hKTOOBClientAddress, hKTOOBTFTPDesiredTimeoutInterval, hKTLoadedKeyTableLastChanged, hKTLoadedKeyAction, hKTOOBACAddress, hKTIBDKPPKSegment, hKTOOBKeyFileRegister, hKTOOBLoadedKeyDeletedUsedPPKError, hKTIBClientPPKShortTitle, hKTLoadedKeyText, hKTOOBKeyFileShortTitle, hKTIBLoadedKeyDeletedUsedPPKError, hKTOOBClientsTableCount, hKTIBClientRowStatus, hKTIBDKShortTitle, hKTLoadedKeyTableCount, hKTOOBACAddressType, hKTIBClientPPKRegister, hKTIBACRowStatus, hKTIBClientAddressType, hKTLoadedKeyShortTitle, hKTIBAuthControllersTableCount, hKTIBClientEffectiveDate, hKTOOBKeyFileName, hKTIBDKPPKEdition, hKTOOBClientPushKey, hKTOOBAuthControllersTableCount, hKTOOBKeyFileEdition, hKTIBACAddressType, hKTLoadedKeySegment, hKTLoadedKeyRegister, hKTIBACName, hKTOOBClientName, hKTIBDisabledKeyTable, hKTIBClientAddress, hKTOOBKeyFileTable, hKTIBClientRetries, hKTOOBClientPath, hKTOOBClientKeyFile, hKTLoadedKeyRowStatus, hKTIBClientPPKEdition, hKTIBClientPPKSegment, hKTLoadedKeyClassification, hKTLoadedKeyUse, hKTIBAuthControllersTableLastChanged, hKTOOBKeyFileRowStatus, hKTIBClientRetryPeriod, hKTIBDKRowStatus, hKTOOBACRowStatus, hKTOOBClientAddressType, hKTIBClientsTableCount, hKTOOBAuthControllersTableLastChanged
      FROM HAIPE-KEY-TRANSFER-MIB
    vacmSecurityToGroupStorageType, vacmMIBGroups, vacmMIBViews, vacmAccessWriteViewName, vacmAccessNotifyViewName, vacmAccessStorageType, vacmViewTreeFamilyType, vacmAccessStatus, vacmViewTreeFamilyMask, vacmAccessReadViewName, vacmMIBConformance, vacmViewTreeFamilyStorageType, snmpVacmMIB, vacmBasicGroup, vacmMIBObjects, vacmGroupName, vacmAccessContextMatch, vacmViewTreeFamilyStatus, vacmViewSpinLock, vacmMIBCompliance, vacmContextName, vacmMIBCompliances, vacmSecurityToGroupStatus
      FROM SNMP-VIEW-BASED-ACM-MIB
    sysORID, sysORLastChange, sysServices, sysName, warmStart, snmpTrapOID, sysLocation, sysDescr, authenticationFailure, snmpTrapEnterprise, sysUpTime, snmpSetSerialNo, sysORUpTime, coldStart, sysObjectID, sysORDescr, sysContact
      FROM SNMPv2-MIB
    snmpFrameworkMIB, snmpFrameworkMIBObjects, snmpEngineID, snmpPrivProtocols, snmpEngineGroup, snmpFrameworkMIBCompliances, snmpFrameworkMIBConformance, snmpAuthProtocols, snmpFrameworkMIBGroups, snmpFrameworkMIBCompliance, snmpEngineMaxMessageSize, snmpEngine, snmpFrameworkAdmin, snmpEngineBoots, snmpEngineTime
      FROM SNMP-FRAMEWORK-MIB
    snmpTargetAddrTAddress, snmpTargetParamsSecurityLevel, snmpUnavailableContexts, snmpTargetAddrTagList, snmpTargetAddrRetryCount, snmpUnknownContexts, snmpTargetSpinLock, snmpTargetAddrStorageType, snmpTargetParamsMPModel, snmpTargetAddrTimeout, snmpTargetAddrParams, snmpTargetParamsRowStatus, snmpTargetParamsSecurityName, snmpTargetParamsSecurityModel, snmpTargetAddrTDomain, snmpTargetParamsStorageType, snmpTargetAddrRowStatus
      FROM SNMP-TARGET-MIB
    hMLDMode, hIfv6SubIdentifier, hIfv6NATTEnable, hIfv6BaseReachableTime, hIfv4SegCoreModeEnable, hiaaType, hIfAddrAssignmentTable, hv6APAddressPrefixOrigin, hIfv6NextHeaderSkipList, hIfv4HaipeTableCount, hNetDuplicateAddressDetected, hv6APLastChanged, hNetDuplicateAddressCheck, hv6APAdvertisePrefix, hIfv4TTL, hIfv4LowPMTUThreshold, hIfv6HaipeTableLastChanged, hIfv6InterfaceIdentifier, hIfv6HopLimit, hIfv6MTU, hv6APAddressPrefixAdvValidLifetime, hIfv6RetransmitTime, hIfv6DupAddressRecoveryID, hiaaPrefixLen, hIfv6LowPMTUThreshold, hIfv4LastChanged, hNetDuplicateAddressIfDown, hIGMPMode, hIfv6SegCoreModeEnable, hv6APAddressPrefixAdvPreferredLifetime, hIfv4MTU, hv6AddressPrefixTableLastChanged, hIfv4HaipeTableLastChanged, hv6APAddressPrefixOnLinkFlag, hIfv6AddressAutoConfig, hIfv6RouterSolicitation, hIfv4Side, hNetSourceAddress, hiaaAddress, hIfv6Side, hIfv6HaipeTableCount, hIfv6DupAddressDetection, hv6AddressPrefixTableCount, hNetSourceAddressType, hiaaInterface, hIfv6PMTUResetPeriod, hIfv6DiscardUnauthRed, hIfv4NATTEnable, hv6APAddressPrefixAutonomousFlag, hIfv6UseDepAddress, hIfv4PMTUResetPeriod, hiaaRowStatus, hIfv6LastChanged, hIfv6ReachableTime, hv6APRowStatus
      FROM HAIPE-NETWORKING-MIB
    inetCidrRouteType, inetCidrRouteProto, inetCidrRouteIfIndex, inetCidrRouteMetric4, inetCidrRouteDiscards, inetCidrRouteMetric3, inetCidrRouteNumber, inetCidrRouteAge, inetCidrRouteMetric2, inetCidrRouteMetric1, inetCidrRouteStatus, inetCidrRouteMetric5, inetCidrRouteNextHopAS
      FROM IP-FORWARD-MIB
    hDiscRegistrationTableLastChanged, hRemoteEnclaveDestHaipeNATPort, hDiscSolRcvSide, hRemoteEnclaveDestHaipeCTAddrType, hRemoteEnclaveDestHostPTPfxLen, hRemoteEnclaveTableLastChanged, hRemoteEnclaveLifetime, hRIPConfTableLastChanged, hrcSrcAddress, hLocalEnclaveDestHostPTPfxLen, hDiscSearchStartAddress, hRemoteEnclaveMethod, hDiscRegPriority, hDiscDelivType, hDiscRegStatus, hRemoteEnclaveDestAdminCost, hDiscDelivPriority, hLocalEnclaveTableLastChanged, hRemoteEnclaveDestHaipePTAddrType, hDiscSolRcvStatus, hrcDefaultMetric, hrcMetric, hDiscoveryEnabled, hLocalEnclaveRowStatus, hDiscSolRcvPort, hrcFilterDefaultRoutes, hrcAdvertising, hRemoteEnclaveDestHaipeCTAddr, hDiscoveryDeliveryTableLastChanged, hDiscSolReceptionTableLastChanged, hrcSend, hRIPConfTableCount, hDiscRegistrationTableCount, hLocalEnclaveDestAdminCost, hDiscRegPTAddress, hrcStatus, hDiscoverySolicitationRetry, hRemoteEnclaveDestHaipeNATAddr, hRemoteEnclaveTableCount, hDiscSolRcvAddressType, hDiscoveryRegistrationRetry, hDiscSolReceptionTableCount, hRemoteEnclaveDestHostAddrType, hLocalEnclaveLifetime, hDiscDelivPTAddress, hLocalEnclaveTableCount, hDiscoveryProbeRetry, hDiscDelivStatus, hDiscSearchEndAddress, hLocalEnclaveMethod, hrcAuthType, hDiscoveryProbeTimeout, hRemoteEnclaveDestHaipePTAddr, hDiscoveryRegistrationTimeout, hDiscoveryMessageConfig, hDiscoveryAdvertiseAdminCost, hrcReceive, hDiscRegPTAddressType, hRemoteEnclaveRowStatus, hrcIfConfDomain, hrcAddr, hDiscDelivPTPort, hDiscSolRcvType, hDiscRegistrationDefaultLifetime, hDiscRegPTPort, hDiscSearchAddressType, hDiscSolRcvAddress, hRemoteEnclaveDestHost, hrcAuthKey, hrcAddrType, hLocalEnclaveDestHost, hDiscDelivPTAddressType, hDiscoveryDeliveryTableCount, hDiscoverySolicitationTimeout, hLocalEnclaveDestHostAddrType
      FROM HAIPE-NETWORKING-DISCOVERY-MIB
    usmUserPublic, usmUserPrivProtocol, usmStatsDecryptionErrors, usmUserStorageType, usmUserOwnPrivKeyChange, usmUserAuthProtocol, usmDESPrivProtocol, usmUserCloneFrom, usmUserSpinLock, usmHMACSHAAuthProtocol, usmStatsUnknownEngineIDs, usmUserStatus, usmHMACMD5AuthProtocol, usmUserPrivKeyChange, usmStatsUnsupportedSecLevels, usmStatsUnknownUserNames, usmNoAuthProtocol, usmStatsNotInTimeWindows, usmUserSecurityName, usmStatsWrongDigests, usmNoPrivProtocol, usmUserAuthKeyChange, usmUserOwnAuthKeyChange
      FROM SNMP-USER-BASED-SM-MIB
    nlmLogVariableValueType, nlmStatsGlobalNotificationsBumped, nlmConfigGlobalAgeOut, nlmLogEngineTAddress, nlmLogVariableOpaqueVal, nlmLogVariableOctetStringVal, nlmLogEngineTDomain, nlmStatsLogNotificationsLogged, nlmLogVariableIpAddressVal, nlmConfigGlobalEntryLimit, nlmLogContextEngineID, nlmLogVariableUnsigned32Val, nlmLogVariableID, nlmStatsGlobalNotificationsLogged, nlmLogVariableInteger32Val, nlmLogContextName, nlmLogVariableTimeTicksVal, nlmLogVariableCounter64Val, nlmStatsLogNotificationsBumped, nlmLogTime, nlmLogDateAndTime, nlmLogVariableOidVal, nlmLogEngineID, nlmLogVariableCounter32Val, nlmLogNotificationID
      FROM NOTIFICATION-LOG-MIB
    hPPKEKTableMaxCount, hIPhFFSATransformLastChanged, hTPSANATPort, hUniversalCKLVersion, hTPSAIntegrityAlgorithm, hPPKEffectiveDate, hTPSAEndTime, hIPhSelectorNextHeaderOpt1End, hTPSARemoteCAName, hTPSALocalCAName, hFFExpiration, hIPhFFSATransformKeyUpdateMethod, hPPKChainRowStatus, hTPTFCConfigPacketSizeList, hTPSAPTAddressType, hIPhSelectorTableLastChanged, hIPhFFSATransformAuthenticationAlgorithm, hIPhFFSATransformsTableCount, hPPKKeyExpirationWarningCount, hTPTFCConfigPacketSize, hIPhSelectorSrcAddressEnd, hTPSASelectorDSCP, hTPSAConnectionType, hTPSASelectorNextHeaderOpt2End, hIPhFFSADFBit, hIPhFFSATransformHashAlgorithm, hTPSANATAddress, hPPKChainPPK, hTPSADSCPValue, hTPTFCConfigPacketSizeType, hTPTransportMapTableLastChanged, hIPhSelectorNextHeaderStart, hFFMaterialType, hPPKRegister, hFFKMID, hTPSARemotePTAddress, hIPhSelectorSrcAddressBegin, hIPhSelectorNextHeaderEnd, hIPhFFSATransformKeyUpdateFrequency, hFFZeroizeKey, hTPTFCConfigTransmissionRate, hFFNextVector, hPPKEKKeyType, hPreplacedKeyTableLastChanged, hIPhRuleLastChanged, hIPhFFSATransformCryptoBlockSize, haipeZeroizeAllKeys, hPPKSecurityLevel, hTPTFCConfigTableLastChanged, hTPSACryptoBlockSize, hTPSACreationReason, hTPSADirection, hIPhSelectorIPVersion, hTPiDestinationAddress, hTPSAFlowLabel, hFireflyTableLastChanged, hPPKShortTitleName, hIPhFFSATableCount, hTPSAHCOctets, hTPSAPMTU, hIPhFFSAFFUniversal, hPPKZeroizeKey, hPPKChainID, hPPKChainOrder, hTPiDestinationAddressType, hTPSAHCUcastPkts, hFFPartitionCode, hTPSAReachable, hFFShortTitleName, hTPSASelectorNextHeaderOpt1Start, hLocalCKListRowStatus, hTPnSACreated, hTPSATFCConfig, hTPTransMapDestPTAddress, hTPnSADestroyed, hIPhFFSATransformsTableLastChanged, hUniversalCKLDate, hIPhFFSATransformEncryptAlgorithm, hIPhRuleActionIndex, hPPKTrafficTable, hTPAddressMapTable, hPPKLastChanged, hIPhFFSAConnectionType, hFFASCIIID, hPPKEdition, hTPiSADestroyedReason, hTPSAHCBrdcastPkts, hLocalCKListReason, hTPSAAddressSrcOrDest, hTPSARowStatus, hIPhFFSAFFUniversalEdition, hIPhFFSADSCP, hLocalCKListKMIDEnd, hIPhFFSAECN, hFFKeyExpirationWarning, hTPSASelectorNextHeaderStart, hUniversalTable, hIPhSelectorNextHeaderOpt1Start, hTPTransportMapTableCount, hIPhFFSAFlowLabelValue, hPPKUsageType, hIPhFFSADSCPValue, hTPSADecrementTTL, hTPTransMapRowStatus, hIPhFFSARetryICMPCount, hTPTFCConfigRowStatus, hTPSAAddressRowStatus, hTPSARemoteCredentialType, hIPhFFSACTOutAddressType, hTPTFCConfigTransmissionType, hTPAddMapCTAddress, hIPhFFSATransformsName, hTPSAHCMcastPkts, hTPSADSCP, hPPKTrafficIntegrityAlgorithm, hIPhSelectorDSCP, hTPSAspi, hTPSASelectorOpaques, hFFUniversalEdition, hLocalCKListKMIDBegin, hIPhRuleTableLastChanged, hIPhFFSALastChanged, hTPSASelectorNextHeaderOpt2Start, hPPKChainEffectiveDate, hTPSALocalPTAddress, hTPSATRPMDControlPlaneSignaling, hIPhRuleAdminStatus, hTPAddMapRowStatus, hTPSAECN, hTPSAAddressSelectorTable, hIPhSelectorNextHeaderOpt2End, hIPhFFSADecrementTTL, hTPSADFBit, hTPSARetryICMPCount, hIPhFFSAPHRDRate, hIPhFFSARowStatus, hTPTFCConfigTableCount, hPreplacedKeyTableCapacity, hFFUniversalID, hIPhFFSATransformRowStatus, hTPSARemoteCTAddress, hFFSecurityLevels, hTPSALocalCredentialType, hTPSAFlowLabelValue, hTPSAEncryptAlgorithm, hIPhSelectorRowStatus, hTPTransMapSourcePTAddress, hIPhFFSAPDUNEnabled, hIPhFFSATransformIntegrityAlgorithm, hTPSALocalCTAddress, hTPSAPDUNEnabled, hIPhFFSADIndexType, hTPAddMapLastChanged, hFFEnhancedFFTag, hTPSASelectorNextHeaderEnd, hPPKTrafficTableMaxCount, hIPhFFSATableLastChanged, hTPSATableCount, hTPiSPI, hPreplacedKeyTableCount, hIPhSelectorDstAddressEnd, hTPSASelectorType, hPPKEKUniversalID, hIPhRuleAction, hLocalCKListUniversal, hTPSALocalCredentialID, hIPhSelectorNextHeaderOpt2Start, hIPhRuleRowStatus, hTPSAStartTime, hLocalCompromisedKeyListTable, hFFLastChanged, hIPhSelectorDstAddressBegin, hFFIsTestKey, hTPTransMapLastChanged, hTPSADIndexType, hTPSASelectorNextHeaderOpt1End, hTPSATableLastChanged, hIPhFFSAFF, hPPKTrafficEncryptAlgorithm, hTPSARemoteCredentialID, hIPhFFSAFlowLabel, hPPKKeyExpirationWarning, hTPSAPPK, hIPhFFSACTOutAddress, hIPhRuleSelectorName, hIPhSelectorOpaques, hIPhFFSAPopulateFromPacket, hTPSASecurityPayloadType, hIPhFFSATFCConfig, hIPhRuleName, hIPhRuleTableCount, hLocalCKListUniversalEdition, hFireflyTableCount, hTPSAAddressEnd, hTPSAAddressType, hPPKSegment, hUniversalID, hPPKEKTable, hIPhSelectorLastChanged, hTPSAPHRDRate, hLocalCKListDate, hTPSAAddressStart, hPPKChainTableLastChanged, hIPhSelectorType, hPPKChainTableCount, hPPKChainEncryptionAlgorithm, hIPhSelectorTableCount
      FROM HAIPE-TRAFFIC-PROTECTION-MIB
    snmpNotifyFilterProfileName, snmpNotifyStorageType, snmpNotifyRowStatus, snmpNotifyType, snmpNotifyTag, snmpNotifyFilterRowStatus, snmpNotifyFilterType, snmpNotifyFilterProfileRowStatus, snmpNotifyFilterStorageType, snmpNotifyFilterProfileStorType, snmpNotifyFilterMask
      FROM SNMP-NOTIFICATION-MIB
;

haipeV030102ComplianceMIB MODULE-IDENTITY
    LAST-UPDATED "200810030834Z"
    ORGANIZATION "HAIPE PO"
    CONTACT-INFO
         "(U//FOUO) Not Available"
    DESCRIPTION
        "(U//FOUO) This MIB defines compliance statements which
        define the levels of conformance required by the various HAIPE
        Version 3.1.2 IS documents.

        (U//FOUO) This MIB is not entirely conformant to SMIv2 parsing
        rules. Specifically, object groups are only allowed to
        reference objects defined in the local MIB, and in this file
        we're importing a large number of objects from other MIBs
        rather than importing their particular object groups."
    ::= { haipeComplianceMIB 3 1 2 }

haipeV030102Conformance OBJECT IDENTIFIER ::= { haipeV030102ComplianceMIB 1 }
haipeV030102Groups      OBJECT IDENTIFIER ::= { haipeV030102ComplianceMIB 2 }

--
-- Objects referenced by the Implicit Peer Enclave Prefix Discovery Document
--
hImplicitPeerEnclavePrefixDiscoveryGroup OBJECT-GROUP
    OBJECTS {
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hIfv4SegCoreModeEnable,
                hIfv6InterfaceIdentifier,
                hIfv6SegCoreModeEnable,
                hIfv6SubIdentifier,
                hiaaInterface,
                hiaaType,
                hiaaAddress,
                hiaaPrefixLen,
                hiaaRowStatus,
                hIPhRuleSelectorName,
                hIPhRuleAction,
                hIPhRuleActionIndex,
                hIPhSelectorType,
                hIPhSelectorIPVersion,
                hIPhSelectorDstAddressBegin,
                hIPhSelectorDstAddressEnd,
                hIPhSelectorNextHeaderStart,
                hIPhSelectorNextHeaderEnd,
                hIPhSelectorNextHeaderOpt1Start,
                hIPhSelectorNextHeaderOpt1End
            }
    STATUS    current
    DESCRIPTION
        "(U//FOUO) Objects for the 'Implicit Peer Enclave Prefix Discovery' document"
    ::= { haipeV030102Groups 1 }

--
-- Conformance levels required by the 'Implicit Peer Enclave Prefix Discovery' document
--
hImplicitPeerEnclavePrefixDiscoveryCompliance MODULE-COMPLIANCE
    STATUS    current
    DESCRIPTION
        "(U//FOUO) Compliance levels for objects required by the
          'Implicit Peer Enclave Prefix Discovery' document"
    MODULE -- this module
    MANDATORY-GROUPS { hImplicitPeerEnclavePrefixDiscoveryGroup }

    OBJECT		hIfv6SubIdentifier
    MIN-ACCESS	read-write
    DESCRIPTION
        "(U//FOUO) Implementation of this object can be as low
         as read-write depending on which
         IS Objective or MIB desired requirements are
         not being met by the implementation.
        "

    OBJECT		hIfv4SegCoreModeEnable
    MIN-ACCESS	read-write
    DESCRIPTION
        "(U//FOUO) Implementation of this object can be as low
         as read-write depending on which
         IS Objective or MIB desired requirements are
         not being met by the implementation.
        "

    OBJECT		hRemoteEnclaveDestHaipeNATPort
    MIN-ACCESS	read-only
    DESCRIPTION
        "(U//FOUO) Implementation of this object can be as low
         as read-only depending on which
         IS Objective or MIB desired requirements are
         not being met by the implementation.
        "

    OBJECT		hiaaType
    MIN-ACCESS	read-write
    DESCRIPTION
        "(U//FOUO) Implementation of this object can be as low
         as read-write depending on which
         IS Objective or MIB desired requirements are
         not being met by the implementation.
        "

    OBJECT		hRemoteEnclaveDestHaipeCTAddrType
    MIN-ACCESS	read-only
    DESCRIPTION
        "(U//FOUO) Implementation of this object can be as low
         as read-only depending on which
         IS Objective or MIB desired requirements are
         not being met by the implementation.
        "

    OBJECT		hRemoteEnclaveDestHostPTPfxLen
    MIN-ACCESS	read-only
    DESCRIPTION
        "(U//FOUO) Implementation of this object can be as low
         as read-only depending on which
         IS Objective or MIB desired requirements are
         not being met by the implementation.
        "

    OBJECT		hIPhSelectorDstAddressBegin
    MIN-ACCESS	read-write
    DESCRIPTION
        "(U//FOUO) Implementation of this object can be as low
         as read-write depending on which
         IS Objective or MIB desired requirements are
         not being met by the implementation.
        "

    OBJECT		hRemoteEnclaveLifetime
    MIN-ACCESS	read-only
    DESCRIPTION
        "(U//FOUO) Implementation of this object can be as low
         as read-only depending on which
         IS Objective or MIB desired requirements are
         not being met by the implementation.
        "

    OBJECT		hRemoteEnclaveDestHaipeNATAddr
    MIN-ACCESS	read-only
    DESCRIPTION
        "(U//FOUO) Implementation of this object can be as low
         as read-only depending on which
         IS Objective or MIB desired requirements are
         not being met by the implementation.
        "

    OBJECT		hDiscSearchStartAddress
    MIN-ACCESS	read-write
    DESCRIPTION
        "(U//FOUO) Implementation of this object can be as low
         as read-write depending on which
         IS Objective or MIB desired requirements are
         not being met by the implementation.
        "

    OBJECT		hRemoteEnclaveMethod
    MIN-ACCESS	read-only
    DESCRIPTION
        "(U//FOUO) Implementation of this object can be as low
         as read-only depending on which
         IS Objective or MIB desired requirements are
         not being met by the implementation.
        "

    OBJECT		hRemoteEnclaveDestHostAddrType
    MIN-ACCESS	read-only
    DESCRIPTION
        "(U//FOUO) Implementation of this object can be as low
         as read-only depending on which
         IS Objective or MIB desired requirements are
         not being met by the implementation.
        "

    OBJECT		hIPhSelectorNextHeaderOpt1End
    MIN-ACCESS	read-only
    DESCRIPTION
        "(U//FOUO) Implementation of this object can be as low
         as read-only depending on which
         IS Objective or MIB desired requirements are
         not being met by the implementation.
        "

    OBJECT		hDiscDelivPTAddress
    MIN-ACCESS	read-write
    DESCRIPTION
        "(U//FOUO) Implementation of this object can be as low
         as read-write depending on which
         IS Objective or MIB desired requirements are
         not being met by the implementation.
        "

    OBJECT		hDiscDelivStatus
    MIN-ACCESS	read-write
    DESCRIPTION
        "(U//FOUO) Implementation of this object can be as low
         as read-write depending on which
         IS Objective or MIB desired requirements are
         not being met by the implementation.
        "

    OBJECT		hDiscSearchEndAddress
    MIN-ACCESS	read-write
    DESCRIPTION
        "(U//FOUO) Implementation of this object can be as low
         as read-write depending on which
         IS Objective or MIB desired requirements are
         not being met by the implementation.
        "

    OBJECT		hDiscDelivType
    MIN-ACCESS	read-write
    DESCRIPTION
        "(U//FOUO) Implementation of this object can be as low
         as read-write depending on which
         IS Objective or MIB desired requirements are
         not being met by the implementation.
        "

    OBJECT		hIPhRuleActionIndex
    MIN-ACCESS	read-only
    DESCRIPTION
        "(U//FOUO) Implementation of this object can be as low
         as read-only depending on which
         IS Objective or MIB desired requirements are
         not being met by the implementation.
        "

    OBJECT		hRemoteEnclaveDestHaipePTAddr
    MIN-ACCESS	read-only
    DESCRIPTION
        "(U//FOUO) Implementation of this object can be as low
         as read-only depending on which
         IS Objective or MIB desired requirements are
         not being met by the implementation.
        "

    OBJECT		hIfv6InterfaceIdentifier
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-only
    DESCRIPTION
        "(U//FOUO) Implementation of this object can be as low
         as read-only depending on which
         IS Objective or MIB desired requirements are
         not being met by the implementation.
        "

    OBJECT		hIPhRuleSelectorName
    MIN-ACCESS	read-only
    DESCRIPTION
        "(U//FOUO) Implementation of this object can be as low
         as read-only depending on which
         IS Objective or MIB desired requirements are
         not being met by the implementation.
        "

    OBJECT		hDiscDelivPriority
    MIN-ACCESS	read-write
    DESCRIPTION
        "(U//FOUO) Implementation of this object can be as low
         as read-write depending on which
         IS Objective or MIB desired requirements are
         not being met by the implementation.
        "

    OBJECT		hiaaPrefixLen
    MIN-ACCESS	read-write
    DESCRIPTION
        "(U//FOUO) Implementation of this object can be as low
         as read-write depending on which
         IS Objective or MIB desired requirements are
         not being met by the implementation.
        "

    OBJECT		hRemoteEnclaveRowStatus
    MIN-ACCESS	read-only
    DESCRIPTION
        "(U//FOUO) Implementation of this object can be as low
         as read-only depending on which
         IS Objective or MIB desired requirements are
         not being met by the implementation.
        "

    OBJECT		hIfv6SegCoreModeEnable
    MIN-ACCESS	read-write
    DESCRIPTION
        "(U//FOUO) Implementation of this object can be as low
         as read-write depending on which
         IS Objective or MIB desired requirements are
         not being met by the implementation.
        "

    OBJECT		hDiscDelivPTPort
    MIN-ACCESS	read-write
    DESCRIPTION
        "(U//FOUO) Implementation of this object can be as low
         as read-write depending on which
         IS Objective or MIB desired requirements are
         not being met by the implementation.
        "

    OBJECT		hRemoteEnclaveDestHaipePTAddrType
    MIN-ACCESS	read-only
    DESCRIPTION
        "(U//FOUO) Implementation of this object can be as low
         as read-only depending on which
         IS Objective or MIB desired requirements are
         not being met by the implementation.
        "

    OBJECT		hIPhSelectorNextHeaderStart
    MIN-ACCESS	read-only
    DESCRIPTION
        "(U//FOUO) Implementation of this object can be as low
         as read-only depending on which
         IS Objective or MIB desired requirements are
         not being met by the implementation.
        "

    OBJECT		hDiscSearchAddressType
    MIN-ACCESS	read-write
    DESCRIPTION
        "(U//FOUO) Implementation of this object can be as low
         as read-write depending on which
         IS Objective or MIB desired requirements are
         not being met by the implementation.
        "

    OBJECT		hRemoteEnclaveDestHost
    MIN-ACCESS	read-only
    DESCRIPTION
        "(U//FOUO) Implementation of this object can be as low
         as read-only depending on which
         IS Objective or MIB desired requirements are
         not being met by the implementation.
        "

    OBJECT		hiaaAddress
    MIN-ACCESS	read-write
    DESCRIPTION
        "(U//FOUO) Implementation of this object can be as low
         as read-write depending on which
         IS Objective or MIB desired requirements are
         not being met by the implementation.
        "

    OBJECT		hIPhSelectorNextHeaderEnd
    MIN-ACCESS	read-only
    DESCRIPTION
        "(U//FOUO) Implementation of this object can be as low
         as read-only depending on which
         IS Objective or MIB desired requirements are
         not being met by the implementation.
        "

    OBJECT		hRemoteEnclaveDestHaipeCTAddr
    MIN-ACCESS	read-only
    DESCRIPTION
        "(U//FOUO) Implementation of this object can be as low
         as read-only depending on which
         IS Objective or MIB desired requirements are
         not being met by the implementation.
        "

    OBJECT		hDiscDelivPTAddressType
    MIN-ACCESS	read-write
    DESCRIPTION
        "(U//FOUO) Implementation of this object can be as low
         as read-write depending on which
         IS Objective or MIB desired requirements are
         not being met by the implementation.
        "

    OBJECT		hiaaInterface
    MIN-ACCESS	read-only
    DESCRIPTION
        "(U//FOUO) Implementation of this object can be as low
         as read-only depending on which
         IS Objective or MIB desired requirements are
         not being met by the implementation.
        "

    OBJECT		hIPhSelectorNextHeaderOpt1Start
    MIN-ACCESS	read-only
    DESCRIPTION
        "(U//FOUO) Implementation of this object can be as low
         as read-only depending on which
         IS Objective or MIB desired requirements are
         not being met by the implementation.
        "

    OBJECT		hIPhSelectorDstAddressEnd
    MIN-ACCESS	read-write
    DESCRIPTION
        "(U//FOUO) Implementation of this object can be as low
         as read-write depending on which
         IS Objective or MIB desired requirements are
         not being met by the implementation.
        "

    OBJECT		hIPhSelectorType
    MIN-ACCESS	read-write
    DESCRIPTION
        "(U//FOUO) Implementation of this object can be as low
         as read-write depending on which
         IS Objective or MIB desired requirements are
         not being met by the implementation.
        "

    OBJECT		hIPhSelectorIPVersion
    MIN-ACCESS	read-write
    DESCRIPTION
        "(U//FOUO) Implementation of this object can be as low
         as read-write depending on which
         IS Objective or MIB desired requirements are
         not being met by the implementation.
        "

    OBJECT		hiaaRowStatus
    MIN-ACCESS	read-only
    DESCRIPTION
        "(U//FOUO) Implementation of this object can be as low
         as read-only depending on which
         IS Objective or MIB desired requirements are
         not being met by the implementation.
        "

    OBJECT		hIPhRuleAction
    MIN-ACCESS	read-write
    DESCRIPTION
        "(U//FOUO) Implementation of this object can be as low
         as read-write depending on which
         IS Objective or MIB desired requirements are
         not being met by the implementation.
        "
::= { haipeV030102Conformance 1 }

--
-- Objects referenced by the HAIPE IS Document
--
hHAIPEISGroup OBJECT-GROUP
    OBJECTS {
                hKTIBAuthControllersTableCount,
                hKTIBAuthControllersTableLastChanged,
                hKTIBACName,
                hKTIBACAddressType,
                hKTIBACAddress,
                hKTIBACRowStatus,
                hKTIBDKShortTitle,
                hKTIBDKPPKEdition,
                hKTIBDKPPKSegment,
                hKTIBDKRowStatus,
                hDeviceVersionTableCount,
                hDeviceVersionTableLastChanged,
                hdvName,
                hdvVersion,
--                hAudNotificationLogWarning,
--                hAudNotificationLogFull,
--                hAudNotificationLogOk,
--                hGenericAuditNotification,
                hNotificationLogCapacityPercentage,
                hNotificationLogWarningPercentage,
                hNotificationLogFullBehavior,
                hNotificationLogReset,
                hNotificationLogPartialReset,
                hAuditConfigTableCount,
                hAuditConfigTableLastChanged,
                hAudCfgID,
                hAudCfgThrottlingEnabled,
                hAudCfgLogThrottleCfg,
                hAudCfgLogThrottleStatus,
                hAudCfgLogCount,
                hAudCfgLogThrottled,
                hAudCfgNotifEnabled,
                hAudCfgNotifThrottleCfg,
                hAudCfgNotifThrottleStatus,
                hAudCfgNotifCount,
                hAudCfgNotifThrottled,
                hAudCfgRowStatus,
                hAudThrottleConfigTableCount,
                hAudThrottleConfigTableLastChanged,
                hAudThrottleCfgName,
                hAudThrottleCfgThreshold,
                hAudThrottleCfgInterval,
                hAudThrottleCfgLastChanged,
                hAudThrottleCfgRowStatus,
                hLocalEnclaveTableCount,
                hLocalEnclaveTableLastChanged,
                hLocalEnclaveDestHostAddrType,
                hLocalEnclaveDestHost,
                hLocalEnclaveDestHostPTPfxLen,
                hLocalEnclaveDestAdminCost,
                hLocalEnclaveMethod,
                hLocalEnclaveLifetime,
                hLocalEnclaveRowStatus,
                hRemoteEnclaveTableCount,
                hRemoteEnclaveTableLastChanged,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hIfv4LowPMTUThreshold,
                hIfv4PMTUResetPeriod,
                hIfv4MTU,
                hIfv4TTL,
                hIfv6Side,
                hIfv6AddressAutoConfig,
                hIfv6DupAddressDetection,
                hIfv6DupAddressRecoveryID,
                hIfv6UseDepAddress,
                hIfv6RouterSolicitation,
                hIfv6DiscardUnauthRed,
                hIfv6LowPMTUThreshold,
                hIfv6PMTUResetPeriod,
                hIfv6LastChanged,
                hIfv6MTU,
                hIfv6HopLimit,
                hIfv6BaseReachableTime,
                hIfv6ReachableTime,
                hIfv6RetransmitTime,
                hIfv6NextHeaderSkipList,
                hv6AddressPrefixTableCount,
                hv6AddressPrefixTableLastChanged,
                hv6APAddressPrefixOrigin,
                hv6APAddressPrefixOnLinkFlag,
                hv6APAddressPrefixAutonomousFlag,
                hv6APAddressPrefixAdvPreferredLifetime,
                hv6APAddressPrefixAdvValidLifetime,
                hv6APAdvertisePrefix,
                hv6APRowStatus,
                hv6APLastChanged,
                hiaaInterface,
                hiaaType,
                hiaaAddress,
                hiaaPrefixLen,
                hiaaRowStatus,
                hIGMPMode,
                hMLDMode,
--                hNetDuplicateAddressCheck,
--                hNetDuplicateAddressDetected,
--                hNetDuplicateAddressIfDown,
                hNetSourceAddressType,
                hNetSourceAddress,
                hFireflyTableCount,
                hFireflyTableLastChanged,
                hFFKMID,
                hFFUniversalID,
                hFFUniversalEdition,
                hFFSecurityLevels,
                hFFMaterialType,
                hFFExpiration,
                hFFNextVector,
                hFFPartitionCode,
                hFFLastChanged,
                hFFZeroizeKey,
                hFFASCIIID,
                hFFIsTestKey,
                hFFEnhancedFFTag,
                hFFShortTitleName,
                hPreplacedKeyTableCount,
                hPreplacedKeyTableCapacity,
                hPreplacedKeyTableLastChanged,
                hPPKShortTitleName,
                hPPKEdition,
                hPPKSegment,
                hPPKUsageType,
                hPPKEffectiveDate,
                hPPKSecurityLevel,
                hPPKZeroizeKey,
                hPPKRegister,
                hPPKLastChanged,
                hPPKTrafficTableMaxCount,
                hPPKShortTitleName,
                hPPKEdition,
                hPPKSegment,
                hPPKTrafficIntegrityAlgorithm,
                hPPKTrafficEncryptAlgorithm,
                hPPKShortTitleName,
                hPPKEdition,
                hPPKSegment,
                hPPKEKKeyType,
                hPPKEKUniversalID,
                hPPKChainTableCount,
                hPPKChainTableLastChanged,
                hPPKChainID,
                hPPKChainOrder,
                hPPKChainPPK,
                hPPKChainEffectiveDate,
                hPPKChainEncryptionAlgorithm,
                hPPKChainRowStatus,
--                hFFKeyExpirationWarning,
--                hPPKKeyExpirationWarning,
                hPPKKeyExpirationWarningCount,
                hIPhRuleTableCount,
                hIPhRuleTableLastChanged,
                hIPhRuleName,
                hIPhRuleSelectorName,
                hIPhRuleAction,
                hIPhRuleActionIndex,
                hIPhRuleAdminStatus,
                hIPhRuleLastChanged,
                hIPhRuleRowStatus,
                hIPhSelectorTableCount,
                hIPhSelectorTableLastChanged,
                hIPhSelectorType,
                hIPhSelectorOpaques,
                hIPhSelectorIPVersion,
                hIPhSelectorSrcAddressBegin,
                hIPhSelectorSrcAddressEnd,
                hIPhSelectorDstAddressBegin,
                hIPhSelectorDstAddressEnd,
                hIPhSelectorNextHeaderStart,
                hIPhSelectorNextHeaderEnd,
                hIPhSelectorNextHeaderOpt1Start,
                hIPhSelectorNextHeaderOpt1End,
                hIPhSelectorNextHeaderOpt2Start,
                hIPhSelectorNextHeaderOpt2End,
                hIPhSelectorDSCP,
                hIPhSelectorLastChanged,
                hIPhSelectorRowStatus,
                hIPhFFSATableCount,
                hIPhFFSATableLastChanged,
                hIPhFFSAFF,
                hIPhFFSATransformsName,
                hIPhFFSADSCP,
                hIPhFFSADSCPValue,
                hIPhFFSAECN,
                hIPhFFSAFlowLabel,
                hIPhFFSAFlowLabelValue,
                hIPhFFSADecrementTTL,
                hIPhFFSADIndexType,
                hIPhFFSALastChanged,
                hIPhFFSARowStatus,
                hIPhFFSAPDUNEnabled,
                hIPhFFSAPHRDRate,
                hIPhFFSADFBit,
                hIPhFFSARetryICMPCount,
                hIPhFFSAConnectionType,
                hIPhFFSACTOutAddressType,
                hIPhFFSACTOutAddress,
                hIPhFFSAPopulateFromPacket,
                hIPhFFSAFFUniversal,
                hIPhFFSAFFUniversalEdition,
                hIPhFFSATFCConfig,
                hIPhFFSATransformsTableCount,
                hIPhFFSATransformsTableLastChanged,
                hIPhFFSATransformEncryptAlgorithm,
                hIPhFFSATransformKeyUpdateMethod,
                hIPhFFSATransformKeyUpdateFrequency,
                hIPhFFSATransformCryptoBlockSize,
                hIPhFFSATransformLastChanged,
                hIPhFFSATransformRowStatus,
                hIPhFFSATransformIntegrityAlgorithm,
                hIPhFFSATransformHashAlgorithm,
                hIPhFFSATransformAuthenticationAlgorithm,
                hTPSATableCount,
                hTPSATableLastChanged,
                hTPSAspi,
                hTPSASelectorType,
                hTPSASelectorOpaques,
                hTPSAAddressType,
                hTPSALocalCTAddress,
                hTPSARemoteCTAddress,
                hTPSAPTAddressType,
                hTPSALocalPTAddress,
                hTPSARemotePTAddress,
                hTPSADirection,
                hTPSASelectorNextHeaderStart,
                hTPSASelectorNextHeaderEnd,
                hTPSASelectorNextHeaderOpt1Start,
                hTPSASelectorNextHeaderOpt1End,
                hTPSASelectorNextHeaderOpt2Start,
                hTPSASelectorNextHeaderOpt2End,
                hTPSAConnectionType,
                hTPSASecurityPayloadType,
                hTPSAStartTime,
                hTPSAEndTime,
                hTPSAPPK,
                hTPSACreationReason,
                hTPSAEncryptAlgorithm,
                hTPSAIntegrityAlgorithm,
                hTPSACryptoBlockSize,
                hTPSASelectorDSCP,
                hTPSADSCP,
                hTPSADSCPValue,
                hTPSAPMTU,
                hTPSAECN,
                hTPSAFlowLabel,
                hTPSAFlowLabelValue,
                hTPSADecrementTTL,
                hTPSADIndexType,
                hTPSAPDUNEnabled,
                hTPSAPHRDRate,
                hTPSADFBit,
                hTPSARetryICMPCount,
                hTPSAHCOctets,
                hTPSAHCUcastPkts,
                hTPSAHCMcastPkts,
                hTPSAHCBrdcastPkts,
                hTPSARowStatus,
                hTPSALocalCredentialID,
                hTPSALocalCredentialType,
                hTPSALocalCAName,
                hTPSARemoteCredentialID,
                hTPSARemoteCredentialType,
                hTPSARemoteCAName,
                hTPSAReachable,
                hTPSATFCConfig,
                hTPSATRPMDControlPlaneSignaling,
                hTPSAAddressSrcOrDest,
                hTPSAAddressStart,
                hTPSAAddressEnd,
                hTPSAAddressRowStatus,
                hTPAddMapCTAddress,
                hTPAddMapLastChanged,
                hTPAddMapRowStatus,
                hTPTFCConfigTableCount,
                hTPTFCConfigTableLastChanged,
                hTPTFCConfigTransmissionType,
                hTPTFCConfigTransmissionRate,
                hTPTFCConfigPacketSizeType,
                hTPTFCConfigPacketSize,
                hTPTFCConfigPacketSizeList,
                hTPTFCConfigRowStatus,
--                hTPnSADestroyed,
--                hTPnSACreated,
                hTPiDestinationAddressType,
                hTPiDestinationAddress,
                hTPiSPI,
                hTPiSADestroyedReason,
                hPPKChainID,
                hrSystemDate,
                ifNumber,
                ifIndex,
                ifDescr,
                ifType,
                ifMtu,
                ifSpeed,
                ifPhysAddress,
                ifAdminStatus,
                ifOperStatus,
                ifLastChange,
                ifIndex,
                ifName,
                ifInMulticastPkts,
                ifInBroadcastPkts,
                ifOutMulticastPkts,
                ifOutBroadcastPkts,
                ifHCInOctets,
                ifHCInUcastPkts,
                ifHCInMulticastPkts,
                ifHCInBroadcastPkts,
                ifHCOutOctets,
                ifHCOutUcastPkts,
                ifHCOutMulticastPkts,
                ifHCOutBroadcastPkts,
                ifLinkUpDownTrapEnable,
                ifHighSpeed,
                ifPromiscuousMode,
                ifConnectorPresent,
                ifAlias,
                ifCounterDiscontinuityTime,
                ifIndex,
                ifIndex,
                inetCidrRouteNumber,
                inetCidrRouteIfIndex,
                inetCidrRouteType,
                inetCidrRouteProto,
                inetCidrRouteAge,
                inetCidrRouteNextHopAS,
                inetCidrRouteMetric1,
                inetCidrRouteMetric2,
                inetCidrRouteMetric3,
                inetCidrRouteMetric4,
                inetCidrRouteMetric5,
                inetCidrRouteStatus,
                inetCidrRouteDiscards,
                ipv4InterfaceEnableStatus,
                ipv6InterfaceReasmMaxSize,
                ipv6InterfaceIdentifier,
                ipv6InterfaceEnableStatus,
                ipv6InterfaceReachableTime,
                ipv6InterfaceRetransmitTime,
                ipv6InterfaceForwarding,
                ipAddressIfIndex,
                ipAddressType,
                ipAddressPrefix,
                ipAddressOrigin,
                ipAddressStatus,
                ipAddressCreated,
                ipAddressLastChanged,
                ipAddressRowStatus,
                ipAddressStorageType,
                nlmConfigGlobalEntryLimit,
                nlmStatsGlobalNotificationsLogged,
                nlmStatsGlobalNotificationsBumped,
                nlmStatsLogNotificationsLogged,
                nlmStatsLogNotificationsBumped,
                nlmLogTime,
                nlmLogDateAndTime,
                nlmLogEngineID,
                nlmLogEngineTAddress,
                nlmLogEngineTDomain,
                nlmLogContextEngineID,
                nlmLogContextName,
                nlmLogNotificationID,
                nlmLogVariableID,
                nlmLogVariableValueType,
                nlmLogVariableCounter32Val,
                nlmLogVariableUnsigned32Val,
                nlmLogVariableTimeTicksVal,
                nlmLogVariableInteger32Val,
                nlmLogVariableOctetStringVal,
                nlmLogVariableIpAddressVal,
                nlmLogVariableOidVal,
                nlmLogVariableCounter64Val,
                nlmLogVariableOpaqueVal
            }
    STATUS    current
    DESCRIPTION
        "(U//FOUO) Objects for the 'HAIPE IS' document"
    ::= { haipeV030102Groups 2 }

--
-- Conformance levels required by the 'HAIPE IS' document
--
hHAIPEISCompliance MODULE-COMPLIANCE
    STATUS    current
    DESCRIPTION
        "(U//FOUO) Compliance levels for objects required by the
          'HAIPE IS' document"
    MODULE -- this module
    MANDATORY-GROUPS { hHAIPEISGroup }

    OBJECT		hMLDMode
    MIN-ACCESS	read-only
    DESCRIPTION
        "(U//FOUO) Implementation of this object can be as low
         as read-only depending on which
         IS Objective or MIB desired requirements are
         not being met by the implementation.
        "

    OBJECT		hIPhFFSATransformLastChanged
    MIN-ACCESS	read-only
    DESCRIPTION
        "(U//FOUO) Implementation of this object can be as low
         as read-only depending on which
         IS Objective or MIB desired requirements are
         not being met by the implementation.
        "

    OBJECT		hv6APAddressPrefixOrigin
    MIN-ACCESS	read-write
    DESCRIPTION
        "(U//FOUO) Implementation of this object can be as low
         as read-write depending on which
         IS Objective or MIB desired requirements are
         not being met by the implementation.
        "

    OBJECT		hRemoteEnclaveDestHaipeCTAddrType
    MIN-ACCESS	read-write
    DESCRIPTION
        "(U//FOUO) Implementation of this object can be as low
         as read-write depending on which
         IS Objective or MIB desired requirements are
         not being met by the implementation.
        "

    OBJECT		hRemoteEnclaveTableLastChanged
    MIN-ACCESS	read-only
    DESCRIPTION
        "(U//FOUO) Implementation of this object can be as low
         as read-only depending on which
         IS Objective or MIB desired requirements are
         not being met by the implementation.
        "

    OBJECT		nlmLogVariableIpAddressVal
    MIN-ACCESS	read-only
    DESCRIPTION
        "(U//FOUO) Implementation of this object can be as low
         as read-only depending on which
         IS Objective or MIB desired requirements are
         not being met by the implementation.
        "

    OBJECT		hTPSAIntegrityAlgorithm
    MIN-ACCESS	read-write
    DESCRIPTION
        "(U//FOUO) Implementation of this object can be as low
         as read-write depending on which
         IS Objective or MIB desired requirements are
         not being met by the implementation.
        "

    OBJECT		hLocalEnclaveDestHostPTPfxLen
    MIN-ACCESS	read-write
    DESCRIPTION
        "(U//FOUO) Implementation of this object can be as low
         as read-write depending on which
         IS Objective or MIB desired requirements are
         not being met by the implementation.
        "

    OBJECT		hAudThrottleCfgRowStatus
    MIN-ACCESS	read-only
    DESCRIPTION
        "(U//FOUO) Implementation of this object can be as low
         as read-only depending on which
         IS Objective or MIB desired requirements are
         not being met by the implementation.
        "

    OBJECT		hPPKEffectiveDate
    MIN-ACCESS	read-only
    DESCRIPTION
        "(U//FOUO) Implementation of this object can be as low
         as read-only depending on which
         IS Objective or MIB desired requirements are
         not being met by the implementation.
        "

    OBJECT		hTPSAEndTime
    MIN-ACCESS	read-write
    DESCRIPTION
        "(U//FOUO) Implementation of this object can be as low
         as read-write depending on which
         IS Objective or MIB desired requirements are
         not being met by the implementation.
        "

    OBJECT		hTPSARemoteCAName
    MIN-ACCESS	read-only
    DESCRIPTION
        "(U//FOUO) Implementation of this object can be as low
         as read-only depending on which
         IS Objective or MIB desired requirements are
         not being met by the implementation.
        "

    OBJECT		hTPSALocalCAName
    MIN-ACCESS	read-only
    DESCRIPTION
        "(U//FOUO) Implementation of this object can be as low
         as read-only depending on which
         IS Objective or MIB desired requirements are
         not being met by the implementation.
        "

    OBJECT		hFFExpiration
    MIN-ACCESS	read-only
    DESCRIPTION
        "(U//FOUO) Implementation of this object can be as low
         as read-only depending on which
         IS Objective or MIB desired requirements are
         not being met by the implementation.
        "

    OBJECT		hAudCfgLogThrottled
    MIN-ACCESS	not-accessible
    DESCRIPTION
        "(U//FOUO) Implementation of this object can be as low
         as not-accessible depending on which
         IS Objective or MIB desired requirements are
         not being met by the implementation.
        "

    OBJECT		nlmLogVariableCounter64Val
    MIN-ACCESS	read-only
    DESCRIPTION
        "(U//FOUO) Implementation of this object can be as low
         as read-only depending on which
         IS Objective or MIB desired requirements are
         not being met by the implementation.
        "

    OBJECT		hIfv4TTL
    MIN-ACCESS	read-only
    DESCRIPTION
        "(U//FOUO) Implementation of this object can be as low
         as read-only depending on which
         IS Objective or MIB desired requirements are
         not being met by the implementation.
        "

    OBJECT		hIPhSelectorTableLastChanged
    MIN-ACCESS	read-only
    DESCRIPTION
        "(U//FOUO) Implementation of this object can be as low
         as read-only depending on which
         IS Objective or MIB desired requirements are
         not being met by the implementation.
        "

    OBJECT		hIPhFFSATransformAuthenticationAlgorithm
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-write
    DESCRIPTION
        "(U//FOUO) Implementation of this object can be as low
         as read-write depending on which
         IS Objective or MIB desired requirements are
         not being met by the implementation.
        "

    OBJECT		hIfv6DupAddressRecoveryID
    MIN-ACCESS	read-write
    DESCRIPTION
        "(U//FOUO) Implementation of this object can be as low
         as read-write depending on which
         IS Objective or MIB desired requirements are
         not being met by the implementation.
        "

    OBJECT		hIPhFFSATransformsTableCount
    MIN-ACCESS	read-only
    DESCRIPTION
        "(U//FOUO) Implementation of this object can be as low
         as read-only depending on which
         IS Objective or MIB desired requirements are
         not being met by the implementation.
        "

    OBJECT		hAudCfgNotifThrottleCfg
    MIN-ACCESS	read-only
    DESCRIPTION
        "(U//FOUO) Implementation of this object can be as low
         as read-only depending on which
         IS Objective or MIB desired requirements are
         not being met by the implementation.
        "

    OBJECT		hIPhSelectorSrcAddressEnd
    MIN-ACCESS	read-write
    DESCRIPTION
        "(U//FOUO) Implementation of this object can be as low
         as read-write depending on which
         IS Objective or MIB desired requirements are
         not being met by the implementation.
        "

    OBJECT		nlmLogNotificationID
    MIN-ACCESS	read-only
    DESCRIPTION
        "(U//FOUO) Implementation of this object can be as low
         as read-only depending on which
         IS Objective or MIB desired requirements are
         not being met by the implementation.
        "

    OBJECT		hTPSAConnectionType
    MIN-ACCESS	read-write
    DESCRIPTION
        "(U//FOUO) Implementation of this object can be as low
         as read-write depending on which
         IS Objective or MIB desired requirements are
         not being met by the implementation.
        "

    OBJECT		hTPSASelectorNextHeaderOpt2End
    MIN-ACCESS	read-write
    DESCRIPTION
        "(U//FOUO) Implementation of this object can be as low
         as read-write depending on which
         IS Objective or MIB desired requirements are
         not being met by the implementation.
        "

    OBJECT		hIPhFFSADFBit
    MIN-ACCESS	read-write
    DESCRIPTION
        "(U//FOUO) Implementation of this object can be as low
         as read-write depending on which
         IS Objective or MIB desired requirements are
         not being met by the implementation.
        "

    OBJECT		hTPSADSCPValue
    MIN-ACCESS	read-write
    DESCRIPTION
        "(U//FOUO) Implementation of this object can be as low
         as read-write depending on which
         IS Objective or MIB desired requirements are
         not being met by the implementation.
        "

    OBJECT		ipv6InterfaceRetransmitTime
    MIN-ACCESS	read-only
    DESCRIPTION
        "(U//FOUO) Implementation of this object can be as low
         as read-only depending on which
         IS Objective or MIB desired requirements are
         not being met by the implementation.
        "

    OBJECT		hPPKRegister
    MIN-ACCESS	not-accessible
    DESCRIPTION
        "(U//FOUO) Implementation of this object can be as low
         as not-accessible depending on which
         IS Objective or MIB desired requirements are
         not being met by the implementation.
        "

    OBJECT		ifLinkUpDownTrapEnable
    MIN-ACCESS	not-accessible
    DESCRIPTION
        "(U//FOUO) Implementation of this object can be as low
         as not-accessible depending on which
         IS Objective or MIB desired requirements are
         not being met by the implementation.
        "

    OBJECT		hIPhSelectorSrcAddressBegin
    MIN-ACCESS	read-write
    DESCRIPTION
        "(U//FOUO) Implementation of this object can be as low
         as read-write depending on which
         IS Objective or MIB desired requirements are
         not being met by the implementation.
        "

    OBJECT		hIPhFFSATransformKeyUpdateFrequency
    MIN-ACCESS	read-write
    DESCRIPTION
        "(U//FOUO) Implementation of this object can be as low
         as read-write depending on which
         IS Objective or MIB desired requirements are
         not being met by the implementation.
        "

    OBJECT		hTPTFCConfigTransmissionRate
    MIN-ACCESS	not-accessible
    DESCRIPTION
        "(U//FOUO) Implementation of this object can be as low
         as not-accessible depending on which
         IS Objective or MIB desired requirements are
         not being met by the implementation.
        "

    OBJECT		hFFNextVector
    MIN-ACCESS	read-only
    DESCRIPTION
        "(U//FOUO) Implementation of this object can be as low
         as read-only depending on which
         IS Objective or MIB desired requirements are
         not being met by the implementation.
        "

    OBJECT		hPPKEKKeyType
    MIN-ACCESS	read-write
    DESCRIPTION
        "(U//FOUO) Implementation of this object can be as low
         as read-write depending on which
         IS Objective or MIB desired requirements are
         not being met by the implementation.
        "

    OBJECT		hIPhRuleLastChanged
    MIN-ACCESS	read-only
    DESCRIPTION
        "(U//FOUO) Implementation of this object can be as low
         as read-only depending on which
         IS Objective or MIB desired requirements are
         not being met by the implementation.
        "

    OBJECT		hPPKSecurityLevel
    MIN-ACCESS	read-only
    DESCRIPTION
        "(U//FOUO) Implementation of this object can be as low
         as read-only depending on which
         IS Objective or MIB desired requirements are
         not being met by the implementation.
        "

    OBJECT		ipv6InterfaceReachableTime
    MIN-ACCESS	read-only
    DESCRIPTION
        "(U//FOUO) Implementation of this object can be as low
         as read-only depending on which
         IS Objective or MIB desired requirements are
         not being met by the implementation.
        "

    OBJECT		ifHCInBroadcastPkts
    MIN-ACCESS	not-accessible
    DESCRIPTION
        "(U//FOUO) Implementation of this object can be as low
         as not-accessible depending on which
         IS Objective or MIB desired requirements are
         not being met by the implementation.
        "

    OBJECT		hTPSACryptoBlockSize
    MIN-ACCESS	read-write
    DESCRIPTION
        "(U//FOUO) Implementation of this object can be as low
         as read-write depending on which
         IS Objective or MIB desired requirements are
         not being met by the implementation.
        "

    OBJECT		hTPSADirection
    MIN-ACCESS	read-write
    DESCRIPTION
        "(U//FOUO) Implementation of this object can be as low
         as read-write depending on which
         IS Objective or MIB desired requirements are
         not being met by the implementation.
        "

    OBJECT		hIPhSelectorIPVersion
    MIN-ACCESS	read-write
    DESCRIPTION
        "(U//FOUO) Implementation of this object can be as low
         as read-write depending on which
         IS Objective or MIB desired requirements are
         not being met by the implementation.
        "

    OBJECT		hTPiDestinationAddress
    MIN-ACCESS	not-accessible
    DESCRIPTION
        "(U//FOUO) Implementation of this object can be as low
         as not-accessible depending on which
         IS Objective or MIB desired requirements are
         not being met by the implementation.
        "

    OBJECT		hFireflyTableLastChanged
    MIN-ACCESS	read-only
    DESCRIPTION
        "(U//FOUO) Implementation of this object can be as low
         as read-only depending on which
         IS Objective or MIB desired requirements are
         not being met by the implementation.
        "

    OBJECT		hKTIBDKShortTitle
    MIN-ACCESS	read-write
    DESCRIPTION
        "(U//FOUO) Implementation of this object can be as low
         as read-write depending on which
         IS Objective or MIB desired requirements are
         not being met by the implementation.
        "

    OBJECT		nlmLogVariableCounter32Val
    MIN-ACCESS	read-only
    DESCRIPTION
        "(U//FOUO) Implementation of this object can be as low
         as read-only depending on which
         IS Objective or MIB desired requirements are
         not being met by the implementation.
        "

    OBJECT		hPPKShortTitleName
    MIN-ACCESS	read-only
    DESCRIPTION
        "(U//FOUO) Implementation of this object can be as low
         as read-only depending on which
         IS Objective or MIB desired requirements are
         not being met by the implementation.
        "

    OBJECT		hIPhFFSATableCount
    MIN-ACCESS	read-only
    DESCRIPTION
        "(U//FOUO) Implementation of this object can be as low
         as read-only depending on which
         IS Objective or MIB desired requirements are
         not being met by the implementation.
        "

    OBJECT		nlmLogEngineTAddress
    MIN-ACCESS	read-only
    DESCRIPTION
        "(U//FOUO) Implementation of this object can be as low
         as read-only depending on which
         IS Objective or MIB desired requirements are
         not being met by the implementation.
        "

    OBJECT		hTPSAHCOctets
    MIN-ACCESS	not-accessible
    DESCRIPTION
        "(U//FOUO) Implementation of this object can be as low
         as not-accessible depending on which
         IS Objective or MIB desired requirements are
         not being met by the implementation.
        "

    OBJECT		hTPSAPMTU
    MIN-ACCESS	read-only
    DESCRIPTION
        "(U//FOUO) Implementation of this object can be as low
         as read-only depending on which
         IS Objective or MIB desired requirements are
         not being met by the implementation.
        "

    OBJECT		hiaaType
    MIN-ACCESS	read-write
    DESCRIPTION
        "(U//FOUO) Implementation of this object can be as low
         as read-write depending on which
         IS Objective or MIB desired requirements are
         not being met by the implementation.
        "

    OBJECT		ifIndex
    MIN-ACCESS	read-only
    DESCRIPTION
        "(U//FOUO) Implementation of this object can be as low
         as read-only depending on which
         IS Objective or MIB desired requirements are
         not being met by the implementation.
        "

    OBJECT		hTPiDestinationAddressType
    MIN-ACCESS	not-accessible
    DESCRIPTION
        "(U//FOUO) Implementation of this object can be as low
         as not-accessible depending on which
         IS Objective or MIB desired requirements are
         not being met by the implementation.
        "

    OBJECT		hFFShortTitleName
    MIN-ACCESS	read-only
    DESCRIPTION
        "(U//FOUO) Implementation of this object can be as low
         as read-only depending on which
         IS Objective or MIB desired requirements are
         not being met by the implementation.
        "

    OBJECT		hRemoteEnclaveTableCount
    MIN-ACCESS	read-only
    DESCRIPTION
        "(U//FOUO) Implementation of this object can be as low
         as read-only depending on which
         IS Objective or MIB desired requirements are
         not being met by the implementation.
        "

    OBJECT		hTPSASelectorNextHeaderOpt1Start
    MIN-ACCESS	read-write
    DESCRIPTION
        "(U//FOUO) Implementation of this object can be as low
         as read-write depending on which
         IS Objective or MIB desired requirements are
         not being met by the implementation.
        "

    OBJECT		hAudThrottleConfigTableLastChanged
    MIN-ACCESS	read-only
    DESCRIPTION
        "(U//FOUO) Implementation of this object can be as low
         as read-only depending on which
         IS Objective or MIB desired requirements are
         not being met by the implementation.
        "

    OBJECT		ipAddressStorageType
    MIN-ACCESS	read-only
    DESCRIPTION
        "(U//FOUO) Implementation of this object can be as low
         as read-only depending on which
         IS Objective or MIB desired requirements are
         not being met by the implementation.
        "

    OBJECT		ipAddressStatus
    MIN-ACCESS	read-only
    DESCRIPTION
        "(U//FOUO) Implementation of this object can be as low
         as read-only depending on which
         IS Objective or MIB desired requirements are
         not being met by the implementation.
        "

    OBJECT		nlmLogContextName
    MIN-ACCESS	read-only
    DESCRIPTION
        "(U//FOUO) Implementation of this object can be as low
         as read-only depending on which
         IS Objective or MIB desired requirements are
         not being met by the implementation.
        "

    OBJECT		hIPhFFSATransformEncryptAlgorithm
    MIN-ACCESS	read-write
    DESCRIPTION
        "(U//FOUO) Implementation of this object can be as low
         as read-write depending on which
         IS Objective or MIB desired requirements are
         not being met by the implementation.
        "

    OBJECT		hIPhRuleActionIndex
    MIN-ACCESS	read-write
    DESCRIPTION
        "(U//FOUO) Implementation of this object can be as low
         as read-write depending on which
         IS Objective or MIB desired requirements are
         not being met by the implementation.
        "

    OBJECT		hPPKLastChanged
    MIN-ACCESS	read-only
    DESCRIPTION
        "(U//FOUO) Implementation of this object can be as low
         as read-only depending on which
         IS Objective or MIB desired requirements are
         not being met by the implementation.
        "

    OBJECT		hIPhFFSAConnectionType
    MIN-ACCESS	read-write
    DESCRIPTION
        "(U//FOUO) Implementation of this object can be as low
         as read-write depending on which
         IS Objective or MIB desired requirements are
         not being met by the implementation.
        "

    OBJECT		nlmLogVariableOidVal
    MIN-ACCESS	read-only
    DESCRIPTION
        "(U//FOUO) Implementation of this object can be as low
         as read-only depending on which
         IS Objective or MIB desired requirements are
         not being met by the implementation.
        "

    OBJECT		hRemoteEnclaveRowStatus
    MIN-ACCESS	read-write
    DESCRIPTION
        "(U//FOUO) Implementation of this object can be as low
         as read-write depending on which
         IS Objective or MIB desired requirements are
         not being met by the implementation.
        "

    OBJECT		hIGMPMode
    MIN-ACCESS	read-write
    DESCRIPTION
        "(U//FOUO) Implementation of this object can be as low
         as read-write depending on which
         IS Objective or MIB desired requirements are
         not being met by the implementation.
        "

    OBJECT		ifConnectorPresent
    MIN-ACCESS	read-only
    DESCRIPTION
        "(U//FOUO) Implementation of this object can be as low
         as read-only depending on which
         IS Objective or MIB desired requirements are
         not being met by the implementation.
        "

    OBJECT		hTPSAAddressSrcOrDest
    MIN-ACCESS	read-write
    DESCRIPTION
        "(U//FOUO) Implementation of this object can be as low
         as read-write depending on which
         IS Objective or MIB desired requirements are
         not being met by the implementation.
        "

    OBJECT		hTPSARowStatus
    MIN-ACCESS	read-write
    DESCRIPTION
        "(U//FOUO) Implementation of this object can be as low
         as read-write depending on which
         IS Objective or MIB desired requirements are
         not being met by the implementation.
        "

    OBJECT		hIPhFFSAFFUniversalEdition
    MIN-ACCESS	read-write
    DESCRIPTION
        "(U//FOUO) Implementation of this object can be as low
         as read-write depending on which
         IS Objective or MIB desired requirements are
         not being met by the implementation.
        "

    OBJECT		ipAddressOrigin
    MIN-ACCESS	read-only
    DESCRIPTION
        "(U//FOUO) Implementation of this object can be as low
         as read-only depending on which
         IS Objective or MIB desired requirements are
         not being met by the implementation.
        "

    OBJECT		hIPhFFSADSCP
    MIN-ACCESS	read-write
    DESCRIPTION
        "(U//FOUO) Implementation of this object can be as low
         as read-write depending on which
         IS Objective or MIB desired requirements are
         not being met by the implementation.
        "

    OBJECT		hAuditConfigTableCount
    MIN-ACCESS	read-only
    DESCRIPTION
        "(U//FOUO) Implementation of this object can be as low
         as read-only depending on which
         IS Objective or MIB desired requirements are
         not being met by the implementation.
        "

    OBJECT		hIPhFFSAECN
    MIN-ACCESS	read-write
    DESCRIPTION
        "(U//FOUO) Implementation of this object can be as low
         as read-write depending on which
         IS Objective or MIB desired requirements are
         not being met by the implementation.
        "

--    OBJECT		hFFKeyExpirationWarning
--    MIN-ACCESS	accessible-for-notify
--    DESCRIPTION
--        "(U//FOUO) Implementation of this object can be as low
--         as accessible-for-notify depending on which
--         IS Objective or MIB desired requirements are
--         not being met by the implementation.
--        "

    OBJECT		hTPSASelectorNextHeaderStart
    MIN-ACCESS	read-write
    DESCRIPTION
        "(U//FOUO) Implementation of this object can be as low
         as read-write depending on which
         IS Objective or MIB desired requirements are
         not being met by the implementation.
        "

    OBJECT		hIfv6PMTUResetPeriod
    MIN-ACCESS	not-accessible
    DESCRIPTION
        "(U//FOUO) Implementation of this object can be as low
         as not-accessible depending on which
         IS Objective or MIB desired requirements are
         not being met by the implementation.
        "

    OBJECT		hIPhSelectorNextHeaderOpt1Start
    MIN-ACCESS	read-write
    DESCRIPTION
        "(U//FOUO) Implementation of this object can be as low
         as read-write depending on which
         IS Objective or MIB desired requirements are
         not being met by the implementation.
        "

    OBJECT		ifPromiscuousMode
    MIN-ACCESS	not-accessible
    DESCRIPTION
        "(U//FOUO) Implementation of this object can be as low
         as not-accessible depending on which
         IS Objective or MIB desired requirements are
         not being met by the implementation.
        "

    OBJECT		inetCidrRouteMetric5
    MIN-ACCESS	read-write
    DESCRIPTION
        "(U//FOUO) Implementation of this object can be as low
         as read-write depending on which
         IS Objective or MIB desired requirements are
         not being met by the implementation.
        "

    OBJECT		hIPhFFSADSCPValue
    MIN-ACCESS	read-write
    DESCRIPTION
        "(U//FOUO) Implementation of this object can be as low
         as read-write depending on which
         IS Objective or MIB desired requirements are
         not being met by the implementation.
        "

    OBJECT		hIPhFFSARetryICMPCount
    MIN-ACCESS	read-write
    DESCRIPTION
        "(U//FOUO) Implementation of this object can be as low
         as read-write depending on which
         IS Objective or MIB desired requirements are
         not being met by the implementation.
        "

    OBJECT		hRemoteEnclaveDestHaipeNATPort
    MIN-ACCESS	read-write
    DESCRIPTION
        "(U//FOUO) Implementation of this object can be as low
         as read-write depending on which
         IS Objective or MIB desired requirements are
         not being met by the implementation.
        "

    OBJECT		hTPSAAddressRowStatus
    MIN-ACCESS	read-write
    DESCRIPTION
        "(U//FOUO) Implementation of this object can be as low
         as read-write depending on which
         IS Objective or MIB desired requirements are
         not being met by the implementation.
        "

    OBJECT		hTPSARemoteCredentialType
    MIN-ACCESS	read-only
    DESCRIPTION
        "(U//FOUO) Implementation of this object can be as low
         as read-only depending on which
         IS Objective or MIB desired requirements are
         not being met by the implementation.
        "

    OBJECT		ifOutMulticastPkts
    MIN-ACCESS	not-accessible
    DESCRIPTION
        "(U//FOUO) Implementation of this object can be as low
         as not-accessible depending on which
         IS Objective or MIB desired requirements are
         not being met by the implementation.
        "

    OBJECT		hKTIBACAddress
    MIN-ACCESS	read-write
    DESCRIPTION
        "(U//FOUO) Implementation of this object can be as low
         as read-write depending on which
         IS Objective or MIB desired requirements are
         not being met by the implementation.
        "

    OBJECT		hRemoteEnclaveLifetime
    MIN-ACCESS	read-write
    DESCRIPTION
        "(U//FOUO) Implementation of this object can be as low
         as read-write depending on which
         IS Objective or MIB desired requirements are
         not being met by the implementation.
        "

    OBJECT		hTPAddMapCTAddress
    MIN-ACCESS	read-write
    DESCRIPTION
        "(U//FOUO) Implementation of this object can be as low
         as read-write depending on which
         IS Objective or MIB desired requirements are
         not being met by the implementation.
        "

    OBJECT		hIPhFFSATransformsName
    MIN-ACCESS	read-write
    DESCRIPTION
        "(U//FOUO) Implementation of this object can be as low
         as read-write depending on which
         IS Objective or MIB desired requirements are
         not being met by the implementation.
        "

    OBJECT		hAudCfgNotifEnabled
    MIN-ACCESS	read-only
    DESCRIPTION
        "(U//FOUO) Implementation of this object can be as low
         as read-only depending on which
         IS Objective or MIB desired requirements are
         not being met by the implementation.
        "

    OBJECT		hTPSAHCMcastPkts
    MIN-ACCESS	not-accessible
    DESCRIPTION
        "(U//FOUO) Implementation of this object can be as low
         as not-accessible depending on which
         IS Objective or MIB desired requirements are
         not being met by the implementation.
        "

    OBJECT		hIPhSelectorDSCP
    MIN-ACCESS	not-accessible
    DESCRIPTION
        "(U//FOUO) Implementation of this object can be as low
         as not-accessible depending on which
         IS Objective or MIB desired requirements are
         not being met by the implementation.
        "

    OBJECT		hPPKTrafficIntegrityAlgorithm
    MIN-ACCESS	read-only
    DESCRIPTION
        "(U//FOUO) Implementation of this object can be as low
         as read-only depending on which
         IS Objective or MIB desired requirements are
         not being met by the implementation.
        "

    OBJECT		hTPSASelectorOpaques
    MIN-ACCESS	read-write
    DESCRIPTION
        "(U//FOUO) Implementation of this object can be as low
         as read-write depending on which
         IS Objective or MIB desired requirements are
         not being met by the implementation.
        "

    OBJECT		hIPhRuleTableLastChanged
    MIN-ACCESS	read-only
    DESCRIPTION
        "(U//FOUO) Implementation of this object can be as low
         as read-only depending on which
         IS Objective or MIB desired requirements are
         not being met by the implementation.
        "

    OBJECT		hFFUniversalEdition
    MIN-ACCESS	read-only
    DESCRIPTION
        "(U//FOUO) Implementation of this object can be as low
         as read-only depending on which
         IS Objective or MIB desired requirements are
         not being met by the implementation.
        "

    OBJECT		hAudCfgThrottlingEnabled
    MIN-ACCESS	read-only
    DESCRIPTION
        "(U//FOUO) Implementation of this object can be as low
         as read-only depending on which
         IS Objective or MIB desired requirements are
         not being met by the implementation.
        "

    OBJECT		hTPSASelectorNextHeaderOpt2Start
    MIN-ACCESS	read-write
    DESCRIPTION
        "(U//FOUO) Implementation of this object can be as low
         as read-write depending on which
         IS Objective or MIB desired requirements are
         not being met by the implementation.
        "

    OBJECT		hTPSALocalPTAddress
    MIN-ACCESS	read-write
    DESCRIPTION
        "(U//FOUO) Implementation of this object can be as low
         as read-write depending on which
         IS Objective or MIB desired requirements are
         not being met by the implementation.
        "

--    OBJECT		hAudNotificationLogWarning
--    MIN-ACCESS	accessible-for-notify
--    DESCRIPTION
--        "(U//FOUO) Implementation of this object can be as low
--         as accessible-for-notify depending on which
--         IS Objective or MIB desired requirements are
--         not being met by the implementation.
--        "

--    OBJECT		hGenericAuditNotification
--    MIN-ACCESS	not-accessible
--    DESCRIPTION
--        "(U//FOUO) Implementation of this object can be as low
--         as not-accessible depending on which
--         IS Objective or MIB desired requirements are
--         not being met by the implementation.
--        "

    OBJECT		ipv6InterfaceReasmMaxSize
    MIN-ACCESS	read-only
    DESCRIPTION
        "(U//FOUO) Implementation of this object can be as low
         as read-only depending on which
         IS Objective or MIB desired requirements are
         not being met by the implementation.
        "

    OBJECT		hTPSAECN
    MIN-ACCESS	read-write
    DESCRIPTION
        "(U//FOUO) Implementation of this object can be as low
         as read-write depending on which
         IS Objective or MIB desired requirements are
         not being met by the implementation.
        "

    OBJECT		hIPhSelectorNextHeaderOpt2End
    MIN-ACCESS	read-write
    DESCRIPTION
        "(U//FOUO) Implementation of this object can be as low
         as read-write depending on which
         IS Objective or MIB desired requirements are
         not being met by the implementation.
        "

    OBJECT		hIPhFFSADecrementTTL
    MIN-ACCESS	read-only
    DESCRIPTION
        "(U//FOUO) Implementation of this object can be as low
         as read-only depending on which
         IS Objective or MIB desired requirements are
         not being met by the implementation.
        "

    OBJECT		nlmLogEngineID
    MIN-ACCESS	read-only
    DESCRIPTION
        "(U//FOUO) Implementation of this object can be as low
         as read-only depending on which
         IS Objective or MIB desired requirements are
         not being met by the implementation.
        "

    OBJECT		hTPTFCConfigTableCount
    MIN-ACCESS	not-accessible
    DESCRIPTION
        "(U//FOUO) Implementation of this object can be as low
         as not-accessible depending on which
         IS Objective or MIB desired requirements are
         not being met by the implementation.
        "

    OBJECT		hFFUniversalID
    MIN-ACCESS	read-only
    DESCRIPTION
        "(U//FOUO) Implementation of this object can be as low
         as read-only depending on which
         IS Objective or MIB desired requirements are
         not being met by the implementation.
        "

    OBJECT		hIPhFFSATransformRowStatus
    MIN-ACCESS	read-write
    DESCRIPTION
        "(U//FOUO) Implementation of this object can be as low
         as read-write depending on which
         IS Objective or MIB desired requirements are
         not being met by the implementation.
        "

    OBJECT		nlmStatsLogNotificationsLogged
    MIN-ACCESS	not-accessible
    DESCRIPTION
        "(U//FOUO) Implementation of this object can be as low
         as not-accessible depending on which
         IS Objective or MIB desired requirements are
         not being met by the implementation.
        "

    OBJECT		nlmConfigGlobalEntryLimit
    MIN-ACCESS	read-only
    DESCRIPTION
        "(U//FOUO) Implementation of this object can be as low
         as read-only depending on which
         IS Objective or MIB desired requirements are
         not being met by the implementation.
        "

    OBJECT		hTPSALocalCredentialType
    MIN-ACCESS	read-only
    DESCRIPTION
        "(U//FOUO) Implementation of this object can be as low
         as read-only depending on which
         IS Objective or MIB desired requirements are
         not being met by the implementation.
        "

    OBJECT		hIPhSelectorRowStatus
    MIN-ACCESS	read-write
    DESCRIPTION
        "(U//FOUO) Implementation of this object can be as low
         as read-write depending on which
         IS Objective or MIB desired requirements are
         not being met by the implementation.
        "

    OBJECT		hIPhFFSAPDUNEnabled
    MIN-ACCESS	read-write
    DESCRIPTION
        "(U//FOUO) Implementation of this object can be as low
         as read-write depending on which
         IS Objective or MIB desired requirements are
         not being met by the implementation.
        "

    OBJECT		hIfv6Side
    MIN-ACCESS	read-only
    DESCRIPTION
        "(U//FOUO) Implementation of this object can be as low
         as read-only depending on which
         IS Objective or MIB desired requirements are
         not being met by the implementation.
        "

    OBJECT		hTPSAPDUNEnabled
    MIN-ACCESS	read-write
    DESCRIPTION
        "(U//FOUO) Implementation of this object can be as low
         as read-write depending on which
         IS Objective or MIB desired requirements are
         not being met by the implementation.
        "

    OBJECT		hIPhFFSADIndexType
    MIN-ACCESS	read-write
    DESCRIPTION
        "(U//FOUO) Implementation of this object can be as low
         as read-write depending on which
         IS Objective or MIB desired requirements are
         not being met by the implementation.
        "

    OBJECT		ipAddressRowStatus
    MIN-ACCESS	read-only
    DESCRIPTION
        "(U//FOUO) Implementation of this object can be as low
         as read-only depending on which
         IS Objective or MIB desired requirements are
         not being met by the implementation.
        "

    OBJECT		inetCidrRouteMetric4
    MIN-ACCESS	read-write
    DESCRIPTION
        "(U//FOUO) Implementation of this object can be as low
         as read-write depending on which
         IS Objective or MIB desired requirements are
         not being met by the implementation.
        "

    OBJECT		nlmLogVariableTimeTicksVal
    MIN-ACCESS	read-only
    DESCRIPTION
        "(U//FOUO) Implementation of this object can be as low
         as read-only depending on which
         IS Objective or MIB desired requirements are
         not being met by the implementation.
        "

    OBJECT		ifName
    MIN-ACCESS	read-only
    DESCRIPTION
        "(U//FOUO) Implementation of this object can be as low
         as read-only depending on which
         IS Objective or MIB desired requirements are
         not being met by the implementation.
        "

    OBJECT		hPPKTrafficTableMaxCount
    MIN-ACCESS	read-only
    DESCRIPTION
        "(U//FOUO) Implementation of this object can be as low
         as read-only depending on which
         IS Objective or MIB desired requirements are
         not being met by the implementation.
        "

    OBJECT		nlmLogTime
    MIN-ACCESS	read-only
    DESCRIPTION
        "(U//FOUO) Implementation of this object can be as low
         as read-only depending on which
         IS Objective or MIB desired requirements are
         not being met by the implementation.
        "

    OBJECT		ifOutBroadcastPkts
    MIN-ACCESS	not-accessible
    DESCRIPTION
        "(U//FOUO) Implementation of this object can be as low
         as not-accessible depending on which
         IS Objective or MIB desired requirements are
         not being met by the implementation.
        "

    OBJECT		hIPhFFSATableLastChanged
    MIN-ACCESS	read-only
    DESCRIPTION
        "(U//FOUO) Implementation of this object can be as low
         as read-only depending on which
         IS Objective or MIB desired requirements are
         not being met by the implementation.
        "

    OBJECT		hv6APAddressPrefixAutonomousFlag
    MIN-ACCESS	read-write
    DESCRIPTION
        "(U//FOUO) Implementation of this object can be as low
         as read-write depending on which
         IS Objective or MIB desired requirements are
         not being met by the implementation.
        "

    OBJECT		hAudCfgNotifThrottled
    MIN-ACCESS	not-accessible
    DESCRIPTION
        "(U//FOUO) Implementation of this object can be as low
         as not-accessible depending on which
         IS Objective or MIB desired requirements are
         not being met by the implementation.
        "

    OBJECT		hTPiSPI
    MIN-ACCESS	not-accessible
    DESCRIPTION
        "(U//FOUO) Implementation of this object can be as low
         as not-accessible depending on which
         IS Objective or MIB desired requirements are
         not being met by the implementation.
        "

    OBJECT		hTPSASelectorType
    MIN-ACCESS	read-write
    DESCRIPTION
        "(U//FOUO) Implementation of this object can be as low
         as read-write depending on which
         IS Objective or MIB desired requirements are
         not being met by the implementation.
        "

    OBJECT		hLocalEnclaveDestAdminCost
    MIN-ACCESS	read-write
    DESCRIPTION
        "(U//FOUO) Implementation of this object can be as low
         as read-write depending on which
         IS Objective or MIB desired requirements are
         not being met by the implementation.
        "

    OBJECT		hPPKEKUniversalID
    MIN-ACCESS	read-write
    DESCRIPTION
        "(U//FOUO) Implementation of this object can be as low
         as read-write depending on which
         IS Objective or MIB desired requirements are
         not being met by the implementation.
        "

    OBJECT		hNotificationLogCapacityPercentage
    MIN-ACCESS	read-only
    DESCRIPTION
        "(U//FOUO) Implementation of this object can be as low
         as read-only depending on which
         IS Objective or MIB desired requirements are
         not being met by the implementation.
        "

    OBJECT		hIfv6ReachableTime
    MIN-ACCESS	read-only
    DESCRIPTION
        "(U//FOUO) Implementation of this object can be as low
         as read-only depending on which
         IS Objective or MIB desired requirements are
         not being met by the implementation.
        "

    OBJECT		hIPhRuleAction
    MIN-ACCESS	read-write
    DESCRIPTION
        "(U//FOUO) Implementation of this object can be as low
         as read-write depending on which
         IS Objective or MIB desired requirements are
         not being met by the implementation.
        "

    OBJECT		inetCidrRouteType
    MIN-ACCESS	read-write
    DESCRIPTION
        "(U//FOUO) Implementation of this object can be as low
         as read-write depending on which
         IS Objective or MIB desired requirements are
         not being met by the implementation.
        "

    OBJECT		hIPhSelectorNextHeaderOpt2Start
    MIN-ACCESS	read-write
    DESCRIPTION
        "(U//FOUO) Implementation of this object can be as low
         as read-write depending on which
         IS Objective or MIB desired requirements are
         not being met by the implementation.
        "

    OBJECT		ifHCInMulticastPkts
    MIN-ACCESS	not-accessible
    DESCRIPTION
        "(U//FOUO) Implementation of this object can be as low
         as not-accessible depending on which
         IS Objective or MIB desired requirements are
         not being met by the implementation.
        "

    OBJECT		hTPSAStartTime
    MIN-ACCESS	read-write
    DESCRIPTION
        "(U//FOUO) Implementation of this object can be as low
         as read-write depending on which
         IS Objective or MIB desired requirements are
         not being met by the implementation.
        "

    OBJECT		hFFLastChanged
    MIN-ACCESS	read-only
    DESCRIPTION
        "(U//FOUO) Implementation of this object can be as low
         as read-only depending on which
         IS Objective or MIB desired requirements are
         not being met by the implementation.
        "

    OBJECT		hTPSASelectorNextHeaderOpt1End
    MIN-ACCESS	read-write
    DESCRIPTION
        "(U//FOUO) Implementation of this object can be as low
         as read-write depending on which
         IS Objective or MIB desired requirements are
         not being met by the implementation.
        "

    OBJECT		nlmLogContextEngineID
    MIN-ACCESS	read-only
    DESCRIPTION
        "(U//FOUO) Implementation of this object can be as low
         as read-only depending on which
         IS Objective or MIB desired requirements are
         not being met by the implementation.
        "

    OBJECT		hTPSATableLastChanged
    MIN-ACCESS	read-only
    DESCRIPTION
        "(U//FOUO) Implementation of this object can be as low
         as read-only depending on which
         IS Objective or MIB desired requirements are
         not being met by the implementation.
        "

    OBJECT		hLocalEnclaveLifetime
    MIN-ACCESS	read-write
    DESCRIPTION
        "(U//FOUO) Implementation of this object can be as low
         as read-write depending on which
         IS Objective or MIB desired requirements are
         not being met by the implementation.
        "

    OBJECT		hLocalEnclaveTableCount
    MIN-ACCESS	read-only
    DESCRIPTION
        "(U//FOUO) Implementation of this object can be as low
         as read-only depending on which
         IS Objective or MIB desired requirements are
         not being met by the implementation.
        "

    OBJECT		ipAddressPrefix
    MIN-ACCESS	read-only
    DESCRIPTION
        "(U//FOUO) Implementation of this object can be as low
         as read-only depending on which
         IS Objective or MIB desired requirements are
         not being met by the implementation.
        "

    OBJECT		nlmLogVariableInteger32Val
    MIN-ACCESS	read-only
    DESCRIPTION
        "(U//FOUO) Implementation of this object can be as low
         as read-only depending on which
         IS Objective or MIB desired requirements are
         not being met by the implementation.
        "

    OBJECT		hTPSARemoteCredentialID
    MIN-ACCESS	read-only
    DESCRIPTION
        "(U//FOUO) Implementation of this object can be as low
         as read-only depending on which
         IS Objective or MIB desired requirements are
         not being met by the implementation.
        "

    OBJECT		inetCidrRouteDiscards
    MIN-ACCESS	not-accessible
    DESCRIPTION
        "(U//FOUO) Implementation of this object can be as low
         as not-accessible depending on which
         IS Objective or MIB desired requirements are
         not being met by the implementation.
        "

    OBJECT		hRemoteEnclaveDestHaipePTAddr
    MIN-ACCESS	read-write
    DESCRIPTION
        "(U//FOUO) Implementation of this object can be as low
         as read-write depending on which
         IS Objective or MIB desired requirements are
         not being met by the implementation.
        "

    OBJECT		hTPSAPPK
    MIN-ACCESS	read-write
    DESCRIPTION
        "(U//FOUO) Implementation of this object can be as low
         as read-write depending on which
         IS Objective or MIB desired requirements are
         not being met by the implementation.
        "

    OBJECT		hIfv6MTU
    MIN-ACCESS	read-write
    DESCRIPTION
        "(U//FOUO) Implementation of this object can be as low
         as read-write depending on which
         IS Objective or MIB desired requirements are
         not being met by the implementation.
        "

    OBJECT		nlmStatsGlobalNotificationsBumped
    MIN-ACCESS	not-accessible
    DESCRIPTION
        "(U//FOUO) Implementation of this object can be as low
         as not-accessible depending on which
         IS Objective or MIB desired requirements are
         not being met by the implementation.
        "

    OBJECT		hKTIBACName
    MIN-ACCESS	read-write
    DESCRIPTION
        "(U//FOUO) Implementation of this object can be as low
         as read-write depending on which
         IS Objective or MIB desired requirements are
         not being met by the implementation.
        "

    OBJECT		hIfv4MTU
    MIN-ACCESS	not-accessible
    DESCRIPTION
        "(U//FOUO) Implementation of this object can be as low
         as not-accessible depending on which
         IS Objective or MIB desired requirements are
         not being met by the implementation.
        "

    OBJECT		hv6APAddressPrefixAdvPreferredLifetime
    MIN-ACCESS	read-write
    DESCRIPTION
        "(U//FOUO) Implementation of this object can be as low
         as read-write depending on which
         IS Objective or MIB desired requirements are
         not being met by the implementation.
        "

    OBJECT		hIPhFFSATFCConfig
    MIN-ACCESS	not-accessible
    DESCRIPTION
        "(U//FOUO) Implementation of this object can be as low
         as not-accessible depending on which
         IS Objective or MIB desired requirements are
         not being met by the implementation.
        "

    OBJECT		hAudThrottleCfgName
    MIN-ACCESS	read-only
    DESCRIPTION
        "(U//FOUO) Implementation of this object can be as low
         as read-only depending on which
         IS Objective or MIB desired requirements are
         not being met by the implementation.
        "

    OBJECT		hv6APAddressPrefixOnLinkFlag
    MIN-ACCESS	read-write
    DESCRIPTION
        "(U//FOUO) Implementation of this object can be as low
         as read-write depending on which
         IS Objective or MIB desired requirements are
         not being met by the implementation.
        "

    OBJECT		hAudCfgRowStatus
    MIN-ACCESS	read-only
    DESCRIPTION
        "(U//FOUO) Implementation of this object can be as low
         as read-only depending on which
         IS Objective or MIB desired requirements are
         not being met by the implementation.
        "

    OBJECT		hIfv6AddressAutoConfig
    MIN-ACCESS	read-write
    DESCRIPTION
        "(U//FOUO) Implementation of this object can be as low
         as read-write depending on which
         IS Objective or MIB desired requirements are
         not being met by the implementation.
        "

    OBJECT		hFireflyTableCount
    MIN-ACCESS	read-only
    DESCRIPTION
        "(U//FOUO) Implementation of this object can be as low
         as read-only depending on which
         IS Objective or MIB desired requirements are
         not being met by the implementation.
        "

    OBJECT		hTPSAAddressEnd
    MIN-ACCESS	read-write
    DESCRIPTION
        "(U//FOUO) Implementation of this object can be as low
         as read-write depending on which
         IS Objective or MIB desired requirements are
         not being met by the implementation.
        "

    OBJECT		hRemoteEnclaveDestHost
    MIN-ACCESS	read-write
    DESCRIPTION
        "(U//FOUO) Implementation of this object can be as low
         as read-write depending on which
         IS Objective or MIB desired requirements are
         not being met by the implementation.
        "

    OBJECT		hTPSAAddressType
    MIN-ACCESS	read-write
    DESCRIPTION
        "(U//FOUO) Implementation of this object can be as low
         as read-write depending on which
         IS Objective or MIB desired requirements are
         not being met by the implementation.
        "

    OBJECT		hNetSourceAddress
    MIN-ACCESS	not-accessible
    DESCRIPTION
        "(U//FOUO) Implementation of this object can be as low
         as not-accessible depending on which
         IS Objective or MIB desired requirements are
         not being met by the implementation.
        "

    OBJECT		hPPKSegment
    MIN-ACCESS	read-only
    DESCRIPTION
        "(U//FOUO) Implementation of this object can be as low
         as read-only depending on which
         IS Objective or MIB desired requirements are
         not being met by the implementation.
        "

    OBJECT		hLocalEnclaveDestHost
    MIN-ACCESS	read-write
    DESCRIPTION
        "(U//FOUO) Implementation of this object can be as low
         as read-write depending on which
         IS Objective or MIB desired requirements are
         not being met by the implementation.
        "

    OBJECT		hNetSourceAddressType
    MIN-ACCESS	not-accessible
    DESCRIPTION
        "(U//FOUO) Implementation of this object can be as low
         as not-accessible depending on which
         IS Objective or MIB desired requirements are
         not being met by the implementation.
        "

    OBJECT		hiaaInterface
    MIN-ACCESS	read-write
    DESCRIPTION
        "(U//FOUO) Implementation of this object can be as low
         as read-write depending on which
         IS Objective or MIB desired requirements are
         not being met by the implementation.
        "

    OBJECT		hKTIBDKRowStatus
    MIN-ACCESS	read-write
    DESCRIPTION
        "(U//FOUO) Implementation of this object can be as low
         as read-write depending on which
         IS Objective or MIB desired requirements are
         not being met by the implementation.
        "

    OBJECT		hIfv6DiscardUnauthRed
    MIN-ACCESS	read-only
    DESCRIPTION
        "(U//FOUO) Implementation of this object can be as low
         as read-only depending on which
         IS Objective or MIB desired requirements are
         not being met by the implementation.
        "

    OBJECT		hdvVersion
    MIN-ACCESS	read-only
    DESCRIPTION
        "(U//FOUO) Implementation of this object can be as low
         as read-only depending on which
         IS Objective or MIB desired requirements are
         not being met by the implementation.
        "

    OBJECT		hAudCfgID
    MIN-ACCESS	read-only
    DESCRIPTION
        "(U//FOUO) Implementation of this object can be as low
         as read-only depending on which
         IS Objective or MIB desired requirements are
         not being met by the implementation.
        "

    OBJECT		hPPKChainTableLastChanged
    MIN-ACCESS	read-only
    DESCRIPTION
        "(U//FOUO) Implementation of this object can be as low
         as read-only depending on which
         IS Objective or MIB desired requirements are
         not being met by the implementation.
        "

    OBJECT		hIPhSelectorType
    MIN-ACCESS	read-write
    DESCRIPTION
        "(U//FOUO) Implementation of this object can be as low
         as read-write depending on which
         IS Objective or MIB desired requirements are
         not being met by the implementation.
        "

    OBJECT		hIfv4PMTUResetPeriod
    MIN-ACCESS	not-accessible
    DESCRIPTION
        "(U//FOUO) Implementation of this object can be as low
         as not-accessible depending on which
         IS Objective or MIB desired requirements are
         not being met by the implementation.
        "

    OBJECT		hiaaRowStatus
    MIN-ACCESS	read-write
    DESCRIPTION
        "(U//FOUO) Implementation of this object can be as low
         as read-write depending on which
         IS Objective or MIB desired requirements are
         not being met by the implementation.
        "

    OBJECT		hIfv6LastChanged
    MIN-ACCESS	read-only
    DESCRIPTION
        "(U//FOUO) Implementation of this object can be as low
         as read-only depending on which
         IS Objective or MIB desired requirements are
         not being met by the implementation.
        "

    OBJECT		hPPKChainTableCount
    MIN-ACCESS	read-only
    DESCRIPTION
        "(U//FOUO) Implementation of this object can be as low
         as read-only depending on which
         IS Objective or MIB desired requirements are
         not being met by the implementation.
        "

    OBJECT		hRemoteEnclaveDestHostPTPfxLen
    MIN-ACCESS	read-write
    DESCRIPTION
        "(U//FOUO) Implementation of this object can be as low
         as read-write depending on which
         IS Objective or MIB desired requirements are
         not being met by the implementation.
        "

    OBJECT		inetCidrRouteNumber
    MIN-ACCESS	read-only
    DESCRIPTION
        "(U//FOUO) Implementation of this object can be as low
         as read-only depending on which
         IS Objective or MIB desired requirements are
         not being met by the implementation.
        "

    OBJECT		hIPhSelectorNextHeaderOpt1End
    MIN-ACCESS	read-write
    DESCRIPTION
        "(U//FOUO) Implementation of this object can be as low
         as read-write depending on which
         IS Objective or MIB desired requirements are
         not being met by the implementation.
        "

    OBJECT		hIPhFFSATransformKeyUpdateMethod
    MIN-ACCESS	read-write
    DESCRIPTION
        "(U//FOUO) Implementation of this object can be as low
         as read-write depending on which
         IS Objective or MIB desired requirements are
         not being met by the implementation.
        "

    OBJECT		hPPKChainRowStatus
    MIN-ACCESS	read-write
    DESCRIPTION
        "(U//FOUO) Implementation of this object can be as low
         as read-write depending on which
         IS Objective or MIB desired requirements are
         not being met by the implementation.
        "

--    OBJECT		hNetDuplicateAddressCheck
--    MIN-ACCESS	not-accessible
--    DESCRIPTION
--        "(U//FOUO) Implementation of this object can be as low
--         as not-accessible depending on which
--         IS Objective or MIB desired requirements are
--         not being met by the implementation.
--        "

    OBJECT		ifHCOutOctets
    MIN-ACCESS	not-accessible
    DESCRIPTION
        "(U//FOUO) Implementation of this object can be as low
         as not-accessible depending on which
         IS Objective or MIB desired requirements are
         not being met by the implementation.
        "

    OBJECT		hTPTFCConfigPacketSizeList
    MIN-ACCESS	not-accessible
    DESCRIPTION
        "(U//FOUO) Implementation of this object can be as low
         as not-accessible depending on which
         IS Objective or MIB desired requirements are
         not being met by the implementation.

	 Comment from TP.ESP.47: A device must support the ability to
	 configure this list of at least 8 items or less.
        "

    OBJECT		hTPSAPTAddressType
    MIN-ACCESS	read-write
    DESCRIPTION
        "(U//FOUO) Implementation of this object can be as low
         as read-write depending on which
         IS Objective or MIB desired requirements are
         not being met by the implementation.
        "

    OBJECT		hIfv4LowPMTUThreshold
    MIN-ACCESS	not-accessible
    DESCRIPTION
        "(U//FOUO) Implementation of this object can be as low
         as not-accessible depending on which
         IS Objective or MIB desired requirements are
         not being met by the implementation.
        "

--    OBJECT		hAudNotificationLogFull
--    MIN-ACCESS	accessible-for-notify
--    DESCRIPTION
--        "(U//FOUO) Implementation of this object can be as low
--         as accessible-for-notify depending on which
--         IS Objective or MIB desired requirements are
--         not being met by the implementation.
--        "

    OBJECT		nlmLogDateAndTime
    MIN-ACCESS	read-only
    DESCRIPTION
        "(U//FOUO) Implementation of this object can be as low
         as read-only depending on which
         IS Objective or MIB desired requirements are
         not being met by the implementation.
        "

    OBJECT		ifAlias
    MIN-ACCESS	read-only
    DESCRIPTION
        "(U//FOUO) Implementation of this object can be as low
         as read-only depending on which
         IS Objective or MIB desired requirements are
         not being met by the implementation.
        "

    OBJECT		hPPKKeyExpirationWarningCount
    MIN-ACCESS	accessible-for-notify
    DESCRIPTION
        "(U//FOUO) Implementation of this object can be as low
         as accessible-for-notify depending on which
         IS Objective or MIB desired requirements are
         not being met by the implementation.
        "

    OBJECT		hTPTFCConfigPacketSize
    MIN-ACCESS	not-accessible
    DESCRIPTION
        "(U//FOUO) Implementation of this object can be as low
         as not-accessible depending on which
         IS Objective or MIB desired requirements are
         not being met by the implementation.
        "

    OBJECT		ipv4InterfaceEnableStatus
    MIN-ACCESS	read-write
    DESCRIPTION
        "(U//FOUO) Implementation of this object can be as low
         as read-write depending on which
         IS Objective or MIB desired requirements are
         not being met by the implementation.
        "

    OBJECT		hTPSASelectorDSCP
    MIN-ACCESS	not-accessible
    DESCRIPTION
        "(U//FOUO) Implementation of this object can be as low
         as not-accessible depending on which
         IS Objective or MIB desired requirements are
         not being met by the implementation.
        "

    OBJECT		ifMtu
    MIN-ACCESS	read-only
    DESCRIPTION
        "(U//FOUO) Implementation of this object can be as low
         as read-only depending on which
         IS Objective or MIB desired requirements are
         not being met by the implementation.
        "

    OBJECT		hIPhFFSATransformHashAlgorithm
    MIN-ACCESS	read-write
    DESCRIPTION
        "(U//FOUO) Implementation of this object can be as low
         as read-write depending on which
         IS Objective or MIB desired requirements are
         not being met by the implementation.
        "

    OBJECT		hPPKChainPPK
    MIN-ACCESS	read-write
    DESCRIPTION
        "(U//FOUO) Implementation of this object can be as low
         as read-write depending on which
         IS Objective or MIB desired requirements are
         not being met by the implementation.
        "

    OBJECT		ipv6InterfaceForwarding
    MIN-ACCESS	read-only
    DESCRIPTION
        "(U//FOUO) Implementation of this object can be as low
         as read-only depending on which
         IS Objective or MIB desired requirements are
         not being met by the implementation.
        "

    OBJECT		hAudCfgLogCount
    MIN-ACCESS	not-accessible
    DESCRIPTION
        "(U//FOUO) Implementation of this object can be as low
         as not-accessible depending on which
         IS Objective or MIB desired requirements are
         not being met by the implementation.
        "

    OBJECT		nlmLogVariableOctetStringVal
    MIN-ACCESS	read-only
    DESCRIPTION
        "(U//FOUO) Implementation of this object can be as low
         as read-only depending on which
         IS Objective or MIB desired requirements are
         not being met by the implementation.
        "

    OBJECT		hTPTFCConfigPacketSizeType
    MIN-ACCESS	not-accessible
    DESCRIPTION
        "(U//FOUO) Implementation of this object can be as low
         as not-accessible depending on which
         IS Objective or MIB desired requirements are
         not being met by the implementation.
        "

    OBJECT		ipAddressIfIndex
    MIN-ACCESS	read-only
    DESCRIPTION
        "(U//FOUO) Implementation of this object can be as low
         as read-only depending on which
         IS Objective or MIB desired requirements are
         not being met by the implementation.
        "

    OBJECT		hIPhSelectorNextHeaderStart
    MIN-ACCESS	read-write
    DESCRIPTION
        "(U//FOUO) Implementation of this object can be as low
         as read-write depending on which
         IS Objective or MIB desired requirements are
         not being met by the implementation.
        "

    OBJECT		ifLastChange
    MIN-ACCESS	read-only
    DESCRIPTION
        "(U//FOUO) Implementation of this object can be as low
         as read-only depending on which
         IS Objective or MIB desired requirements are
         not being met by the implementation.
        "

    OBJECT		hFFMaterialType
    MIN-ACCESS	read-only
    DESCRIPTION
        "(U//FOUO) Implementation of this object can be as low
         as read-only depending on which
         IS Objective or MIB desired requirements are
         not being met by the implementation.
        "

    OBJECT		ifHCOutBroadcastPkts
    MIN-ACCESS	not-accessible
    DESCRIPTION
        "(U//FOUO) Implementation of this object can be as low
         as not-accessible depending on which
         IS Objective or MIB desired requirements are
         not being met by the implementation.
        "

    OBJECT		hFFKMID
    MIN-ACCESS	read-only
    DESCRIPTION
        "(U//FOUO) Implementation of this object can be as low
         as read-only depending on which
         IS Objective or MIB desired requirements are
         not being met by the implementation.
        "

    OBJECT		hTPSARemotePTAddress
    MIN-ACCESS	read-write
    DESCRIPTION
        "(U//FOUO) Implementation of this object can be as low
         as read-write depending on which
         IS Objective or MIB desired requirements are
         not being met by the implementation.
        "

    OBJECT		inetCidrRouteMetric1
    MIN-ACCESS	read-write
    DESCRIPTION
        "(U//FOUO) Implementation of this object can be as low
         as read-write depending on which
         IS Objective or MIB desired requirements are
         not being met by the implementation.
        "

    OBJECT		hAudThrottleConfigTableCount
    MIN-ACCESS	read-only
    DESCRIPTION
        "(U//FOUO) Implementation of this object can be as low
         as read-only depending on which
         IS Objective or MIB desired requirements are
         not being met by the implementation.
        "

    OBJECT		hIPhSelectorNextHeaderEnd
    MIN-ACCESS	read-write
    DESCRIPTION
        "(U//FOUO) Implementation of this object can be as low
         as read-write depending on which
         IS Objective or MIB desired requirements are
         not being met by the implementation.
        "

    OBJECT		inetCidrRouteStatus
    MIN-ACCESS	read-write
    DESCRIPTION
        "(U//FOUO) Implementation of this object can be as low
         as read-write depending on which
         IS Objective or MIB desired requirements are
         not being met by the implementation.
        "

    OBJECT		hKTIBDKPPKSegment
    MIN-ACCESS	read-write
    DESCRIPTION
        "(U//FOUO) Implementation of this object can be as low
         as read-write depending on which
         IS Objective or MIB desired requirements are
         not being met by the implementation.
        "

    OBJECT		hIfv6DupAddressDetection
    MIN-ACCESS	read-write
    DESCRIPTION
        "(U//FOUO) Implementation of this object can be as low
         as read-write depending on which
         IS Objective or MIB desired requirements are
         not being met by the implementation.
        "

    OBJECT		hFFZeroizeKey
    MIN-ACCESS	read-write
    DESCRIPTION
        "(U//FOUO) Implementation of this object can be as low
         as read-write depending on which
         IS Objective or MIB desired requirements are
         not being met by the implementation.
        "

    OBJECT		hdvName
    MIN-ACCESS	read-only
    DESCRIPTION
        "(U//FOUO) Implementation of this object can be as low
         as read-only depending on which
         IS Objective or MIB desired requirements are
         not being met by the implementation.
        "

    OBJECT		hAudThrottleCfgThreshold
    MIN-ACCESS	read-only
    DESCRIPTION
        "(U//FOUO) Implementation of this object can be as low
         as read-only depending on which
         IS Objective or MIB desired requirements are
         not being met by the implementation.
        "

    OBJECT		hPreplacedKeyTableLastChanged
    MIN-ACCESS	read-only
    DESCRIPTION
        "(U//FOUO) Implementation of this object can be as low
         as read-only depending on which
         IS Objective or MIB desired requirements are
         not being met by the implementation.
        "

    OBJECT		hAudCfgNotifCount
    MIN-ACCESS	not-accessible
    DESCRIPTION
        "(U//FOUO) Implementation of this object can be as low
         as not-accessible depending on which
         IS Objective or MIB desired requirements are
         not being met by the implementation.
        "

    OBJECT		hIPhFFSATransformCryptoBlockSize
    MIN-ACCESS	read-write
    DESCRIPTION
        "(U//FOUO) Implementation of this object can be as low
         as read-write depending on which
         IS Objective or MIB desired requirements are
         not being met by the implementation.
        "

    OBJECT		hTPTFCConfigTableLastChanged
    MIN-ACCESS	not-accessible
    DESCRIPTION
        "(U//FOUO) Implementation of this object can be as low
         as not-accessible depending on which
         IS Objective or MIB desired requirements are
         not being met by the implementation.
        "

    OBJECT		hTPSACreationReason
    MIN-ACCESS	read-only
    DESCRIPTION
        "(U//FOUO) Implementation of this object can be as low
         as read-only depending on which
         IS Objective or MIB desired requirements are
         not being met by the implementation.
        "

    OBJECT		hTPSAFlowLabel
    MIN-ACCESS	read-write
    DESCRIPTION
        "(U//FOUO) Implementation of this object can be as low
         as read-write depending on which
         IS Objective or MIB desired requirements are
         not being met by the implementation.
        "

    OBJECT		nlmLogVariableValueType
    MIN-ACCESS	read-only
    DESCRIPTION
        "(U//FOUO) Implementation of this object can be as low
         as read-only depending on which
         IS Objective or MIB desired requirements are
         not being met by the implementation.
        "

    OBJECT		ifOperStatus
    MIN-ACCESS	read-only
    DESCRIPTION
        "(U//FOUO) Implementation of this object can be as low
         as read-only depending on which
         IS Objective or MIB desired requirements are
         not being met by the implementation.
        "

    OBJECT		inetCidrRouteProto
    MIN-ACCESS	read-only
    DESCRIPTION
        "(U//FOUO) Implementation of this object can be as low
         as read-only depending on which
         IS Objective or MIB desired requirements are
         not being met by the implementation.
        "

    OBJECT		ifHCOutUcastPkts
    MIN-ACCESS	not-accessible
    DESCRIPTION
        "(U//FOUO) Implementation of this object can be as low
         as not-accessible depending on which
         IS Objective or MIB desired requirements are
         not being met by the implementation.
        "

    OBJECT		hAudCfgNotifThrottleStatus
    MIN-ACCESS	read-only
    DESCRIPTION
        "(U//FOUO) Implementation of this object can be as low
         as read-only depending on which
         IS Objective or MIB desired requirements are
         not being met by the implementation.
        "

    OBJECT		hIfv6BaseReachableTime
    MIN-ACCESS	read-write
    DESCRIPTION
        "(U//FOUO) Implementation of this object can be as low
         as read-write depending on which
         IS Objective or MIB desired requirements are
         not being met by the implementation.
        "

    OBJECT		hIPhFFSAFFUniversal
    MIN-ACCESS	read-write
    DESCRIPTION
        "(U//FOUO) Implementation of this object can be as low
         as read-write depending on which
         IS Objective or MIB desired requirements are
         not being met by the implementation.
        "

    OBJECT		hPPKZeroizeKey
    MIN-ACCESS	read-write
    DESCRIPTION
        "(U//FOUO) Implementation of this object can be as low
         as read-write depending on which
         IS Objective or MIB desired requirements are
         not being met by the implementation.
        "

    OBJECT		hPPKChainID
    MIN-ACCESS	read-write
    DESCRIPTION
        "(U//FOUO) Implementation of this object can be as low
         as read-write depending on which
         IS Objective or MIB desired requirements are
         not being met by the implementation.
        "

    OBJECT		hPPKChainOrder
    MIN-ACCESS	read-write
    DESCRIPTION
        "(U//FOUO) Implementation of this object can be as low
         as read-write depending on which
         IS Objective or MIB desired requirements are
         not being met by the implementation.
        "

    OBJECT		hTPSAHCUcastPkts
    MIN-ACCESS	not-accessible
    DESCRIPTION
        "(U//FOUO) Implementation of this object can be as low
         as not-accessible depending on which
         IS Objective or MIB desired requirements are
         not being met by the implementation.
        "

    OBJECT		hFFPartitionCode
    MIN-ACCESS	read-only
    DESCRIPTION
        "(U//FOUO) Implementation of this object can be as low
         as read-only depending on which
         IS Objective or MIB desired requirements are
         not being met by the implementation.
        "

    OBJECT		ipv6InterfaceEnableStatus
    MIN-ACCESS	read-write
    DESCRIPTION
        "(U//FOUO) Implementation of this object can be as low
         as read-write depending on which
         IS Objective or MIB desired requirements are
         not being met by the implementation.
        "

    OBJECT		hTPSAReachable
    MIN-ACCESS	read-only
    DESCRIPTION
        "(U//FOUO) Implementation of this object can be as low
         as read-only depending on which
         IS Objective or MIB desired requirements are
         not being met by the implementation.
        "

    OBJECT		hRemoteEnclaveDestHostAddrType
    MIN-ACCESS	read-write
    DESCRIPTION
        "(U//FOUO) Implementation of this object can be as low
         as read-write depending on which
         IS Objective or MIB desired requirements are
         not being met by the implementation.
        "

--    OBJECT		hTPnSACreated
--    MIN-ACCESS	not-accessible
--    DESCRIPTION
--        "(U//FOUO) Implementation of this object can be as low
--         as not-accessible depending on which
--         IS Objective or MIB desired requirements are
--         not being met by the implementation.
--        "

    OBJECT		hTPSATFCConfig
    MIN-ACCESS	not-accessible
    DESCRIPTION
        "(U//FOUO) Implementation of this object can be as low
         as not-accessible depending on which
         IS Objective or MIB desired requirements are
         not being met by the implementation.
        "

--    OBJECT		hTPnSADestroyed
--    MIN-ACCESS	not-accessible
--    DESCRIPTION
--        "(U//FOUO) Implementation of this object can be as low
--         as not-accessible depending on which
--         IS Objective or MIB desired requirements are
--         not being met by the implementation.
--        "

    OBJECT		hLocalEnclaveMethod
    MIN-ACCESS	read-only
    DESCRIPTION
        "(U//FOUO) Implementation of this object can be as low
         as read-only depending on which
         IS Objective or MIB desired requirements are
         not being met by the implementation.
        "

    OBJECT		hIPhFFSATransformsTableLastChanged
    MIN-ACCESS	read-only
    DESCRIPTION
        "(U//FOUO) Implementation of this object can be as low
         as read-only depending on which
         IS Objective or MIB desired requirements are
         not being met by the implementation.
        "

    OBJECT		hKTIBDKPPKEdition
    MIN-ACCESS	read-write
    DESCRIPTION
        "(U//FOUO) Implementation of this object can be as low
         as read-write depending on which
         IS Objective or MIB desired requirements are
         not being met by the implementation.
        "

--    OBJECT		hAudNotificationLogOk
--    MIN-ACCESS	accessible-for-notify
--    DESCRIPTION
--        "(U//FOUO) Implementation of this object can be as low
--         as accessible-for-notify depending on which
--         IS Objective or MIB desired requirements are
--         not being met by the implementation.
--        "

    OBJECT		hDeviceVersionTableCount
    MIN-ACCESS	read-only
    DESCRIPTION
        "(U//FOUO) Implementation of this object can be as low
         as read-only depending on which
         IS Objective or MIB desired requirements are
         not being met by the implementation.
        "

    OBJECT		inetCidrRouteAge
    MIN-ACCESS	read-only
    DESCRIPTION
        "(U//FOUO) Implementation of this object can be as low
         as read-only depending on which
         IS Objective or MIB desired requirements are
         not being met by the implementation.
        "

    OBJECT		hv6APAddressPrefixAdvValidLifetime
    MIN-ACCESS	read-write
    DESCRIPTION
        "(U//FOUO) Implementation of this object can be as low
         as read-write depending on which
         IS Objective or MIB desired requirements are
         not being met by the implementation.
        "

    OBJECT		hFFASCIIID
    MIN-ACCESS	not-accessible
    DESCRIPTION
        "(U//FOUO) Implementation of this object can be as low
         as not-accessible depending on which
         IS Objective or MIB desired requirements are
         not being met by the implementation.
        "

    OBJECT		hiaaPrefixLen
    MIN-ACCESS	read-write
    DESCRIPTION
        "(U//FOUO) Implementation of this object can be as low
         as read-write depending on which
         IS Objective or MIB desired requirements are
         not being met by the implementation.
        "

    OBJECT		hPPKEdition
    MIN-ACCESS	read-only
    DESCRIPTION
        "(U//FOUO) Implementation of this object can be as low
         as read-only depending on which
         IS Objective or MIB desired requirements are
         not being met by the implementation.
        "

    OBJECT		hTPiSADestroyedReason
    MIN-ACCESS	not-accessible
    DESCRIPTION
        "(U//FOUO) Implementation of this object can be as low
         as not-accessible depending on which
         IS Objective or MIB desired requirements are
         not being met by the implementation.
        "

    OBJECT		hTPSAHCBrdcastPkts
    MIN-ACCESS	not-accessible
    DESCRIPTION
        "(U//FOUO) Implementation of this object can be as low
         as not-accessible depending on which
         IS Objective or MIB desired requirements are
         not being met by the implementation.
        "

--    OBJECT		hNetDuplicateAddressIfDown
--    MIN-ACCESS	not-accessible
--    DESCRIPTION
--        "(U//FOUO) Implementation of this object can be as low
--         as not-accessible depending on which
--         IS Objective or MIB desired requirements are
--         not being met by the implementation.
--        "

    OBJECT		ifType
    MIN-ACCESS	read-only
    DESCRIPTION
        "(U//FOUO) Implementation of this object can be as low
         as read-only depending on which
         IS Objective or MIB desired requirements are
         not being met by the implementation.
        "

    OBJECT		ifPhysAddress
    MIN-ACCESS	read-only
    DESCRIPTION
        "(U//FOUO) Implementation of this object can be as low
         as read-only depending on which
         IS Objective or MIB desired requirements are
         not being met by the implementation.
        "

    OBJECT		ifDescr
    MIN-ACCESS	read-only
    DESCRIPTION
        "(U//FOUO) Implementation of this object can be as low
         as read-only depending on which
         IS Objective or MIB desired requirements are
         not being met by the implementation.
        "

    OBJECT		hDeviceVersionTableLastChanged
    MIN-ACCESS	read-only
    DESCRIPTION
        "(U//FOUO) Implementation of this object can be as low
         as read-only depending on which
         IS Objective or MIB desired requirements are
         not being met by the implementation.
        "

    OBJECT		hv6AddressPrefixTableLastChanged
    MIN-ACCESS	read-only
    DESCRIPTION
        "(U//FOUO) Implementation of this object can be as low
         as read-only depending on which
         IS Objective or MIB desired requirements are
         not being met by the implementation.
        "

    OBJECT		nlmLogEngineTDomain
    MIN-ACCESS	read-only
    DESCRIPTION
        "(U//FOUO) Implementation of this object can be as low
         as read-only depending on which
         IS Objective or MIB desired requirements are
         not being met by the implementation.
        "

    OBJECT		hAudCfgLogThrottleStatus
    MIN-ACCESS	read-only
    DESCRIPTION
        "(U//FOUO) Implementation of this object can be as low
         as read-only depending on which
         IS Objective or MIB desired requirements are
         not being met by the implementation.
        "

    OBJECT		hAuditConfigTableLastChanged
    MIN-ACCESS	read-only
    DESCRIPTION
        "(U//FOUO) Implementation of this object can be as low
         as read-only depending on which
         IS Objective or MIB desired requirements are
         not being met by the implementation.
        "

    OBJECT		hKTIBAuthControllersTableLastChanged
    MIN-ACCESS	read-only
    DESCRIPTION
        "(U//FOUO) Implementation of this object can be as low
         as read-only depending on which
         IS Objective or MIB desired requirements are
         not being met by the implementation.
        "

    OBJECT		ifSpeed
    MIN-ACCESS	read-only
    DESCRIPTION
        "(U//FOUO) Implementation of this object can be as low
         as read-only depending on which
         IS Objective or MIB desired requirements are
         not being met by the implementation.
        "

    OBJECT		hLocalEnclaveDestHostAddrType
    MIN-ACCESS	read-write
    DESCRIPTION
        "(U//FOUO) Implementation of this object can be as low
         as read-write depending on which
         IS Objective or MIB desired requirements are
         not being met by the implementation.
        "

    OBJECT		hIPhFFSAFlowLabelValue
    MIN-ACCESS	read-write
    DESCRIPTION
        "(U//FOUO) Implementation of this object can be as low
         as read-write depending on which
         IS Objective or MIB desired requirements are
         not being met by the implementation.
        "

    OBJECT		hPPKUsageType
    MIN-ACCESS	read-write
    DESCRIPTION
        "(U//FOUO) Implementation of this object can be as low
         as read-write depending on which
         IS Objective or MIB desired requirements are
         not being met by the implementation.
        "

    OBJECT		hv6APRowStatus
    MIN-ACCESS	read-write
    DESCRIPTION
        "(U//FOUO) Implementation of this object can be as low
         as read-write depending on which
         IS Objective or MIB desired requirements are
         not being met by the implementation.
        "

    OBJECT		hTPSADecrementTTL
    MIN-ACCESS	read-only
    DESCRIPTION
        "(U//FOUO) Implementation of this object can be as low
         as read-only depending on which
         IS Objective or MIB desired requirements are
         not being met by the implementation.
        "

    OBJECT		hTPTFCConfigRowStatus
    MIN-ACCESS	not-accessible
    DESCRIPTION
        "(U//FOUO) Implementation of this object can be as low
         as not-accessible depending on which
         IS Objective or MIB desired requirements are
         not being met by the implementation.
        "

    OBJECT		hIPhFFSACTOutAddressType
    MIN-ACCESS	read-write
    DESCRIPTION
        "(U//FOUO) Implementation of this object can be as low
         as read-write depending on which
         IS Objective or MIB desired requirements are
         not being met by the implementation.
        "

    OBJECT		hTPTFCConfigTransmissionType
    MIN-ACCESS	not-accessible
    DESCRIPTION
        "(U//FOUO) Implementation of this object can be as low
         as not-accessible depending on which
         IS Objective or MIB desired requirements are
         not being met by the implementation.
        "

    OBJECT		hRemoteEnclaveMethod
    MIN-ACCESS	read-write
    DESCRIPTION
        "(U//FOUO) Implementation of this object can be as low
         as read-write depending on which
         IS Objective or MIB desired requirements are
         not being met by the implementation.
        "

    OBJECT		hTPSAspi
    MIN-ACCESS	read-write
    DESCRIPTION
        "(U//FOUO) Implementation of this object can be as low
         as read-write depending on which
         IS Objective or MIB desired requirements are
         not being met by the implementation.
        "

    OBJECT		hTPSADSCP
    MIN-ACCESS	read-write
    DESCRIPTION
        "(U//FOUO) Implementation of this object can be as low
         as read-write depending on which
         IS Objective or MIB desired requirements are
         not being met by the implementation.
        "

    OBJECT		nlmLogVariableID
    MIN-ACCESS	read-only
    DESCRIPTION
        "(U//FOUO) Implementation of this object can be as low
         as read-only depending on which
         IS Objective or MIB desired requirements are
         not being met by the implementation.
        "

--    OBJECT		hNetDuplicateAddressDetected
--    MIN-ACCESS	not-accessible
--    DESCRIPTION
--        "(U//FOUO) Implementation of this object can be as low
--         as not-accessible depending on which
--         IS Objective or MIB desired requirements are
--         not being met by the implementation.
--        "

    OBJECT		hIPhFFSALastChanged
    MIN-ACCESS	read-only
    DESCRIPTION
        "(U//FOUO) Implementation of this object can be as low
         as read-only depending on which
         IS Objective or MIB desired requirements are
         not being met by the implementation.
        "

    OBJECT		hv6APLastChanged
    MIN-ACCESS	read-only
    DESCRIPTION
        "(U//FOUO) Implementation of this object can be as low
         as read-only depending on which
         IS Objective or MIB desired requirements are
         not being met by the implementation.
        "

    OBJECT		hPPKChainEffectiveDate
    MIN-ACCESS	read-write
    DESCRIPTION
        "(U//FOUO) Implementation of this object can be as low
         as read-write depending on which
         IS Objective or MIB desired requirements are
         not being met by the implementation.
        "

    OBJECT		ifHCInUcastPkts
    MIN-ACCESS	not-accessible
    DESCRIPTION
        "(U//FOUO) Implementation of this object can be as low
         as not-accessible depending on which
         IS Objective or MIB desired requirements are
         not being met by the implementation.
        "

    OBJECT		ifInBroadcastPkts
    MIN-ACCESS	not-accessible
    DESCRIPTION
        "(U//FOUO) Implementation of this object can be as low
         as not-accessible depending on which
         IS Objective or MIB desired requirements are
         not being met by the implementation.
        "

    OBJECT		hTPSATRPMDControlPlaneSignaling
    MIN-ACCESS	read-write
    DESCRIPTION
        "(U//FOUO) Implementation of this object can be as low
         as read-write depending on which
         IS Objective or MIB desired requirements are
         not being met by the implementation.
        "

    OBJECT		hIPhRuleAdminStatus
    MIN-ACCESS	read-write
    DESCRIPTION
        "(U//FOUO) Implementation of this object can be as low
         as read-write depending on which
         IS Objective or MIB desired requirements are
         not being met by the implementation.
        "

    OBJECT		hTPAddMapRowStatus
    MIN-ACCESS	read-write
    DESCRIPTION
        "(U//FOUO) Implementation of this object can be as low
         as read-write depending on which
         IS Objective or MIB desired requirements are
         not being met by the implementation.
        "

    OBJECT		ifCounterDiscontinuityTime
    MIN-ACCESS	not-accessible
    DESCRIPTION
        "(U//FOUO) Implementation of this object can be as low
         as not-accessible depending on which
         IS Objective or MIB desired requirements are
         not being met by the implementation.
        "

    OBJECT		hTPSADFBit
    MIN-ACCESS	read-write
    DESCRIPTION
        "(U//FOUO) Implementation of this object can be as low
         as read-write depending on which
         IS Objective or MIB desired requirements are
         not being met by the implementation.
        "

    OBJECT		hIfv6RetransmitTime
    MIN-ACCESS	read-write
    DESCRIPTION
        "(U//FOUO) Implementation of this object can be as low
         as read-write depending on which
         IS Objective or MIB desired requirements are
         not being met by the implementation.
        "

    OBJECT		hLocalEnclaveTableLastChanged
    MIN-ACCESS	read-only
    DESCRIPTION
        "(U//FOUO) Implementation of this object can be as low
         as read-only depending on which
         IS Objective or MIB desired requirements are
         not being met by the implementation.
        "

    OBJECT		ifHCOutMulticastPkts
    MIN-ACCESS	not-accessible
    DESCRIPTION
        "(U//FOUO) Implementation of this object can be as low
         as not-accessible depending on which
         IS Objective or MIB desired requirements are
         not being met by the implementation.
        "

    OBJECT		hIfv6LowPMTUThreshold
    MIN-ACCESS	not-accessible
    DESCRIPTION
        "(U//FOUO) Implementation of this object can be as low
         as not-accessible depending on which
         IS Objective or MIB desired requirements are
         not being met by the implementation.
        "

    OBJECT		inetCidrRouteNextHopAS
    MIN-ACCESS	read-write
    DESCRIPTION
        "(U//FOUO) Implementation of this object can be as low
         as read-write depending on which
         IS Objective or MIB desired requirements are
         not being met by the implementation.
        "

    OBJECT		hTPSARetryICMPCount
    MIN-ACCESS	read-write
    DESCRIPTION
        "(U//FOUO) Implementation of this object can be as low
         as read-write depending on which
         IS Objective or MIB desired requirements are
         not being met by the implementation.
        "

    OBJECT		hNotificationLogPartialReset
    MIN-ACCESS	not-accessible
    DESCRIPTION
        "(U//FOUO) Implementation of this object can be as low
         as not-accessible depending on which
         IS Objective or MIB desired requirements are
         not being met by the implementation.
        "

    OBJECT		hIPhFFSAPHRDRate
    MIN-ACCESS	read-write
    DESCRIPTION
        "(U//FOUO) Implementation of this object can be as low
         as read-write depending on which
         IS Objective or MIB desired requirements are
         not being met by the implementation.
        "

    OBJECT		hIPhFFSARowStatus
    MIN-ACCESS	read-write
    DESCRIPTION
        "(U//FOUO) Implementation of this object can be as low
         as read-write depending on which
         IS Objective or MIB desired requirements are
         not being met by the implementation.
        "

    OBJECT		hPreplacedKeyTableCapacity
    MIN-ACCESS	read-only
    DESCRIPTION
        "(U//FOUO) Implementation of this object can be as low
         as read-only depending on which
         IS Objective or MIB desired requirements are
         not being met by the implementation.
        "

    OBJECT		nlmLogVariableOpaqueVal
    MIN-ACCESS	read-only
    DESCRIPTION
        "(U//FOUO) Implementation of this object can be as low
         as read-only depending on which
         IS Objective or MIB desired requirements are
         not being met by the implementation.
        "

    OBJECT		hRemoteEnclaveDestHaipePTAddrType
    MIN-ACCESS	read-write
    DESCRIPTION
        "(U//FOUO) Implementation of this object can be as low
         as read-write depending on which
         IS Objective or MIB desired requirements are
         not being met by the implementation.
        "

    OBJECT		hFFSecurityLevels
    MIN-ACCESS	read-only
    DESCRIPTION
        "(U//FOUO) Implementation of this object can be as low
         as read-only depending on which
         IS Objective or MIB desired requirements are
         not being met by the implementation.
        "

    OBJECT		hTPSARemoteCTAddress
    MIN-ACCESS	read-write
    DESCRIPTION
        "(U//FOUO) Implementation of this object can be as low
         as read-write depending on which
         IS Objective or MIB desired requirements are
         not being met by the implementation.
        "

    OBJECT		hIfv6RouterSolicitation
    MIN-ACCESS	read-write
    DESCRIPTION
        "(U//FOUO) Implementation of this object can be as low
         as read-write depending on which
         IS Objective or MIB desired requirements are
         not being met by the implementation.
        "

    OBJECT		hTPSAEncryptAlgorithm
    MIN-ACCESS	read-only
    DESCRIPTION
        "(U//FOUO) Implementation of this object can be as low
         as read-only depending on which
         IS Objective or MIB desired requirements are
         not being met by the implementation.
        "

    OBJECT		hTPSAFlowLabelValue
    MIN-ACCESS	read-write
    DESCRIPTION
        "(U//FOUO) Implementation of this object can be as low
         as read-write depending on which
         IS Objective or MIB desired requirements are
         not being met by the implementation.
        "

    OBJECT		hAudThrottleCfgInterval
    MIN-ACCESS	read-only
    DESCRIPTION
        "(U//FOUO) Implementation of this object can be as low
         as read-only depending on which
         IS Objective or MIB desired requirements are
         not being met by the implementation.
        "

    OBJECT		hiaaAddress
    MIN-ACCESS	read-write
    DESCRIPTION
        "(U//FOUO) Implementation of this object can be as low
         as read-write depending on which
         IS Objective or MIB desired requirements are
         not being met by the implementation.
        "

    OBJECT		hIPhFFSATransformIntegrityAlgorithm
    MIN-ACCESS	read-write
    DESCRIPTION
        "(U//FOUO) Implementation of this object can be as low
         as read-write depending on which
         IS Objective or MIB desired requirements are
         not being met by the implementation.
        "

    OBJECT		hTPSALocalCTAddress
    MIN-ACCESS	read-write
    DESCRIPTION
        "(U//FOUO) Implementation of this object can be as low
         as read-write depending on which
         IS Objective or MIB desired requirements are
         not being met by the implementation.
        "

    OBJECT		hLocalEnclaveRowStatus
    MIN-ACCESS	read-write
    DESCRIPTION
        "(U//FOUO) Implementation of this object can be as low
         as read-write depending on which
         IS Objective or MIB desired requirements are
         not being met by the implementation.
        "

    OBJECT		ipAddressLastChanged
    MIN-ACCESS	read-only
    DESCRIPTION
        "(U//FOUO) Implementation of this object can be as low
         as read-only depending on which
         IS Objective or MIB desired requirements are
         not being met by the implementation.
        "

    OBJECT		hTPAddMapLastChanged
    MIN-ACCESS	read-only
    DESCRIPTION
        "(U//FOUO) Implementation of this object can be as low
         as read-only depending on which
         IS Objective or MIB desired requirements are
         not being met by the implementation.
        "

    OBJECT		nlmStatsGlobalNotificationsLogged
    MIN-ACCESS	not-accessible
    DESCRIPTION
        "(U//FOUO) Implementation of this object can be as low
         as not-accessible depending on which
         IS Objective or MIB desired requirements are
         not being met by the implementation.
        "

    OBJECT		hFFEnhancedFFTag
    MIN-ACCESS	read-only
    DESCRIPTION
        "(U//FOUO) Implementation of this object can be as low
         as read-only depending on which
         IS Objective or MIB desired requirements are
         not being met by the implementation.
        "

    OBJECT		hRemoteEnclaveDestHaipeCTAddr
    MIN-ACCESS	read-write
    DESCRIPTION
        "(U//FOUO) Implementation of this object can be as low
         as read-write depending on which
         IS Objective or MIB desired requirements are
         not being met by the implementation.
        "

    OBJECT		ipAddressType
    MIN-ACCESS	read-only
    DESCRIPTION
        "(U//FOUO) Implementation of this object can be as low
         as read-only depending on which
         IS Objective or MIB desired requirements are
         not being met by the implementation.
        "

    OBJECT		hTPSASelectorNextHeaderEnd
    MIN-ACCESS	read-write
    DESCRIPTION
        "(U//FOUO) Implementation of this object can be as low
         as read-write depending on which
         IS Objective or MIB desired requirements are
         not being met by the implementation.
        "

    OBJECT		ipv6InterfaceIdentifier
    MIN-ACCESS	read-only
    DESCRIPTION
        "(U//FOUO) Implementation of this object can be as low
         as read-only depending on which
         IS Objective or MIB desired requirements are
         not being met by the implementation.
        "

    OBJECT		ifNumber
    MIN-ACCESS	read-only
    DESCRIPTION
        "(U//FOUO) Implementation of this object can be as low
         as read-only depending on which
         IS Objective or MIB desired requirements are
         not being met by the implementation.
        "

    OBJECT		nlmStatsLogNotificationsBumped
    MIN-ACCESS	not-accessible
    DESCRIPTION
        "(U//FOUO) Implementation of this object can be as low
         as not-accessible depending on which
         IS Objective or MIB desired requirements are
         not being met by the implementation.
        "

    OBJECT		hTPSATableCount
    MIN-ACCESS	read-only
    DESCRIPTION
        "(U//FOUO) Implementation of this object can be as low
         as read-only depending on which
         IS Objective or MIB desired requirements are
         not being met by the implementation.
        "

    OBJECT		hIfv6UseDepAddress
    MIN-ACCESS	read-write
    DESCRIPTION
        "(U//FOUO) Implementation of this object can be as low
         as read-write depending on which
         IS Objective or MIB desired requirements are
         not being met by the implementation.
        "

    OBJECT		hNotificationLogFullBehavior
    MIN-ACCESS	read-only
    DESCRIPTION
        "(U//FOUO) Implementation of this object can be as low
         as read-only depending on which
         IS Objective or MIB desired requirements are
         not being met by the implementation.
        "

    OBJECT		hrSystemDate
    MIN-ACCESS	read-write
    DESCRIPTION
        "(U//FOUO) Implementation of this object can be as low
         as read-write depending on which
         IS Objective or MIB desired requirements are
         not being met by the implementation.
        "

    OBJECT		hPreplacedKeyTableCount
    MIN-ACCESS	read-only
    DESCRIPTION
        "(U//FOUO) Implementation of this object can be as low
         as read-only depending on which
         IS Objective or MIB desired requirements are
         not being met by the implementation.
        "

    OBJECT		hIPhSelectorDstAddressEnd
    MIN-ACCESS	read-write
    DESCRIPTION
        "(U//FOUO) Implementation of this object can be as low
         as read-write depending on which
         IS Objective or MIB desired requirements are
         not being met by the implementation.
        "

    OBJECT		inetCidrRouteIfIndex
    MIN-ACCESS	read-write
    DESCRIPTION
        "(U//FOUO) Implementation of this object can be as low
         as read-write depending on which
         IS Objective or MIB desired requirements are
         not being met by the implementation.
        "

    OBJECT		hTPSALocalCredentialID
    MIN-ACCESS	read-only
    DESCRIPTION
        "(U//FOUO) Implementation of this object can be as low
         as read-only depending on which
         IS Objective or MIB desired requirements are
         not being met by the implementation.
        "

    OBJECT		ifAdminStatus
    MIN-ACCESS	read-write
    DESCRIPTION
        "(U//FOUO) Implementation of this object can be as low
         as read-write depending on which
         IS Objective or MIB desired requirements are
         not being met by the implementation.
        "

    OBJECT		hIPhRuleRowStatus
    MIN-ACCESS	read-write
    DESCRIPTION
        "(U//FOUO) Implementation of this object can be as low
         as read-write depending on which
         IS Objective or MIB desired requirements are
         not being met by the implementation.
        "

    OBJECT		hIfv6NextHeaderSkipList
    MIN-ACCESS	read-only
    DESCRIPTION
        "(U//FOUO) Implementation of this object can be as low
         as read-only depending on which
         IS Objective or MIB desired requirements are
         not being met by the implementation.
        "

    OBJECT		hKTIBACRowStatus
    MIN-ACCESS	read-write
    DESCRIPTION
        "(U//FOUO) Implementation of this object can be as low
         as read-write depending on which
         IS Objective or MIB desired requirements are
         not being met by the implementation.
        "

    OBJECT		hRemoteEnclaveDestHaipeNATAddr
    MIN-ACCESS	read-write
    DESCRIPTION
        "(U//FOUO) Implementation of this object can be as low
         as read-write depending on which
         IS Objective or MIB desired requirements are
         not being met by the implementation.
        "

    OBJECT		hIPhSelectorDstAddressBegin
    MIN-ACCESS	read-write
    DESCRIPTION
        "(U//FOUO) Implementation of this object can be as low
         as read-write depending on which
         IS Objective or MIB desired requirements are
         not being met by the implementation.
        "

    OBJECT		hFFIsTestKey
    MIN-ACCESS	not-accessible
    DESCRIPTION
        "(U//FOUO) Implementation of this object can be as low
         as not-accessible depending on which
         IS Objective or MIB desired requirements are
         not being met by the implementation.
        "

    OBJECT		hNotificationLogReset
    MIN-ACCESS	read-write
    DESCRIPTION
        "(U//FOUO) Implementation of this object can be as low
         as read-write depending on which
         IS Objective or MIB desired requirements are
         not being met by the implementation.
        "

    OBJECT		hTPSADIndexType
    MIN-ACCESS	read-write
    DESCRIPTION
        "(U//FOUO) Implementation of this object can be as low
         as read-write depending on which
         IS Objective or MIB desired requirements are
         not being met by the implementation.
        "

    OBJECT		inetCidrRouteMetric2
    MIN-ACCESS	read-write
    DESCRIPTION
        "(U//FOUO) Implementation of this object can be as low
         as read-write depending on which
         IS Objective or MIB desired requirements are
         not being met by the implementation.
        "

    OBJECT		hKTIBAuthControllersTableCount
    MIN-ACCESS	read-only
    DESCRIPTION
        "(U//FOUO) Implementation of this object can be as low
         as read-only depending on which
         IS Objective or MIB desired requirements are
         not being met by the implementation.
        "

    OBJECT		hAudCfgLogThrottleCfg
    MIN-ACCESS	read-only
    DESCRIPTION
        "(U//FOUO) Implementation of this object can be as low
         as read-only depending on which
         IS Objective or MIB desired requirements are
         not being met by the implementation.
        "

    OBJECT		nlmLogVariableUnsigned32Val
    MIN-ACCESS	read-only
    DESCRIPTION
        "(U//FOUO) Implementation of this object can be as low
         as read-only depending on which
         IS Objective or MIB desired requirements are
         not being met by the implementation.
        "

    OBJECT		hIPhFFSAFF
    MIN-ACCESS	read-write
    DESCRIPTION
        "(U//FOUO) Implementation of this object can be as low
         as read-write depending on which
         IS Objective or MIB desired requirements are
         not being met by the implementation.
        "

    OBJECT		hAudThrottleCfgLastChanged
    MIN-ACCESS	read-only
    DESCRIPTION
        "(U//FOUO) Implementation of this object can be as low
         as read-only depending on which
         IS Objective or MIB desired requirements are
         not being met by the implementation.
        "

    OBJECT		hPPKTrafficEncryptAlgorithm
    MIN-ACCESS	read-only
    DESCRIPTION
        "(U//FOUO) Implementation of this object can be as low
         as read-only depending on which
         IS Objective or MIB desired requirements are
         not being met by the implementation.
        "

    OBJECT		ipAddressCreated
    MIN-ACCESS	read-only
    DESCRIPTION
        "(U//FOUO) Implementation of this object can be as low
         as read-only depending on which
         IS Objective or MIB desired requirements are
         not being met by the implementation.
        "

    OBJECT		hv6APAdvertisePrefix
    MIN-ACCESS	read-write
    DESCRIPTION
        "(U//FOUO) Implementation of this object can be as low
         as read-write depending on which
         IS Objective or MIB desired requirements are
         not being met by the implementation.
        "

    OBJECT		hIPhFFSAFlowLabel
    MIN-ACCESS	read-write
    DESCRIPTION
        "(U//FOUO) Implementation of this object can be as low
         as read-write depending on which
         IS Objective or MIB desired requirements are
         not being met by the implementation.
        "

--    OBJECT		hPPKKeyExpirationWarning
--    MIN-ACCESS	accessible-for-notify
--    DESCRIPTION
--        "(U//FOUO) Implementation of this object can be as low
--         as accessible-for-notify depending on which
--         IS Objective or MIB desired requirements are
--         not being met by the implementation.
--        "

    OBJECT		hIfv6HopLimit
    MIN-ACCESS	read-only
    DESCRIPTION
        "(U//FOUO) Implementation of this object can be as low
         as read-only depending on which
         IS Objective or MIB desired requirements are
         not being met by the implementation.
        "

    OBJECT		hIPhFFSACTOutAddress
    MIN-ACCESS	read-write
    DESCRIPTION
        "(U//FOUO) Implementation of this object can be as low
         as read-write depending on which
         IS Objective or MIB desired requirements are
         not being met by the implementation.
        "

    OBJECT		hIPhRuleSelectorName
    MIN-ACCESS	read-write
    DESCRIPTION
        "(U//FOUO) Implementation of this object can be as low
         as read-write depending on which
         IS Objective or MIB desired requirements are
         not being met by the implementation.
        "

    OBJECT		hIPhSelectorOpaques
    MIN-ACCESS	read-write
    DESCRIPTION
        "(U//FOUO) Implementation of this object can be as low
         as read-write depending on which
         IS Objective or MIB desired requirements are
         not being met by the implementation.
        "

    OBJECT		ifInMulticastPkts
    MIN-ACCESS	not-accessible
    DESCRIPTION
        "(U//FOUO) Implementation of this object can be as low
         as not-accessible depending on which
         IS Objective or MIB desired requirements are
         not being met by the implementation.
        "

    OBJECT		hKTIBACAddressType
    MIN-ACCESS	read-write
    DESCRIPTION
        "(U//FOUO) Implementation of this object can be as low
         as read-write depending on which
         IS Objective or MIB desired requirements are
         not being met by the implementation.
        "

    OBJECT		hIPhFFSAPopulateFromPacket
    MIN-ACCESS	not-accessible
    DESCRIPTION
        "(U//FOUO) Implementation of this object can be as low
         as not-accessible depending on which
         IS Objective or MIB desired requirements are
         not being met by the implementation.
        "

    OBJECT		ifHCInOctets
    MIN-ACCESS	not-accessible
    DESCRIPTION
        "(U//FOUO) Implementation of this object can be as low
         as not-accessible depending on which
         IS Objective or MIB desired requirements are
         not being met by the implementation.
        "

    OBJECT		hTPSASecurityPayloadType
    MIN-ACCESS	read-only
    DESCRIPTION
        "(U//FOUO) Implementation of this object can be as low
         as read-only depending on which
         IS Objective or MIB desired requirements are
         not being met by the implementation.
        "

    OBJECT		hIPhRuleTableCount
    MIN-ACCESS	read-only
    DESCRIPTION
        "(U//FOUO) Implementation of this object can be as low
         as read-only depending on which
         IS Objective or MIB desired requirements are
         not being met by the implementation.
        "

    OBJECT		hIPhRuleName
    MIN-ACCESS	read-write
    DESCRIPTION
        "(U//FOUO) Implementation of this object can be as low
         as read-write depending on which
         IS Objective or MIB desired requirements are
         not being met by the implementation.
        "

    OBJECT		inetCidrRouteMetric3
    MIN-ACCESS	read-write
    DESCRIPTION
        "(U//FOUO) Implementation of this object can be as low
         as read-write depending on which
         IS Objective or MIB desired requirements are
         not being met by the implementation.
        "

    OBJECT		hIPhSelectorLastChanged
    MIN-ACCESS	read-only
    DESCRIPTION
        "(U//FOUO) Implementation of this object can be as low
         as read-only depending on which
         IS Objective or MIB desired requirements are
         not being met by the implementation.
        "

    OBJECT		hTPSAPHRDRate
    MIN-ACCESS	read-write
    DESCRIPTION
        "(U//FOUO) Implementation of this object can be as low
         as read-write depending on which
         IS Objective or MIB desired requirements are
         not being met by the implementation.
        "

    OBJECT		hv6AddressPrefixTableCount
    MIN-ACCESS	read-only
    DESCRIPTION
        "(U//FOUO) Implementation of this object can be as low
         as read-only depending on which
         IS Objective or MIB desired requirements are
         not being met by the implementation.
        "

    OBJECT		ifHighSpeed
    MIN-ACCESS	read-only
    DESCRIPTION
        "(U//FOUO) Implementation of this object can be as low
         as read-only depending on which
         IS Objective or MIB desired requirements are
         not being met by the implementation.
        "

    OBJECT		hNotificationLogWarningPercentage
    MIN-ACCESS	read-only
    DESCRIPTION
        "(U//FOUO) Implementation of this object can be as low
         as read-only depending on which
         IS Objective or MIB desired requirements are
         not being met by the implementation.
        "

    OBJECT		hTPSAAddressStart
    MIN-ACCESS	read-write
    DESCRIPTION
        "(U//FOUO) Implementation of this object can be as low
         as read-write depending on which
         IS Objective or MIB desired requirements are
         not being met by the implementation.
        "

    OBJECT		hPPKChainEncryptionAlgorithm
    MIN-ACCESS	read-write
    DESCRIPTION
        "(U//FOUO) Implementation of this object can be as low
         as read-write depending on which
         IS Objective or MIB desired requirements are
         not being met by the implementation.
        "

    OBJECT		hIPhSelectorTableCount
    MIN-ACCESS	read-only
    DESCRIPTION
        "(U//FOUO) Implementation of this object can be as low
         as read-only depending on which
         IS Objective or MIB desired requirements are
         not being met by the implementation.
        "
::= { haipeV030102Conformance 2 }

--
-- Objects referenced by the Reachability Document
--
hReachabilityGroup OBJECT-GROUP
    OBJECTS {
                hLocalEnclaveTableCount,
                hLocalEnclaveTableLastChanged,
                hLocalEnclaveDestHostAddrType,
                hLocalEnclaveDestHost,
                hLocalEnclaveDestHostPTPfxLen,
                hLocalEnclaveDestAdminCost,
                hLocalEnclaveMethod,
                hLocalEnclaveLifetime,
                hLocalEnclaveRowStatus,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hRIPConfTableCount,
                hRIPConfTableLastChanged,
                hrcAddrType,
                hrcAddr,
                hrcAuthType,
                hrcAuthKey,
                hrcSend,
                hrcReceive,
                hrcDefaultMetric,
                hrcAdvertising,
                hrcFilterDefaultRoutes,
                hrcSrcAddress,
                hrcStatus,
                hrcIfConfDomain,
                hrcMetric
            }
    STATUS    current
    DESCRIPTION
        "(U//FOUO) Objects for the 'Reachability' document"
    ::= { haipeV030102Groups 3 }

--
-- Conformance levels required by the 'Reachability' document
--
hReachabilityCompliance MODULE-COMPLIANCE
    STATUS    current
    DESCRIPTION
        "(U//FOUO) Compliance levels for objects required by the
          'Reachability' document"
    MODULE -- this module
    MANDATORY-GROUPS { hReachabilityGroup }

    OBJECT		hrcStatus
    MIN-ACCESS	read-write
    DESCRIPTION
        "(U//FOUO) Implementation of this object can be as low
         as read-write depending on which
         IS Objective or MIB desired requirements are
         not being met by the implementation.
        "

    OBJECT		hRemoteEnclaveDestHaipeNATPort
    MIN-ACCESS	read-only
    DESCRIPTION
        "(U//FOUO) Implementation of this object can be as low
         as read-only depending on which
         IS Objective or MIB desired requirements are
         not being met by the implementation.
        "

    OBJECT		hRemoteEnclaveDestHaipeCTAddrType
    MIN-ACCESS	read-only
    DESCRIPTION
        "(U//FOUO) Implementation of this object can be as low
         as read-only depending on which
         IS Objective or MIB desired requirements are
         not being met by the implementation.
        "

    OBJECT		hRemoteEnclaveDestHostPTPfxLen
    MIN-ACCESS	read-only
    DESCRIPTION
        "(U//FOUO) Implementation of this object can be as low
         as read-only depending on which
         IS Objective or MIB desired requirements are
         not being met by the implementation.
        "

    OBJECT		hRemoteEnclaveLifetime
    MIN-ACCESS	read-only
    DESCRIPTION
        "(U//FOUO) Implementation of this object can be as low
         as read-only depending on which
         IS Objective or MIB desired requirements are
         not being met by the implementation.
        "

    OBJECT		hRemoteEnclaveDestHaipeNATAddr
    MIN-ACCESS	read-only
    DESCRIPTION
        "(U//FOUO) Implementation of this object can be as low
         as read-only depending on which
         IS Objective or MIB desired requirements are
         not being met by the implementation.
        "

    OBJECT		hRIPConfTableLastChanged
    MIN-ACCESS	read-only
    DESCRIPTION
        "(U//FOUO) Implementation of this object can be as low
         as read-only depending on which
         IS Objective or MIB desired requirements are
         not being met by the implementation.
        "

    OBJECT		hrcSrcAddress
    MIN-ACCESS	read-write
    DESCRIPTION
        "(U//FOUO) Implementation of this object can be as low
         as read-write depending on which
         IS Objective or MIB desired requirements are
         not being met by the implementation.
        "

    OBJECT		hLocalEnclaveDestHostPTPfxLen
    MIN-ACCESS	read-write
    DESCRIPTION
        "(U//FOUO) Implementation of this object can be as low
         as read-write depending on which
         IS Objective or MIB desired requirements are
         not being met by the implementation.
        "

    OBJECT		hRemoteEnclaveMethod
    MIN-ACCESS	read-only
    DESCRIPTION
        "(U//FOUO) Implementation of this object can be as low
         as read-only depending on which
         IS Objective or MIB desired requirements are
         not being met by the implementation.
        "

    OBJECT		hRemoteEnclaveDestHostAddrType
    MIN-ACCESS	read-only
    DESCRIPTION
        "(U//FOUO) Implementation of this object can be as low
         as read-only depending on which
         IS Objective or MIB desired requirements are
         not being met by the implementation.
        "

    OBJECT		hLocalEnclaveLifetime
    MIN-ACCESS	read-write
    DESCRIPTION
        "(U//FOUO) Implementation of this object can be as low
         as read-write depending on which
         IS Objective or MIB desired requirements are
         not being met by the implementation.
        "

    OBJECT		hLocalEnclaveTableCount
    MIN-ACCESS	read-only
    DESCRIPTION
        "(U//FOUO) Implementation of this object can be as low
         as read-only depending on which
         IS Objective or MIB desired requirements are
         not being met by the implementation.
        "

    OBJECT		hLocalEnclaveMethod
    MIN-ACCESS	read-only
    DESCRIPTION
        "(U//FOUO) Implementation of this object can be as low
         as read-only depending on which
         IS Objective or MIB desired requirements are
         not being met by the implementation.
        "

    OBJECT		hrcAuthType
    MIN-ACCESS	read-write
    DESCRIPTION
        "(U//FOUO) Implementation of this object can be as low
         as read-write depending on which
         IS Objective or MIB desired requirements are
         not being met by the implementation.
        "

    OBJECT		hRemoteEnclaveDestHaipePTAddr
    MIN-ACCESS	read-only
    DESCRIPTION
        "(U//FOUO) Implementation of this object can be as low
         as read-only depending on which
         IS Objective or MIB desired requirements are
         not being met by the implementation.
        "

    OBJECT		hrcReceive
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-only
    DESCRIPTION
        "(U//FOUO) Implementation of this object can be as low
         as read-only depending on which
         IS Objective or MIB desired requirements are
         not being met by the implementation.
        "

    OBJECT		hLocalEnclaveTableLastChanged
    MIN-ACCESS	read-only
    DESCRIPTION
        "(U//FOUO) Implementation of this object can be as low
         as read-only depending on which
         IS Objective or MIB desired requirements are
         not being met by the implementation.
        "

    OBJECT		hRemoteEnclaveRowStatus
    MIN-ACCESS	read-only
    DESCRIPTION
        "(U//FOUO) Implementation of this object can be as low
         as read-only depending on which
         IS Objective or MIB desired requirements are
         not being met by the implementation.
        "

    OBJECT		hrcIfConfDomain
    MIN-ACCESS	read-write
    DESCRIPTION
        "(U//FOUO) Implementation of this object can be as low
         as read-write depending on which
         IS Objective or MIB desired requirements are
         not being met by the implementation.
        "

    OBJECT		hrcAddr
    MIN-ACCESS	read-write
    DESCRIPTION
        "(U//FOUO) Implementation of this object can be as low
         as read-write depending on which
         IS Objective or MIB desired requirements are
         not being met by the implementation.
        "

    OBJECT		hRemoteEnclaveDestHaipePTAddrType
    MIN-ACCESS	read-only
    DESCRIPTION
        "(U//FOUO) Implementation of this object can be as low
         as read-only depending on which
         IS Objective or MIB desired requirements are
         not being met by the implementation.
        "

    OBJECT		hRemoteEnclaveDestHost
    MIN-ACCESS	read-only
    DESCRIPTION
        "(U//FOUO) Implementation of this object can be as low
         as read-only depending on which
         IS Objective or MIB desired requirements are
         not being met by the implementation.
        "

    OBJECT		hrcDefaultMetric
    MIN-ACCESS	read-write
    DESCRIPTION
        "(U//FOUO) Implementation of this object can be as low
         as read-write depending on which
         IS Objective or MIB desired requirements are
         not being met by the implementation.
        "

    OBJECT		hrcMetric
    MIN-ACCESS	read-write
    DESCRIPTION
        "(U//FOUO) Implementation of this object can be as low
         as read-write depending on which
         IS Objective or MIB desired requirements are
         not being met by the implementation.
        "

    OBJECT		hrcAuthKey
    MIN-ACCESS	read-write
    DESCRIPTION
        "(U//FOUO) Implementation of this object can be as low
         as read-write depending on which
         IS Objective or MIB desired requirements are
         not being met by the implementation.
        "

    OBJECT		hLocalEnclaveRowStatus
    MIN-ACCESS	read-write
    DESCRIPTION
        "(U//FOUO) Implementation of this object can be as low
         as read-write depending on which
         IS Objective or MIB desired requirements are
         not being met by the implementation.
        "

    OBJECT		hrcFilterDefaultRoutes
    MIN-ACCESS	read-write
    DESCRIPTION
        "(U//FOUO) Implementation of this object can be as low
         as read-write depending on which
         IS Objective or MIB desired requirements are
         not being met by the implementation.
        "

    OBJECT		hrcAddrType
    MIN-ACCESS	read-write
    DESCRIPTION
        "(U//FOUO) Implementation of this object can be as low
         as read-write depending on which
         IS Objective or MIB desired requirements are
         not being met by the implementation.
        "

    OBJECT		hrcAdvertising
    MIN-ACCESS	read-write
    DESCRIPTION
        "(U//FOUO) Implementation of this object can be as low
         as read-write depending on which
         IS Objective or MIB desired requirements are
         not being met by the implementation.
        "

    OBJECT		hRemoteEnclaveDestHaipeCTAddr
    MIN-ACCESS	read-only
    DESCRIPTION
        "(U//FOUO) Implementation of this object can be as low
         as read-only depending on which
         IS Objective or MIB desired requirements are
         not being met by the implementation.
        "

    OBJECT		hLocalEnclaveDestHost
    MIN-ACCESS	read-write
    DESCRIPTION
        "(U//FOUO) Implementation of this object can be as low
         as read-write depending on which
         IS Objective or MIB desired requirements are
         not being met by the implementation.
        "

    OBJECT		hrcSend
    MIN-ACCESS	read-write
    DESCRIPTION
        "(U//FOUO) Implementation of this object can be as low
         as read-write depending on which
         IS Objective or MIB desired requirements are
         not being met by the implementation.
        "

    OBJECT		hLocalEnclaveDestHostAddrType
    MIN-ACCESS	read-write
    DESCRIPTION
        "(U//FOUO) Implementation of this object can be as low
         as read-write depending on which
         IS Objective or MIB desired requirements are
         not being met by the implementation.
        "

    OBJECT		hRIPConfTableCount
    MIN-ACCESS	read-only
    DESCRIPTION
        "(U//FOUO) Implementation of this object can be as low
         as read-only depending on which
         IS Objective or MIB desired requirements are
         not being met by the implementation.
        "

    OBJECT		hLocalEnclaveDestAdminCost
    MIN-ACCESS	read-write
    DESCRIPTION
        "(U//FOUO) Implementation of this object can be as low
         as read-write depending on which
         IS Objective or MIB desired requirements are
         not being met by the implementation.
        "
::= { haipeV030102Conformance 3 }

--
-- Objects referenced by the Generic Discovery Client Document
--
hGenericDiscoveryClientGroup OBJECT-GROUP
    OBJECTS {
                hDiscoveryEnabled,
                hDiscoveryAdvertiseAdminCost,
--                hDiscoveryMessageConfig,
                hDiscoveryProbeTimeout,
                hDiscoveryProbeRetry,
                hDiscoveryRegistrationTimeout,
                hDiscoveryRegistrationRetry,
                hDiscoverySolicitationTimeout,
                hDiscoverySolicitationRetry,
                hDiscoveryDeliveryTableCount,
                hDiscoveryDeliveryTableLastChanged,
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hDiscRegistrationTableCount,
                hDiscRegistrationTableLastChanged,
                hDiscRegPriority,
                hDiscRegPTAddressType,
                hDiscRegPTAddress,
                hDiscRegPTPort,
                hDiscRegStatus,
                hDiscRegistrationDefaultLifetime,
                hDiscSolReceptionTableCount,
                hDiscSolReceptionTableLastChanged,
                hDiscSolRcvSide,
                hDiscSolRcvAddressType,
                hDiscSolRcvAddress,
                hDiscSolRcvPort,
                hDiscSolRcvType,
                hDiscSolRcvStatus,
                hRemoteEnclaveTableCount,
                hRemoteEnclaveTableLastChanged,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hIPhFFSAPDUNEnabled,
                hTPSAPDUNEnabled
            }
    STATUS    current
    DESCRIPTION
        "(U//FOUO) Objects for the 'Generic Discovery Client' document"
    ::= { haipeV030102Groups 4 }

--
-- Conformance levels required by the 'Generic Discovery Client' document
--
hGenericDiscoveryClientCompliance MODULE-COMPLIANCE
    STATUS    current
    DESCRIPTION
        "(U//FOUO) Compliance levels for objects required by the
          'Generic Discovery Client' document"
    MODULE -- this module
    MANDATORY-GROUPS { hGenericDiscoveryClientGroup }

    OBJECT		hDiscRegistrationTableLastChanged
    MIN-ACCESS	read-only
    DESCRIPTION
        "(U//FOUO) Implementation of this object can be as low
         as read-only depending on which
         IS Objective or MIB desired requirements are
         not being met by the implementation.
        "

    OBJECT		hRemoteEnclaveDestHaipeNATPort
    MIN-ACCESS	read-write
    DESCRIPTION
        "(U//FOUO) Implementation of this object can be as low
         as read-write depending on which
         IS Objective or MIB desired requirements are
         not being met by the implementation.
        "

    OBJECT		hDiscoverySolicitationRetry
    MIN-ACCESS	read-write
    DESCRIPTION
        "(U//FOUO) Implementation of this object can be as low
         as read-write depending on which
         IS Objective or MIB desired requirements are
         not being met by the implementation.
        "

    OBJECT		hDiscSolRcvSide
    MIN-ACCESS	read-write
    DESCRIPTION
        "(U//FOUO) Implementation of this object can be as low
         as read-write depending on which
         IS Objective or MIB desired requirements are
         not being met by the implementation.
        "

    OBJECT		hRemoteEnclaveDestHaipeCTAddrType
    MIN-ACCESS	read-write
    DESCRIPTION
        "(U//FOUO) Implementation of this object can be as low
         as read-write depending on which
         IS Objective or MIB desired requirements are
         not being met by the implementation.
        "

    OBJECT		hRemoteEnclaveDestHostPTPfxLen
    MIN-ACCESS	read-write
    DESCRIPTION
        "(U//FOUO) Implementation of this object can be as low
         as read-write depending on which
         IS Objective or MIB desired requirements are
         not being met by the implementation.
        "

    OBJECT		hRemoteEnclaveTableLastChanged
    MIN-ACCESS	read-only
    DESCRIPTION
        "(U//FOUO) Implementation of this object can be as low
         as read-only depending on which
         IS Objective or MIB desired requirements are
         not being met by the implementation.
        "

    OBJECT		hRemoteEnclaveLifetime
    MIN-ACCESS	read-write
    DESCRIPTION
        "(U//FOUO) Implementation of this object can be as low
         as read-write depending on which
         IS Objective or MIB desired requirements are
         not being met by the implementation.
        "

    OBJECT		hRemoteEnclaveDestHaipeNATAddr
    MIN-ACCESS	read-write
    DESCRIPTION
        "(U//FOUO) Implementation of this object can be as low
         as read-write depending on which
         IS Objective or MIB desired requirements are
         not being met by the implementation.
        "

    OBJECT		hDiscSearchStartAddress
    MIN-ACCESS	read-write
    DESCRIPTION
        "(U//FOUO) Implementation of this object can be as low
         as read-write depending on which
         IS Objective or MIB desired requirements are
         not being met by the implementation.
        "

    OBJECT		hRemoteEnclaveMethod
    MIN-ACCESS	read-write
    DESCRIPTION
        "(U//FOUO) Implementation of this object can be as low
         as read-write depending on which
         IS Objective or MIB desired requirements are
         not being met by the implementation.
        "

    OBJECT		hRemoteEnclaveTableCount
    MIN-ACCESS	read-only
    DESCRIPTION
        "(U//FOUO) Implementation of this object can be as low
         as read-only depending on which
         IS Objective or MIB desired requirements are
         not being met by the implementation.
        "

    OBJECT		hDiscSolRcvAddressType
    MIN-ACCESS	read-write
    DESCRIPTION
        "(U//FOUO) Implementation of this object can be as low
         as read-write depending on which
         IS Objective or MIB desired requirements are
         not being met by the implementation.
        "

    OBJECT		hRemoteEnclaveDestHostAddrType
    MIN-ACCESS	read-write
    DESCRIPTION
        "(U//FOUO) Implementation of this object can be as low
         as read-write depending on which
         IS Objective or MIB desired requirements are
         not being met by the implementation.
        "

    OBJECT		hDiscSolReceptionTableCount
    MIN-ACCESS	read-only
    DESCRIPTION
        "(U//FOUO) Implementation of this object can be as low
         as read-only depending on which
         IS Objective or MIB desired requirements are
         not being met by the implementation.
        "

    OBJECT		hDiscoveryRegistrationRetry
    MIN-ACCESS	read-write
    DESCRIPTION
        "(U//FOUO) Implementation of this object can be as low
         as read-write depending on which
         IS Objective or MIB desired requirements are
         not being met by the implementation.
        "

    OBJECT		hDiscRegPriority
    MIN-ACCESS	read-write
    DESCRIPTION
        "(U//FOUO) Implementation of this object can be as low
         as read-write depending on which
         IS Objective or MIB desired requirements are
         not being met by the implementation.
        "

    OBJECT		hDiscDelivPTAddress
    MIN-ACCESS	read-write
    DESCRIPTION
        "(U//FOUO) Implementation of this object can be as low
         as read-write depending on which
         IS Objective or MIB desired requirements are
         not being met by the implementation.
        "

    OBJECT		hDiscDelivStatus
    MIN-ACCESS	read-write
    DESCRIPTION
        "(U//FOUO) Implementation of this object can be as low
         as read-write depending on which
         IS Objective or MIB desired requirements are
         not being met by the implementation.
        "

    OBJECT		hDiscoveryProbeRetry
    MIN-ACCESS	read-write
    DESCRIPTION
        "(U//FOUO) Implementation of this object can be as low
         as read-write depending on which
         IS Objective or MIB desired requirements are
         not being met by the implementation.
        "

    OBJECT		hDiscSearchEndAddress
    MIN-ACCESS	read-write
    DESCRIPTION
        "(U//FOUO) Implementation of this object can be as low
         as read-write depending on which
         IS Objective or MIB desired requirements are
         not being met by the implementation.
        "

    OBJECT		hDiscDelivType
    MIN-ACCESS	read-write
    DESCRIPTION
        "(U//FOUO) Implementation of this object can be as low
         as read-write depending on which
         IS Objective or MIB desired requirements are
         not being met by the implementation.
        "

    OBJECT		hRemoteEnclaveDestHaipePTAddr
    MIN-ACCESS	read-write
    DESCRIPTION
        "(U//FOUO) Implementation of this object can be as low
         as read-write depending on which
         IS Objective or MIB desired requirements are
         not being met by the implementation.
        "

    OBJECT		hDiscRegStatus
    MIN-ACCESS	read-write
    DESCRIPTION
        "(U//FOUO) Implementation of this object can be as low
         as read-write depending on which
         IS Objective or MIB desired requirements are
         not being met by the implementation.
        "

    OBJECT		hDiscoveryProbeTimeout
    MIN-ACCESS	read-write
    DESCRIPTION
        "(U//FOUO) Implementation of this object can be as low
         as read-write depending on which
         IS Objective or MIB desired requirements are
         not being met by the implementation.
        "

    OBJECT		hDiscoveryAdvertiseAdminCost
    MIN-ACCESS	read-write
    DESCRIPTION
        "(U//FOUO) Implementation of this object can be as low
         as read-write depending on which
         IS Objective or MIB desired requirements are
         not being met by the implementation.
        "

--    OBJECT		hDiscoveryMessageConfig
--    MIN-ACCESS	read-write
--    DESCRIPTION
--        "(U//FOUO) Implementation of this object can be as low
--         as read-write depending on which
--         IS Objective or MIB desired requirements are
--         not being met by the implementation.
--        "

    OBJECT		hDiscoveryRegistrationTimeout
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-write
    DESCRIPTION
        "(U//FOUO) Implementation of this object can be as low
         as read-write depending on which
         IS Objective or MIB desired requirements are
         not being met by the implementation.
        "

    OBJECT		hDiscRegPTAddressType
    MIN-ACCESS	read-write
    DESCRIPTION
        "(U//FOUO) Implementation of this object can be as low
         as read-write depending on which
         IS Objective or MIB desired requirements are
         not being met by the implementation.
        "

    OBJECT		hDiscDelivPriority
    MIN-ACCESS	read-write
    DESCRIPTION
        "(U//FOUO) Implementation of this object can be as low
         as read-write depending on which
         IS Objective or MIB desired requirements are
         not being met by the implementation.
        "

    OBJECT		hRemoteEnclaveRowStatus
    MIN-ACCESS	read-write
    DESCRIPTION
        "(U//FOUO) Implementation of this object can be as low
         as read-write depending on which
         IS Objective or MIB desired requirements are
         not being met by the implementation.
        "

    OBJECT		hDiscDelivPTPort
    MIN-ACCESS	read-write
    DESCRIPTION
        "(U//FOUO) Implementation of this object can be as low
         as read-write depending on which
         IS Objective or MIB desired requirements are
         not being met by the implementation.
        "

    OBJECT		hDiscSolRcvType
    MIN-ACCESS	read-write
    DESCRIPTION
        "(U//FOUO) Implementation of this object can be as low
         as read-write depending on which
         IS Objective or MIB desired requirements are
         not being met by the implementation.
        "

    OBJECT		hRemoteEnclaveDestHaipePTAddrType
    MIN-ACCESS	read-write
    DESCRIPTION
        "(U//FOUO) Implementation of this object can be as low
         as read-write depending on which
         IS Objective or MIB desired requirements are
         not being met by the implementation.
        "

    OBJECT		hDiscRegPTPort
    MIN-ACCESS	read-write
    DESCRIPTION
        "(U//FOUO) Implementation of this object can be as low
         as read-write depending on which
         IS Objective or MIB desired requirements are
         not being met by the implementation.
        "

    OBJECT		hDiscRegistrationDefaultLifetime
    MIN-ACCESS	read-only
    DESCRIPTION
        "(U//FOUO) Implementation of this object can be as low
         as read-only depending on which
         IS Objective or MIB desired requirements are
         not being met by the implementation.
        "

    OBJECT		hDiscSolRcvStatus
    MIN-ACCESS	read-write
    DESCRIPTION
        "(U//FOUO) Implementation of this object can be as low
         as read-write depending on which
         IS Objective or MIB desired requirements are
         not being met by the implementation.
        "

    OBJECT		hDiscSearchAddressType
    MIN-ACCESS	read-write
    DESCRIPTION
        "(U//FOUO) Implementation of this object can be as low
         as read-write depending on which
         IS Objective or MIB desired requirements are
         not being met by the implementation.
        "

    OBJECT		hRemoteEnclaveDestHost
    MIN-ACCESS	read-write
    DESCRIPTION
        "(U//FOUO) Implementation of this object can be as low
         as read-write depending on which
         IS Objective or MIB desired requirements are
         not being met by the implementation.
        "

    OBJECT		hDiscSolRcvAddress
    MIN-ACCESS	read-write
    DESCRIPTION
        "(U//FOUO) Implementation of this object can be as low
         as read-write depending on which
         IS Objective or MIB desired requirements are
         not being met by the implementation.
        "

    OBJECT		hIPhFFSAPDUNEnabled
    MIN-ACCESS	read-write
    DESCRIPTION
        "(U//FOUO) Implementation of this object can be as low
         as read-write depending on which
         IS Objective or MIB desired requirements are
         not being met by the implementation.
        "

    OBJECT		hDiscoveryEnabled
    MIN-ACCESS	read-write
    DESCRIPTION
        "(U//FOUO) Implementation of this object can be as low
         as read-write depending on which
         IS Objective or MIB desired requirements are
         not being met by the implementation.
        "

    OBJECT		hTPSAPDUNEnabled
    MIN-ACCESS	read-write
    DESCRIPTION
        "(U//FOUO) Implementation of this object can be as low
         as read-write depending on which
         IS Objective or MIB desired requirements are
         not being met by the implementation.
        "

    OBJECT		hDiscSolRcvPort
    MIN-ACCESS	read-write
    DESCRIPTION
        "(U//FOUO) Implementation of this object can be as low
         as read-write depending on which
         IS Objective or MIB desired requirements are
         not being met by the implementation.
        "

    OBJECT		hRemoteEnclaveDestHaipeCTAddr
    MIN-ACCESS	read-write
    DESCRIPTION
        "(U//FOUO) Implementation of this object can be as low
         as read-write depending on which
         IS Objective or MIB desired requirements are
         not being met by the implementation.
        "

    OBJECT		hDiscoveryDeliveryTableLastChanged
    MIN-ACCESS	read-only
    DESCRIPTION
        "(U//FOUO) Implementation of this object can be as low
         as read-only depending on which
         IS Objective or MIB desired requirements are
         not being met by the implementation.
        "

    OBJECT		hDiscDelivPTAddressType
    MIN-ACCESS	read-write
    DESCRIPTION
        "(U//FOUO) Implementation of this object can be as low
         as read-write depending on which
         IS Objective or MIB desired requirements are
         not being met by the implementation.
        "

    OBJECT		hDiscSolReceptionTableLastChanged
    MIN-ACCESS	read-only
    DESCRIPTION
        "(U//FOUO) Implementation of this object can be as low
         as read-only depending on which
         IS Objective or MIB desired requirements are
         not being met by the implementation.
        "

    OBJECT		hDiscoveryDeliveryTableCount
    MIN-ACCESS	read-only
    DESCRIPTION
        "(U//FOUO) Implementation of this object can be as low
         as read-only depending on which
         IS Objective or MIB desired requirements are
         not being met by the implementation.
        "

    OBJECT		hDiscoverySolicitationTimeout
    MIN-ACCESS	read-write
    DESCRIPTION
        "(U//FOUO) Implementation of this object can be as low
         as read-write depending on which
         IS Objective or MIB desired requirements are
         not being met by the implementation.
        "

    OBJECT		hDiscRegistrationTableCount
    MIN-ACCESS	read-only
    DESCRIPTION
        "(U//FOUO) Implementation of this object can be as low
         as read-only depending on which
         IS Objective or MIB desired requirements are
         not being met by the implementation.
        "

    OBJECT		hDiscRegPTAddress
    MIN-ACCESS	read-write
    DESCRIPTION
        "(U//FOUO) Implementation of this object can be as low
         as read-write depending on which
         IS Objective or MIB desired requirements are
         not being met by the implementation.
        "
::= { haipeV030102Conformance 4 }

--
-- Objects referenced by the Automated SA Document
--
hAutomatedSAGroup OBJECT-GROUP
    OBJECTS {
                hLocalEnclaveDestHostAddrType,
                hLocalEnclaveDestHost,
                hLocalEnclaveDestHostPTPfxLen,
                hLocalEnclaveDestAdminCost,
                hLocalEnclaveMethod,
                hLocalEnclaveLifetime,
                hLocalEnclaveRowStatus,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hIfv4NATTEnable,
                hIfv6NATTEnable,
                hiaaInterface,
                hiaaType,
                hiaaAddress,
                hiaaPrefixLen,
                hiaaRowStatus,
                hFireflyTableCount,
                hFireflyTableLastChanged,
                hFFKMID,
                hFFUniversalID,
                hFFUniversalEdition,
                hFFSecurityLevels,
                hFFMaterialType,
                hFFExpiration,
                hFFNextVector,
                hFFPartitionCode,
                hFFLastChanged,
                hFFZeroizeKey,
                hFFASCIIID,
                hFFIsTestKey,
                hFFEnhancedFFTag,
                hFFShortTitleName,
                hPreplacedKeyTableCount,
                hPreplacedKeyTableCapacity,
                hPreplacedKeyTableLastChanged,
                hPPKUsageType,
                hPPKEffectiveDate,
                hPPKSecurityLevel,
                hPPKZeroizeKey,
                hPPKRegister,
                hPPKLastChanged,
                hPPKEKTableMaxCount,
                hPPKEKKeyType,
                hPPKEKUniversalID,
                hPPKChainTableCount,
                hPPKChainTableLastChanged,
                hPPKChainID,
                hPPKChainOrder,
                hPPKChainPPK,
                hPPKChainEffectiveDate,
                hPPKChainEncryptionAlgorithm,
                hPPKChainRowStatus,
                hUniversalID,
                hUniversalCKLDate,
                hUniversalCKLVersion,
                hIPhRuleTableCount,
                hIPhRuleTableLastChanged,
                hIPhRuleName,
                hIPhRuleSelectorName,
                hIPhRuleAction,
                hIPhRuleActionIndex,
                hIPhRuleAdminStatus,
                hIPhRuleLastChanged,
                hIPhRuleRowStatus,
                hIPhFFSAECN,
                hIPhFFSAConnectionType,
                hIPhFFSATransformsTableCount,
                hIPhFFSATransformsTableLastChanged,
                hIPhFFSATransformEncryptAlgorithm,
                hIPhFFSATransformKeyUpdateMethod,
                hIPhFFSATransformKeyUpdateFrequency,
                hIPhFFSATransformCryptoBlockSize,
                hIPhFFSATransformLastChanged,
                hIPhFFSATransformRowStatus,
                hIPhFFSATransformIntegrityAlgorithm,
                hIPhFFSATransformHashAlgorithm,
                hIPhFFSATransformAuthenticationAlgorithm,
                hTPSAAddressType,
                hTPSALocalCTAddress,
                hTPSARemoteCTAddress,
                hTPSAPTAddressType,
                hTPSALocalPTAddress,
                hTPSARemotePTAddress,
                hTPSAConnectionType,
                hTPSASecurityPayloadType,
                hTPSAEncryptAlgorithm,
                hTPSAIntegrityAlgorithm,
                hTPSACryptoBlockSize,
                hTPSAECN,
                hTPSARowStatus,
                hTPSANATAddress,
                hTPSANATPort,
                hPPKChainID
            }
    STATUS    current
    DESCRIPTION
        "(U//FOUO) Objects for the 'Automated SA' document"
    ::= { haipeV030102Groups 5 }

--
-- Conformance levels required by the 'Automated SA' document
--
hAutomatedSACompliance MODULE-COMPLIANCE
    STATUS    current
    DESCRIPTION
        "(U//FOUO) Compliance levels for objects required by the
          'Automated SA' document"
    MODULE -- this module
    MANDATORY-GROUPS { hAutomatedSAGroup }

    OBJECT		hPPKEKTableMaxCount
    MIN-ACCESS	read-only
    DESCRIPTION
        "(U//FOUO) Implementation of this object can be as low
         as read-only depending on which
         IS Objective or MIB desired requirements are
         not being met by the implementation.
        "

    OBJECT		hIPhFFSATransformLastChanged
    MIN-ACCESS	read-only
    DESCRIPTION
        "(U//FOUO) Implementation of this object can be as low
         as read-only depending on which
         IS Objective or MIB desired requirements are
         not being met by the implementation.
        "

    OBJECT		hTPSANATPort
    MIN-ACCESS	read-only
    DESCRIPTION
        "(U//FOUO) Implementation of this object can be as low
         as read-only depending on which
         IS Objective or MIB desired requirements are
         not being met by the implementation.
        "

    OBJECT		hIfv6NATTEnable
    MIN-ACCESS	read-write
    DESCRIPTION
        "(U//FOUO) Implementation of this object can be as low
         as read-write depending on which
         IS Objective or MIB desired requirements are
         not being met by the implementation.
        "

    OBJECT		hRemoteEnclaveDestHaipeNATPort
    MIN-ACCESS	read-only
    DESCRIPTION
        "(U//FOUO) Implementation of this object can be as low
         as read-only depending on which
         IS Objective or MIB desired requirements are
         not being met by the implementation.
        "

    OBJECT		hUniversalCKLVersion
    MIN-ACCESS	read-only
    DESCRIPTION
        "(U//FOUO) Implementation of this object can be as low
         as read-only depending on which
         IS Objective or MIB desired requirements are
         not being met by the implementation.
        "

    OBJECT		hRemoteEnclaveDestHaipeCTAddrType
    MIN-ACCESS	read-only
    DESCRIPTION
        "(U//FOUO) Implementation of this object can be as low
         as read-only depending on which
         IS Objective or MIB desired requirements are
         not being met by the implementation.
        "

    OBJECT		hRemoteEnclaveDestHostPTPfxLen
    MIN-ACCESS	read-only
    DESCRIPTION
        "(U//FOUO) Implementation of this object can be as low
         as read-only depending on which
         IS Objective or MIB desired requirements are
         not being met by the implementation.
        "

    OBJECT		hRemoteEnclaveLifetime
    MIN-ACCESS	read-only
    DESCRIPTION
        "(U//FOUO) Implementation of this object can be as low
         as read-only depending on which
         IS Objective or MIB desired requirements are
         not being met by the implementation.
        "

    OBJECT		hTPSAIntegrityAlgorithm
    MIN-ACCESS	read-only
    DESCRIPTION
        "(U//FOUO) Implementation of this object can be as low
         as read-only depending on which
         IS Objective or MIB desired requirements are
         not being met by the implementation.
        "

    OBJECT		hLocalEnclaveDestHostPTPfxLen
    MIN-ACCESS	read-only
    DESCRIPTION
        "(U//FOUO) Implementation of this object can be as low
         as read-only depending on which
         IS Objective or MIB desired requirements are
         not being met by the implementation.
        "

    OBJECT		hRemoteEnclaveMethod
    MIN-ACCESS	read-only
    DESCRIPTION
        "(U//FOUO) Implementation of this object can be as low
         as read-only depending on which
         IS Objective or MIB desired requirements are
         not being met by the implementation.
        "

    OBJECT		hPPKEffectiveDate
    MIN-ACCESS	read-only
    DESCRIPTION
        "(U//FOUO) Implementation of this object can be as low
         as read-only depending on which
         IS Objective or MIB desired requirements are
         not being met by the implementation.
        "

    OBJECT		hIPhRuleTableLastChanged
    MIN-ACCESS	read-only
    DESCRIPTION
        "(U//FOUO) Implementation of this object can be as low
         as read-only depending on which
         IS Objective or MIB desired requirements are
         not being met by the implementation.
        "

    OBJECT		hFFExpiration
    MIN-ACCESS	read-only
    DESCRIPTION
        "(U//FOUO) Implementation of this object can be as low
         as read-only depending on which
         IS Objective or MIB desired requirements are
         not being met by the implementation.
        "

    OBJECT		hFFUniversalEdition
    MIN-ACCESS	read-only
    DESCRIPTION
        "(U//FOUO) Implementation of this object can be as low
         as read-only depending on which
         IS Objective or MIB desired requirements are
         not being met by the implementation.
        "

    OBJECT		hIPhFFSATransformKeyUpdateMethod
    MIN-ACCESS	read-write
    DESCRIPTION
        "(U//FOUO) Implementation of this object can be as low
         as read-write depending on which
         IS Objective or MIB desired requirements are
         not being met by the implementation.
        "

    OBJECT		hPPKChainRowStatus
    MIN-ACCESS	read-write
    DESCRIPTION
        "(U//FOUO) Implementation of this object can be as low
         as read-write depending on which
         IS Objective or MIB desired requirements are
         not being met by the implementation.
        "

    OBJECT		hPPKChainEffectiveDate
    MIN-ACCESS	read-write
    DESCRIPTION
        "(U//FOUO) Implementation of this object can be as low
         as read-write depending on which
         IS Objective or MIB desired requirements are
         not being met by the implementation.
        "

    OBJECT		hTPSALocalPTAddress
    MIN-ACCESS	read-only
    DESCRIPTION
        "(U//FOUO) Implementation of this object can be as low
         as read-only depending on which
         IS Objective or MIB desired requirements are
         not being met by the implementation.
        "

    OBJECT		hTPSAPTAddressType
    MIN-ACCESS	read-only
    DESCRIPTION
        "(U//FOUO) Implementation of this object can be as low
         as read-only depending on which
         IS Objective or MIB desired requirements are
         not being met by the implementation.
        "

    OBJECT		hIPhRuleAdminStatus
    MIN-ACCESS	read-write
    DESCRIPTION
        "(U//FOUO) Implementation of this object can be as low
         as read-write depending on which
         IS Objective or MIB desired requirements are
         not being met by the implementation.
        "

    OBJECT		hTPSAECN
    MIN-ACCESS	read-write
    DESCRIPTION
        "(U//FOUO) Implementation of this object can be as low
         as read-write depending on which
         IS Objective or MIB desired requirements are
         not being met by the implementation.
        "

    OBJECT		hIPhFFSATransformAuthenticationAlgorithm
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-only
    DESCRIPTION
        "(U//FOUO) Implementation of this object can be as low
         as read-only depending on which
         IS Objective or MIB desired requirements are
         not being met by the implementation.
        "

    OBJECT		hIPhFFSATransformsTableCount
    MIN-ACCESS	read-only
    DESCRIPTION
        "(U//FOUO) Implementation of this object can be as low
         as read-only depending on which
         IS Objective or MIB desired requirements are
         not being met by the implementation.
        "

    OBJECT		hTPSAConnectionType
    MIN-ACCESS	read-only
    DESCRIPTION
        "(U//FOUO) Implementation of this object can be as low
         as read-only depending on which
         IS Objective or MIB desired requirements are
         not being met by the implementation.
        "

    OBJECT		hIPhFFSATransformHashAlgorithm
    MIN-ACCESS	read-write
    DESCRIPTION
        "(U//FOUO) Implementation of this object can be as low
         as read-write depending on which
         IS Objective or MIB desired requirements are
         not being met by the implementation.
        "

    OBJECT		hTPSANATAddress
    MIN-ACCESS	read-only
    DESCRIPTION
        "(U//FOUO) Implementation of this object can be as low
         as read-only depending on which
         IS Objective or MIB desired requirements are
         not being met by the implementation.
        "

    OBJECT		hPPKChainPPK
    MIN-ACCESS	read-write
    DESCRIPTION
        "(U//FOUO) Implementation of this object can be as low
         as read-write depending on which
         IS Objective or MIB desired requirements are
         not being met by the implementation.
        "

    OBJECT		hPreplacedKeyTableCapacity
    MIN-ACCESS	read-only
    DESCRIPTION
        "(U//FOUO) Implementation of this object can be as low
         as read-only depending on which
         IS Objective or MIB desired requirements are
         not being met by the implementation.
        "

    OBJECT		hRemoteEnclaveDestHaipePTAddrType
    MIN-ACCESS	read-only
    DESCRIPTION
        "(U//FOUO) Implementation of this object can be as low
         as read-only depending on which
         IS Objective or MIB desired requirements are
         not being met by the implementation.
        "

    OBJECT		hFFUniversalID
    MIN-ACCESS	read-only
    DESCRIPTION
        "(U//FOUO) Implementation of this object can be as low
         as read-only depending on which
         IS Objective or MIB desired requirements are
         not being met by the implementation.
        "

    OBJECT		hIPhFFSATransformRowStatus
    MIN-ACCESS	read-write
    DESCRIPTION
        "(U//FOUO) Implementation of this object can be as low
         as read-write depending on which
         IS Objective or MIB desired requirements are
         not being met by the implementation.
        "

    OBJECT		hTPSARemoteCTAddress
    MIN-ACCESS	read-only
    DESCRIPTION
        "(U//FOUO) Implementation of this object can be as low
         as read-only depending on which
         IS Objective or MIB desired requirements are
         not being met by the implementation.
        "

    OBJECT		hFFSecurityLevels
    MIN-ACCESS	read-only
    DESCRIPTION
        "(U//FOUO) Implementation of this object can be as low
         as read-only depending on which
         IS Objective or MIB desired requirements are
         not being met by the implementation.
        "

    OBJECT		hPPKRegister
    MIN-ACCESS	not-accessible
    DESCRIPTION
        "(U//FOUO) Implementation of this object can be as low
         as not-accessible depending on which
         IS Objective or MIB desired requirements are
         not being met by the implementation.
        "

    OBJECT		hFFMaterialType
    MIN-ACCESS	read-only
    DESCRIPTION
        "(U//FOUO) Implementation of this object can be as low
         as read-only depending on which
         IS Objective or MIB desired requirements are
         not being met by the implementation.
        "

    OBJECT		hTPSAEncryptAlgorithm
    MIN-ACCESS	read-only
    DESCRIPTION
        "(U//FOUO) Implementation of this object can be as low
         as read-only depending on which
         IS Objective or MIB desired requirements are
         not being met by the implementation.
        "

    OBJECT		hFFKMID
    MIN-ACCESS	read-only
    DESCRIPTION
        "(U//FOUO) Implementation of this object can be as low
         as read-only depending on which
         IS Objective or MIB desired requirements are
         not being met by the implementation.
        "

    OBJECT		hTPSARemotePTAddress
    MIN-ACCESS	read-only
    DESCRIPTION
        "(U//FOUO) Implementation of this object can be as low
         as read-only depending on which
         IS Objective or MIB desired requirements are
         not being met by the implementation.
        "

    OBJECT		hiaaAddress
    MIN-ACCESS	not-accessible
    DESCRIPTION
        "(U//FOUO) Implementation of this object can be as low
         as not-accessible depending on which
         IS Objective or MIB desired requirements are
         not being met by the implementation.
        "

    OBJECT		hTPSALocalCTAddress
    MIN-ACCESS	read-only
    DESCRIPTION
        "(U//FOUO) Implementation of this object can be as low
         as read-only depending on which
         IS Objective or MIB desired requirements are
         not being met by the implementation.
        "

    OBJECT		hIPhFFSATransformIntegrityAlgorithm
    MIN-ACCESS	read-write
    DESCRIPTION
        "(U//FOUO) Implementation of this object can be as low
         as read-write depending on which
         IS Objective or MIB desired requirements are
         not being met by the implementation.
        "

    OBJECT		hIPhFFSATransformKeyUpdateFrequency
    MIN-ACCESS	read-write
    DESCRIPTION
        "(U//FOUO) Implementation of this object can be as low
         as read-write depending on which
         IS Objective or MIB desired requirements are
         not being met by the implementation.
        "

    OBJECT		hLocalEnclaveRowStatus
    MIN-ACCESS	read-only
    DESCRIPTION
        "(U//FOUO) Implementation of this object can be as low
         as read-only depending on which
         IS Objective or MIB desired requirements are
         not being met by the implementation.
        "

    OBJECT		hFFZeroizeKey
    MIN-ACCESS	read-only
    DESCRIPTION
        "(U//FOUO) Implementation of this object can be as low
         as read-only depending on which
         IS Objective or MIB desired requirements are
         not being met by the implementation.
        "

    OBJECT		hFFEnhancedFFTag
    MIN-ACCESS	read-only
    DESCRIPTION
        "(U//FOUO) Implementation of this object can be as low
         as read-only depending on which
         IS Objective or MIB desired requirements are
         not being met by the implementation.
        "

    OBJECT		hFFNextVector
    MIN-ACCESS	read-only
    DESCRIPTION
        "(U//FOUO) Implementation of this object can be as low
         as read-only depending on which
         IS Objective or MIB desired requirements are
         not being met by the implementation.
        "

    OBJECT		hRemoteEnclaveDestHaipeCTAddr
    MIN-ACCESS	read-only
    DESCRIPTION
        "(U//FOUO) Implementation of this object can be as low
         as read-only depending on which
         IS Objective or MIB desired requirements are
         not being met by the implementation.
        "

    OBJECT		hPPKEKKeyType
    MIN-ACCESS	read-write
    DESCRIPTION
        "(U//FOUO) Implementation of this object can be as low
         as read-write depending on which
         IS Objective or MIB desired requirements are
         not being met by the implementation.
        "

    OBJECT		hPreplacedKeyTableLastChanged
    MIN-ACCESS	read-only
    DESCRIPTION
        "(U//FOUO) Implementation of this object can be as low
         as read-only depending on which
         IS Objective or MIB desired requirements are
         not being met by the implementation.
        "

    OBJECT		hIPhRuleLastChanged
    MIN-ACCESS	read-only
    DESCRIPTION
        "(U//FOUO) Implementation of this object can be as low
         as read-only depending on which
         IS Objective or MIB desired requirements are
         not being met by the implementation.
        "

    OBJECT		hIPhFFSATransformCryptoBlockSize
    MIN-ACCESS	read-write
    DESCRIPTION
        "(U//FOUO) Implementation of this object can be as low
         as read-write depending on which
         IS Objective or MIB desired requirements are
         not being met by the implementation.
        "

    OBJECT		hPPKSecurityLevel
    MIN-ACCESS	read-only
    DESCRIPTION
        "(U//FOUO) Implementation of this object can be as low
         as read-only depending on which
         IS Objective or MIB desired requirements are
         not being met by the implementation.
        "

    OBJECT		hIfv4NATTEnable
    MIN-ACCESS	read-write
    DESCRIPTION
        "(U//FOUO) Implementation of this object can be as low
         as read-write depending on which
         IS Objective or MIB desired requirements are
         not being met by the implementation.
        "

    OBJECT		hPreplacedKeyTableCount
    MIN-ACCESS	read-only
    DESCRIPTION
        "(U//FOUO) Implementation of this object can be as low
         as read-only depending on which
         IS Objective or MIB desired requirements are
         not being met by the implementation.
        "

    OBJECT		hTPSACryptoBlockSize
    MIN-ACCESS	read-only
    DESCRIPTION
        "(U//FOUO) Implementation of this object can be as low
         as read-only depending on which
         IS Objective or MIB desired requirements are
         not being met by the implementation.
        "

    OBJECT		hLocalEnclaveDestAdminCost
    MIN-ACCESS	read-only
    DESCRIPTION
        "(U//FOUO) Implementation of this object can be as low
         as read-only depending on which
         IS Objective or MIB desired requirements are
         not being met by the implementation.
        "

    OBJECT		hPPKEKUniversalID
    MIN-ACCESS	read-write
    DESCRIPTION
        "(U//FOUO) Implementation of this object can be as low
         as read-write depending on which
         IS Objective or MIB desired requirements are
         not being met by the implementation.
        "

    OBJECT		hFireflyTableLastChanged
    MIN-ACCESS	read-only
    DESCRIPTION
        "(U//FOUO) Implementation of this object can be as low
         as read-only depending on which
         IS Objective or MIB desired requirements are
         not being met by the implementation.
        "

    OBJECT		hIPhRuleAction
    MIN-ACCESS	read-write
    DESCRIPTION
        "(U//FOUO) Implementation of this object can be as low
         as read-write depending on which
         IS Objective or MIB desired requirements are
         not being met by the implementation.
        "

    OBJECT		hIPhRuleRowStatus
    MIN-ACCESS	read-write
    DESCRIPTION
        "(U//FOUO) Implementation of this object can be as low
         as read-write depending on which
         IS Objective or MIB desired requirements are
         not being met by the implementation.
        "

    OBJECT		hiaaType
    MIN-ACCESS	not-accessible
    DESCRIPTION
        "(U//FOUO) Implementation of this object can be as low
         as not-accessible depending on which
         IS Objective or MIB desired requirements are
         not being met by the implementation.
        "

    OBJECT		hFFLastChanged
    MIN-ACCESS	read-only
    DESCRIPTION
        "(U//FOUO) Implementation of this object can be as low
         as read-only depending on which
         IS Objective or MIB desired requirements are
         not being met by the implementation.
        "

    OBJECT		hRemoteEnclaveDestHaipeNATAddr
    MIN-ACCESS	read-only
    DESCRIPTION
        "(U//FOUO) Implementation of this object can be as low
         as read-only depending on which
         IS Objective or MIB desired requirements are
         not being met by the implementation.
        "

    OBJECT		hPPKZeroizeKey
    MIN-ACCESS	read-only
    DESCRIPTION
        "(U//FOUO) Implementation of this object can be as low
         as read-only depending on which
         IS Objective or MIB desired requirements are
         not being met by the implementation.
        "

    OBJECT		hPPKChainID
    MIN-ACCESS	read-write
    DESCRIPTION
        "(U//FOUO) Implementation of this object can be as low
         as read-write depending on which
         IS Objective or MIB desired requirements are
         not being met by the implementation.
        "

    OBJECT		hPPKChainOrder
    MIN-ACCESS	read-write
    DESCRIPTION
        "(U//FOUO) Implementation of this object can be as low
         as read-write depending on which
         IS Objective or MIB desired requirements are
         not being met by the implementation.
        "

    OBJECT		hFFPartitionCode
    MIN-ACCESS	read-only
    DESCRIPTION
        "(U//FOUO) Implementation of this object can be as low
         as read-only depending on which
         IS Objective or MIB desired requirements are
         not being met by the implementation.
        "

    OBJECT		hFFIsTestKey
    MIN-ACCESS	not-accessible
    DESCRIPTION
        "(U//FOUO) Implementation of this object can be as low
         as not-accessible depending on which
         IS Objective or MIB desired requirements are
         not being met by the implementation.
        "

    OBJECT		hFFShortTitleName
    MIN-ACCESS	read-only
    DESCRIPTION
        "(U//FOUO) Implementation of this object can be as low
         as read-only depending on which
         IS Objective or MIB desired requirements are
         not being met by the implementation.
        "

    OBJECT		hRemoteEnclaveDestHostAddrType
    MIN-ACCESS	read-only
    DESCRIPTION
        "(U//FOUO) Implementation of this object can be as low
         as read-only depending on which
         IS Objective or MIB desired requirements are
         not being met by the implementation.
        "

    OBJECT		hLocalEnclaveLifetime
    MIN-ACCESS	read-only
    DESCRIPTION
        "(U//FOUO) Implementation of this object can be as low
         as read-only depending on which
         IS Objective or MIB desired requirements are
         not being met by the implementation.
        "

    OBJECT		hIPhFFSATransformsTableLastChanged
    MIN-ACCESS	read-only
    DESCRIPTION
        "(U//FOUO) Implementation of this object can be as low
         as read-only depending on which
         IS Objective or MIB desired requirements are
         not being met by the implementation.
        "

    OBJECT		hUniversalCKLDate
    MIN-ACCESS	read-only
    DESCRIPTION
        "(U//FOUO) Implementation of this object can be as low
         as read-only depending on which
         IS Objective or MIB desired requirements are
         not being met by the implementation.
        "

    OBJECT		hLocalEnclaveMethod
    MIN-ACCESS	read-only
    DESCRIPTION
        "(U//FOUO) Implementation of this object can be as low
         as read-only depending on which
         IS Objective or MIB desired requirements are
         not being met by the implementation.
        "

    OBJECT		hIPhFFSATransformEncryptAlgorithm
    MIN-ACCESS	read-write
    DESCRIPTION
        "(U//FOUO) Implementation of this object can be as low
         as read-write depending on which
         IS Objective or MIB desired requirements are
         not being met by the implementation.
        "

    OBJECT		hIPhRuleActionIndex
    MIN-ACCESS	read-write
    DESCRIPTION
        "(U//FOUO) Implementation of this object can be as low
         as read-write depending on which
         IS Objective or MIB desired requirements are
         not being met by the implementation.
        "

    OBJECT		hRemoteEnclaveDestHaipePTAddr
    MIN-ACCESS	read-only
    DESCRIPTION
        "(U//FOUO) Implementation of this object can be as low
         as read-only depending on which
         IS Objective or MIB desired requirements are
         not being met by the implementation.
        "

    OBJECT		hPPKLastChanged
    MIN-ACCESS	read-only
    DESCRIPTION
        "(U//FOUO) Implementation of this object can be as low
         as read-only depending on which
         IS Objective or MIB desired requirements are
         not being met by the implementation.
        "

    OBJECT		hIPhFFSAConnectionType
    MIN-ACCESS	read-write
    DESCRIPTION
        "(U//FOUO) Implementation of this object can be as low
         as read-write depending on which
         IS Objective or MIB desired requirements are
         not being met by the implementation.
        "

    OBJECT		hIPhRuleSelectorName
    MIN-ACCESS	read-write
    DESCRIPTION
        "(U//FOUO) Implementation of this object can be as low
         as read-write depending on which
         IS Objective or MIB desired requirements are
         not being met by the implementation.
        "

    OBJECT		hFFASCIIID
    MIN-ACCESS	not-accessible
    DESCRIPTION
        "(U//FOUO) Implementation of this object can be as low
         as not-accessible depending on which
         IS Objective or MIB desired requirements are
         not being met by the implementation.
        "

    OBJECT		hiaaPrefixLen
    MIN-ACCESS	not-accessible
    DESCRIPTION
        "(U//FOUO) Implementation of this object can be as low
         as not-accessible depending on which
         IS Objective or MIB desired requirements are
         not being met by the implementation.
        "

    OBJECT		hRemoteEnclaveRowStatus
    MIN-ACCESS	read-only
    DESCRIPTION
        "(U//FOUO) Implementation of this object can be as low
         as read-only depending on which
         IS Objective or MIB desired requirements are
         not being met by the implementation.
        "

    OBJECT		hTPSARowStatus
    MIN-ACCESS	not-accessible
    DESCRIPTION
        "(U//FOUO) Implementation of this object can be as low
         as not-accessible depending on which
         IS Objective or MIB desired requirements are
         not being met by the implementation.
        "

    OBJECT		hTPSASecurityPayloadType
    MIN-ACCESS	read-only
    DESCRIPTION
        "(U//FOUO) Implementation of this object can be as low
         as read-only depending on which
         IS Objective or MIB desired requirements are
         not being met by the implementation.
        "

    OBJECT		hIPhRuleName
    MIN-ACCESS	read-write
    DESCRIPTION
        "(U//FOUO) Implementation of this object can be as low
         as read-write depending on which
         IS Objective or MIB desired requirements are
         not being met by the implementation.
        "

    OBJECT		hIPhRuleTableCount
    MIN-ACCESS	read-only
    DESCRIPTION
        "(U//FOUO) Implementation of this object can be as low
         as read-only depending on which
         IS Objective or MIB desired requirements are
         not being met by the implementation.
        "

    OBJECT		hFireflyTableCount
    MIN-ACCESS	read-only
    DESCRIPTION
        "(U//FOUO) Implementation of this object can be as low
         as read-only depending on which
         IS Objective or MIB desired requirements are
         not being met by the implementation.
        "

    OBJECT		hRemoteEnclaveDestHost
    MIN-ACCESS	read-only
    DESCRIPTION
        "(U//FOUO) Implementation of this object can be as low
         as read-only depending on which
         IS Objective or MIB desired requirements are
         not being met by the implementation.
        "

    OBJECT		hTPSAAddressType
    MIN-ACCESS	read-only
    DESCRIPTION
        "(U//FOUO) Implementation of this object can be as low
         as read-only depending on which
         IS Objective or MIB desired requirements are
         not being met by the implementation.
        "

    OBJECT		hIPhFFSAECN
    MIN-ACCESS	read-write
    DESCRIPTION
        "(U//FOUO) Implementation of this object can be as low
         as read-write depending on which
         IS Objective or MIB desired requirements are
         not being met by the implementation.
        "

    OBJECT		hUniversalID
    MIN-ACCESS	read-only
    DESCRIPTION
        "(U//FOUO) Implementation of this object can be as low
         as read-only depending on which
         IS Objective or MIB desired requirements are
         not being met by the implementation.
        "

    OBJECT		hLocalEnclaveDestHost
    MIN-ACCESS	read-only
    DESCRIPTION
        "(U//FOUO) Implementation of this object can be as low
         as read-only depending on which
         IS Objective or MIB desired requirements are
         not being met by the implementation.
        "

    OBJECT		hiaaInterface
    MIN-ACCESS	not-accessible
    DESCRIPTION
        "(U//FOUO) Implementation of this object can be as low
         as not-accessible depending on which
         IS Objective or MIB desired requirements are
         not being met by the implementation.
        "

    OBJECT		hLocalEnclaveDestHostAddrType
    MIN-ACCESS	read-only
    DESCRIPTION
        "(U//FOUO) Implementation of this object can be as low
         as read-only depending on which
         IS Objective or MIB desired requirements are
         not being met by the implementation.
        "

    OBJECT		hPPKChainTableLastChanged
    MIN-ACCESS	read-only
    DESCRIPTION
        "(U//FOUO) Implementation of this object can be as low
         as read-only depending on which
         IS Objective or MIB desired requirements are
         not being met by the implementation.
        "

    OBJECT		hiaaRowStatus
    MIN-ACCESS	not-accessible
    DESCRIPTION
        "(U//FOUO) Implementation of this object can be as low
         as not-accessible depending on which
         IS Objective or MIB desired requirements are
         not being met by the implementation.
        "

    OBJECT		hPPKUsageType
    MIN-ACCESS	read-only
    DESCRIPTION
        "(U//FOUO) Implementation of this object can be as low
         as read-only depending on which
         IS Objective or MIB desired requirements are
         not being met by the implementation.
        "

    OBJECT		hPPKChainTableCount
    MIN-ACCESS	read-only
    DESCRIPTION
        "(U//FOUO) Implementation of this object can be as low
         as read-only depending on which
         IS Objective or MIB desired requirements are
         not being met by the implementation.
        "

    OBJECT		hPPKChainEncryptionAlgorithm
    MIN-ACCESS	read-write
    DESCRIPTION
        "(U//FOUO) Implementation of this object can be as low
         as read-write depending on which
         IS Objective or MIB desired requirements are
         not being met by the implementation.
        "
::= { haipeV030102Conformance 5 }

--
-- Objects referenced by the Remote Configuration and Monitoring Document
--
hRemoteConfigurationandMonitoringGroup OBJECT-GROUP
    OBJECTS {
                hStationID,
                hSecurityLevels,
                hDeviceVersionTableCount,
                hDeviceVersionTableLastChanged,
                hdvName,
                hdvVersion,
                hSpinLock,
                hHMISpinLock,
                hLastChanged,
--                hBatteryLow,
--                hBatteryOK,
                hBatteryLevelWarningPercentage,
                hBatteryNumber,
                hBatteryLevelPercentage,
                hBatteryOperStatus,
                hBatteryChangeDate,
                haipeResetDevice,
                haipeSanitizeDevice,
                hIfv4HaipeTableCount,
                hIfv4HaipeTableLastChanged,
                hIfv4Side,
                hIfv4LastChanged,
                hIfv6HaipeTableCount,
                hIfv6HaipeTableLastChanged,
                hIfv6Side,
                hIfv6LastChanged,
                haipeZeroizeAllKeys,
                hLocalCKListUniversal,
                hLocalCKListUniversalEdition,
                hLocalCKListKMIDBegin,
                hLocalCKListKMIDEnd,
                hLocalCKListDate,
                hLocalCKListReason,
                hLocalCKListRowStatus,
                hrSystemUptime,
                hrSystemDate,
                ifNumber,
                ifIndex,
                ifDescr,
                ifType,
                ifMtu,
                ifSpeed,
                ifPhysAddress,
                ifAdminStatus,
                ifOperStatus,
                ifLastChange,
                ifIndex,
                ifName,
                ifInMulticastPkts,
                ifInBroadcastPkts,
                ifOutMulticastPkts,
                ifOutBroadcastPkts,
                ifHCInOctets,
                ifHCInUcastPkts,
                ifHCInMulticastPkts,
                ifHCInBroadcastPkts,
                ifHCOutOctets,
                ifHCOutUcastPkts,
                ifHCOutMulticastPkts,
                ifHCOutBroadcastPkts,
                ifLinkUpDownTrapEnable,
                ifHighSpeed,
                ifPromiscuousMode,
                ifConnectorPresent,
                ifAlias,
                ifCounterDiscontinuityTime,
                ifIndex,
                ifIndex,
                ipForwarding,
                ipDefaultTTL,
                ipReasmTimeout,
                ipv6IpForwarding,
                ipv6IpDefaultHopLimit,
                ipv4InterfaceReasmMaxSize,
                ipv4InterfaceEnableStatus,
                ipv4InterfaceRetransmitTime,
                ipv6InterfaceReasmMaxSize,
                ipv6InterfaceIdentifier,
                ipv6InterfaceEnableStatus,
                ipv6InterfaceReachableTime,
                ipv6InterfaceRetransmitTime,
                ipv6InterfaceForwarding,
                ipAddressSpinLock,
                ipNetToPhysicalPhysAddress,
                ipNetToPhysicalLastUpdated,
                ipNetToPhysicalType,
                ipNetToPhysicalState,
                ipNetToPhysicalRowStatus,
                nlmConfigGlobalEntryLimit,
                nlmConfigGlobalAgeOut,
                nlmLogTime,
                nlmLogDateAndTime,
                nlmLogEngineID,
                nlmLogEngineTAddress,
                nlmLogEngineTDomain,
                nlmLogContextEngineID,
                nlmLogContextName,
                nlmLogNotificationID,
                nlmLogVariableID,
                nlmLogVariableValueType,
                nlmLogVariableCounter32Val,
                nlmLogVariableUnsigned32Val,
                nlmLogVariableTimeTicksVal,
                nlmLogVariableInteger32Val,
                nlmLogVariableOctetStringVal,
                nlmLogVariableIpAddressVal,
                nlmLogVariableOidVal,
                nlmLogVariableCounter64Val,
                nlmLogVariableOpaqueVal,
--                snmpFrameworkMIB,
--                snmpFrameworkAdmin,
--                snmpAuthProtocols,
--                usmNoAuthProtocol,
--                usmHMACMD5AuthProtocol,
--                usmHMACSHAAuthProtocol,
--                snmpPrivProtocols,
--                usmNoPrivProtocol,
--                usmDESPrivProtocol,
--                snmpFrameworkMIBObjects,
--                snmpEngine,
                snmpEngineID,
                snmpEngineBoots,
                snmpEngineTime,
                snmpEngineMaxMessageSize,
--                snmpFrameworkMIBConformance,
--                snmpFrameworkMIBCompliances,
--                snmpFrameworkMIBCompliance,
--                snmpFrameworkMIBGroups,
--                snmpEngineGroup,
                snmpUnknownSecurityModels,
                snmpInvalidMsgs,
                snmpUnknownPDUHandlers,
                snmpNotifyTag,
                snmpNotifyType,
                snmpNotifyStorageType,
                snmpNotifyRowStatus,
                snmpNotifyFilterProfileName,
                snmpNotifyFilterProfileStorType,
                snmpNotifyFilterProfileRowStatus,
                snmpNotifyFilterProfileName,
                snmpNotifyFilterMask,
                snmpNotifyFilterType,
                snmpNotifyFilterStorageType,
                snmpNotifyFilterRowStatus,
                snmpTargetSpinLock,
                snmpTargetAddrTDomain,
                snmpTargetAddrTAddress,
                snmpTargetAddrTimeout,
                snmpTargetAddrRetryCount,
                snmpTargetAddrTagList,
                snmpTargetAddrParams,
                snmpTargetAddrStorageType,
                snmpTargetAddrRowStatus,
                snmpTargetParamsMPModel,
                snmpTargetParamsSecurityModel,
                snmpTargetParamsSecurityName,
                snmpTargetParamsSecurityLevel,
                snmpTargetParamsStorageType,
                snmpTargetParamsRowStatus,
                snmpUnavailableContexts,
                snmpUnknownContexts,
                usmStatsUnsupportedSecLevels,
                usmStatsNotInTimeWindows,
                usmStatsUnknownUserNames,
                usmStatsUnknownEngineIDs,
                usmStatsWrongDigests,
                usmStatsDecryptionErrors,
                usmUserSpinLock,
                usmUserSecurityName,
                usmUserCloneFrom,
                usmUserAuthProtocol,
                usmUserAuthKeyChange,
                usmUserOwnAuthKeyChange,
                usmUserPrivProtocol,
                usmUserPrivKeyChange,
                usmUserOwnPrivKeyChange,
                usmUserPublic,
                usmUserStorageType,
                usmUserStatus,
--                snmpUsmAesMIB,
--                snmpVacmMIB,
--                vacmMIBObjects,
                vacmContextName,
                vacmGroupName,
                vacmSecurityToGroupStorageType,
                vacmSecurityToGroupStatus,
                vacmGroupName,
                vacmAccessContextMatch,
                vacmAccessReadViewName,
                vacmAccessWriteViewName,
                vacmAccessNotifyViewName,
                vacmAccessStorageType,
                vacmAccessStatus,
--                vacmMIBViews,
                vacmViewSpinLock,
                vacmViewTreeFamilyMask,
                vacmViewTreeFamilyType,
                vacmViewTreeFamilyStorageType,
                vacmViewTreeFamilyStatus,
--                vacmMIBConformance,
--                vacmMIBCompliances,
--                vacmMIBCompliance,
--                vacmMIBGroups,
--                vacmBasicGroup,
                sysDescr,
                sysObjectID,
                sysUpTime,
                sysContact,
                sysName,
                sysLocation,
                sysServices,
                sysORLastChange,
                sysORID,
                sysORDescr,
                sysORUpTime,
                snmpTrapOID,
                snmpTrapEnterprise,
--                coldStart,
--                warmStart,
--                authenticationFailure,
                snmpSetSerialNo
            }
    STATUS    current
    DESCRIPTION
        "(U//FOUO) Objects for the 'Remote Configuration and Monitoring' document"
    ::= { haipeV030102Groups 6 }

--
-- Conformance levels required by the 'Remote Configuration and Monitoring' document
--
hRemoteConfigurationandMonitoringCompliance MODULE-COMPLIANCE
    STATUS    current
    DESCRIPTION
        "(U//FOUO) Compliance levels for objects required by the
          'Remote Configuration and Monitoring' document"
    MODULE -- this module
    MANDATORY-GROUPS { hRemoteConfigurationandMonitoringGroup }

    OBJECT		vacmSecurityToGroupStorageType
    MIN-ACCESS	read-write
    DESCRIPTION
        "(U//FOUO) Implementation of this object can be as low
         as read-write depending on which
         IS Objective or MIB desired requirements are
         not being met by the implementation.
        "

--    OBJECT		snmpPrivProtocols
--    MIN-ACCESS	read-write
--    DESCRIPTION
--        "(U//FOUO) Implementation of this object can be as low
--         as read-write depending on which
--         IS Objective or MIB desired requirements are
--         not being met by the implementation.
--        "

    OBJECT		nlmLogVariableIpAddressVal
    MIN-ACCESS	read-only
    DESCRIPTION
        "(U//FOUO) Implementation of this object can be as low
         as read-only depending on which
         IS Objective or MIB desired requirements are
         not being met by the implementation.
        "

    OBJECT		snmpUnknownSecurityModels
    MIN-ACCESS	not-accessible
    DESCRIPTION
        "(U//FOUO) Implementation of this object can be as low
         as not-accessible depending on which
         IS Objective or MIB desired requirements are
         not being met by the implementation.
        "

    OBJECT		ipv6IpForwarding
    MIN-ACCESS	read-only
    DESCRIPTION
        "(U//FOUO) Implementation of this object can be as low
         as read-only depending on which
         IS Objective or MIB desired requirements are
         not being met by the implementation.
        "

    OBJECT		snmpTargetAddrParams
    MIN-ACCESS	read-write
    DESCRIPTION
        "(U//FOUO) Implementation of this object can be as low
         as read-write depending on which
         IS Objective or MIB desired requirements are
         not being met by the implementation.
        "

    OBJECT		ifHCOutOctets
    MIN-ACCESS	not-accessible
    DESCRIPTION
        "(U//FOUO) Implementation of this object can be as low
         as not-accessible depending on which
         IS Objective or MIB desired requirements are
         not being met by the implementation.
        "

    OBJECT		ipv6IpDefaultHopLimit
    MIN-ACCESS	read-write
    DESCRIPTION
        "(U//FOUO) Implementation of this object can be as low
         as read-write depending on which
         IS Objective or MIB desired requirements are
         not being met by the implementation.
        "

    OBJECT		nlmLogVariableCounter64Val
    MIN-ACCESS	read-only
    DESCRIPTION
        "(U//FOUO) Implementation of this object can be as low
         as read-only depending on which
         IS Objective or MIB desired requirements are
         not being met by the implementation.
        "

--    OBJECT		coldStart
--    MIN-ACCESS	accessible-for-notify
--    DESCRIPTION
--        "(U//FOUO) Implementation of this object can be as low
--         as accessible-for-notify depending on which
--         IS Objective or MIB desired requirements are
--         not being met by the implementation.
--        "

    OBJECT		snmpNotifyFilterStorageType
    MIN-ACCESS	read-write
    DESCRIPTION
        "(U//FOUO) Implementation of this object can be as low
         as read-write depending on which
         IS Objective or MIB desired requirements are
         not being met by the implementation.
        "

    OBJECT		sysObjectID
    MIN-ACCESS	read-only
    DESCRIPTION
        "(U//FOUO) Implementation of this object can be as low
         as read-only depending on which
         IS Objective or MIB desired requirements are
         not being met by the implementation.
        "

    OBJECT		snmpEngineMaxMessageSize
    MIN-ACCESS	read-only
    DESCRIPTION
        "(U//FOUO) Implementation of this object can be as low
         as read-only depending on which
         IS Objective or MIB desired requirements are
         not being met by the implementation.
        "

    OBJECT		nlmLogDateAndTime
    MIN-ACCESS	read-only
    DESCRIPTION
        "(U//FOUO) Implementation of this object can be as low
         as read-only depending on which
         IS Objective or MIB desired requirements are
         not being met by the implementation.
        "

    OBJECT		ifAlias
    MIN-ACCESS	read-only
    DESCRIPTION
        "(U//FOUO) Implementation of this object can be as low
         as read-only depending on which
         IS Objective or MIB desired requirements are
         not being met by the implementation.
        "

    OBJECT		vacmViewTreeFamilyStatus
    MIN-ACCESS	read-write
    DESCRIPTION
        "(U//FOUO) Implementation of this object can be as low
         as read-write depending on which
         IS Objective or MIB desired requirements are
         not being met by the implementation.
        "

    OBJECT		ipv4InterfaceEnableStatus
    MIN-ACCESS	read-only
    DESCRIPTION
        "(U//FOUO) Implementation of this object can be as low
         as read-only depending on which
         IS Objective or MIB desired requirements are
         not being met by the implementation.
        "

    OBJECT		nlmLogNotificationID
    MIN-ACCESS	read-only
    DESCRIPTION
        "(U//FOUO) Implementation of this object can be as low
         as read-only depending on which
         IS Objective or MIB desired requirements are
         not being met by the implementation.
        "

    OBJECT		ifMtu
    MIN-ACCESS	read-only
    DESCRIPTION
        "(U//FOUO) Implementation of this object can be as low
         as read-only depending on which
         IS Objective or MIB desired requirements are
         not being met by the implementation.
        "

--    OBJECT		vacmMIBGroups
--    MIN-ACCESS	read-write
--    DESCRIPTION
--        "(U//FOUO) Implementation of this object can be as low
--         as read-write depending on which
--         IS Objective or MIB desired requirements are
--         not being met by the implementation.
--        "

    OBJECT		sysORID
    MIN-ACCESS	not-accessible
    DESCRIPTION
        "(U//FOUO) Implementation of this object can be as low
         as not-accessible depending on which
         IS Objective or MIB desired requirements are
         not being met by the implementation.
        "

    OBJECT		ipv6InterfaceForwarding
    MIN-ACCESS	read-only
    DESCRIPTION
        "(U//FOUO) Implementation of this object can be as low
         as read-only depending on which
         IS Objective or MIB desired requirements are
         not being met by the implementation.
        "

    OBJECT		ipForwarding
    MIN-ACCESS	read-only
    DESCRIPTION
        "(U//FOUO) Implementation of this object can be as low
         as read-only depending on which
         IS Objective or MIB desired requirements are
         not being met by the implementation.
        "

    OBJECT		nlmLogVariableOctetStringVal
    MIN-ACCESS	read-only
    DESCRIPTION
        "(U//FOUO) Implementation of this object can be as low
         as read-only depending on which
         IS Objective or MIB desired requirements are
         not being met by the implementation.
        "

    OBJECT		ipv6InterfaceRetransmitTime
    MIN-ACCESS	read-only
    DESCRIPTION
        "(U//FOUO) Implementation of this object can be as low
         as read-only depending on which
         IS Objective or MIB desired requirements are
         not being met by the implementation.
        "

    OBJECT		ifLastChange
    MIN-ACCESS	read-only
    DESCRIPTION
        "(U//FOUO) Implementation of this object can be as low
         as read-only depending on which
         IS Objective or MIB desired requirements are
         not being met by the implementation.
        "

    OBJECT		ifLinkUpDownTrapEnable
    MIN-ACCESS	not-accessible
    DESCRIPTION
        "(U//FOUO) Implementation of this object can be as low
         as not-accessible depending on which
         IS Objective or MIB desired requirements are
         not being met by the implementation.
        "

    OBJECT		ifHCOutBroadcastPkts
    MIN-ACCESS	not-accessible
    DESCRIPTION
        "(U//FOUO) Implementation of this object can be as low
         as not-accessible depending on which
         IS Objective or MIB desired requirements are
         not being met by the implementation.
        "

    OBJECT		sysLocation
    MIN-ACCESS	read-write
    DESCRIPTION
        "(U//FOUO) Implementation of this object can be as low
         as read-write depending on which
         IS Objective or MIB desired requirements are
         not being met by the implementation.
        "

--    OBJECT		usmDESPrivProtocol
--    MIN-ACCESS	read-write
--    DESCRIPTION
--        "(U//FOUO) Implementation of this object can be as low
--         as read-write depending on which
--         IS Objective or MIB desired requirements are
--         not being met by the implementation.
--        "

    OBJECT		ipNetToPhysicalRowStatus
    MIN-ACCESS	read-only
    DESCRIPTION
        "(U//FOUO) Implementation of this object can be as low
         as read-only depending on which
         IS Objective or MIB desired requirements are
         not being met by the implementation.
        "

    OBJECT		vacmViewTreeFamilyMask
    MIN-ACCESS	read-write
    DESCRIPTION
        "(U//FOUO) Implementation of this object can be as low
         as read-write depending on which
         IS Objective or MIB desired requirements are
         not being met by the implementation.
        "

    OBJECT		snmpTargetSpinLock
    MIN-ACCESS	read-write
    DESCRIPTION
        "(U//FOUO) Implementation of this object can be as low
         as read-write depending on which
         IS Objective or MIB desired requirements are
         not being met by the implementation.
        "

--    OBJECT		vacmMIBConformance
--    MIN-ACCESS	read-write
--    DESCRIPTION
--        "(U//FOUO) Implementation of this object can be as low
--         as read-write depending on which
--         IS Objective or MIB desired requirements are
--         not being met by the implementation.
--        "

    OBJECT		hIfv6HaipeTableCount
    MIN-ACCESS	read-only
    DESCRIPTION
        "(U//FOUO) Implementation of this object can be as low
         as read-only depending on which
         IS Objective or MIB desired requirements are
         not being met by the implementation.
        "

    OBJECT		hdvName
    MIN-ACCESS	read-only
    DESCRIPTION
        "(U//FOUO) Implementation of this object can be as low
         as read-only depending on which
         IS Objective or MIB desired requirements are
         not being met by the implementation.
        "

    OBJECT		usmStatsUnknownUserNames
    MIN-ACCESS	not-accessible
    DESCRIPTION
        "(U//FOUO) Implementation of this object can be as low
         as not-accessible depending on which
         IS Objective or MIB desired requirements are
         not being met by the implementation.
        "

--    OBJECT		snmpEngineGroup
--    MIN-ACCESS	read-write
--    DESCRIPTION
--        "(U//FOUO) Implementation of this object can be as low
--         as read-write depending on which
--         IS Objective or MIB desired requirements are
--         not being met by the implementation.
--        "

    OBJECT		haipeZeroizeAllKeys
    MIN-ACCESS	read-write
    DESCRIPTION
        "(U//FOUO) Implementation of this object can be as low
         as read-write depending on which
         IS Objective or MIB desired requirements are
         not being met by the implementation.
        "

    OBJECT		ipReasmTimeout
    MIN-ACCESS	read-only
    DESCRIPTION
        "(U//FOUO) Implementation of this object can be as low
         as read-only depending on which
         IS Objective or MIB desired requirements are
         not being met by the implementation.
        "

    OBJECT		ipv6InterfaceReachableTime
    MIN-ACCESS	read-only
    DESCRIPTION
        "(U//FOUO) Implementation of this object can be as low
         as read-only depending on which
         IS Objective or MIB desired requirements are
         not being met by the implementation.
        "

--    OBJECT		snmpFrameworkMIBGroups
--    MIN-ACCESS	read-write
--    DESCRIPTION
--        "(U//FOUO) Implementation of this object can be as low
--         as read-write depending on which
--         IS Objective or MIB desired requirements are
--         not being met by the implementation.
--        "

    OBJECT		ifHCInBroadcastPkts
    MIN-ACCESS	not-accessible
    DESCRIPTION
        "(U//FOUO) Implementation of this object can be as low
         as not-accessible depending on which
         IS Objective or MIB desired requirements are
         not being met by the implementation.
        "

    OBJECT		snmpTargetAddrTDomain
    MIN-ACCESS	read-write
    DESCRIPTION
        "(U//FOUO) Implementation of this object can be as low
         as read-write depending on which
         IS Objective or MIB desired requirements are
         not being met by the implementation.
        "

    OBJECT		snmpInvalidMsgs
    MIN-ACCESS	not-accessible
    DESCRIPTION
        "(U//FOUO) Implementation of this object can be as low
         as not-accessible depending on which
         IS Objective or MIB desired requirements are
         not being met by the implementation.
        "

    OBJECT		usmUserOwnAuthKeyChange
    MIN-ACCESS	read-write
    DESCRIPTION
        "(U//FOUO) Implementation of this object can be as low
         as read-write depending on which
         IS Objective or MIB desired requirements are
         not being met by the implementation.
        "

    OBJECT		snmpTargetAddrRowStatus
    MIN-ACCESS	read-write
    DESCRIPTION
        "(U//FOUO) Implementation of this object can be as low
         as read-write depending on which
         IS Objective or MIB desired requirements are
         not being met by the implementation.
        "

    OBJECT		nlmLogVariableCounter32Val
    MIN-ACCESS	read-only
    DESCRIPTION
        "(U//FOUO) Implementation of this object can be as low
         as read-only depending on which
         IS Objective or MIB desired requirements are
         not being met by the implementation.
        "

    OBJECT		nlmLogVariableValueType
    MIN-ACCESS	read-only
    DESCRIPTION
        "(U//FOUO) Implementation of this object can be as low
         as read-only depending on which
         IS Objective or MIB desired requirements are
         not being met by the implementation.
        "

    OBJECT		ifOperStatus
    MIN-ACCESS	read-only
    DESCRIPTION
        "(U//FOUO) Implementation of this object can be as low
         as read-only depending on which
         IS Objective or MIB desired requirements are
         not being met by the implementation.
        "

    OBJECT		nlmConfigGlobalAgeOut
    MIN-ACCESS	read-write
    DESCRIPTION
        "(U//FOUO) Implementation of this object can be as low
         as read-write depending on which
         IS Objective or MIB desired requirements are
         not being met by the implementation.
        "

    OBJECT		ipv4InterfaceRetransmitTime
    MIN-ACCESS	read-only
    DESCRIPTION
        "(U//FOUO) Implementation of this object can be as low
         as read-only depending on which
         IS Objective or MIB desired requirements are
         not being met by the implementation.
        "

    OBJECT		ifHCOutUcastPkts
    MIN-ACCESS	not-accessible
    DESCRIPTION
        "(U//FOUO) Implementation of this object can be as low
         as not-accessible depending on which
         IS Objective or MIB desired requirements are
         not being met by the implementation.
        "

    OBJECT		vacmAccessWriteViewName
    MIN-ACCESS	read-write
    DESCRIPTION
        "(U//FOUO) Implementation of this object can be as low
         as read-write depending on which
         IS Objective or MIB desired requirements are
         not being met by the implementation.
        "

    OBJECT		usmStatsDecryptionErrors
    MIN-ACCESS	not-accessible
    DESCRIPTION
        "(U//FOUO) Implementation of this object can be as low
         as not-accessible depending on which
         IS Objective or MIB desired requirements are
         not being met by the implementation.
        "

    OBJECT		nlmLogEngineTAddress
    MIN-ACCESS	read-only
    DESCRIPTION
        "(U//FOUO) Implementation of this object can be as low
         as read-only depending on which
         IS Objective or MIB desired requirements are
         not being met by the implementation.
        "

    OBJECT		sysName
    MIN-ACCESS	read-write
    DESCRIPTION
        "(U//FOUO) Implementation of this object can be as low
         as read-write depending on which
         IS Objective or MIB desired requirements are
         not being met by the implementation.
        "

    OBJECT		hBatteryLevelWarningPercentage
    MIN-ACCESS	read-only
    DESCRIPTION
        "(U//FOUO) Implementation of this object can be as low
         as read-only depending on which
         IS Objective or MIB desired requirements are
         not being met by the implementation.
        "

    OBJECT		ifIndex
    MIN-ACCESS	read-only
    DESCRIPTION
        "(U//FOUO) Implementation of this object can be as low
         as read-only depending on which
         IS Objective or MIB desired requirements are
         not being met by the implementation.
        "

    OBJECT		usmUserAuthProtocol
    MIN-ACCESS	read-write
    DESCRIPTION
        "(U//FOUO) Implementation of this object can be as low
         as read-write depending on which
         IS Objective or MIB desired requirements are
         not being met by the implementation.
        "

    OBJECT		snmpTrapOID
    MIN-ACCESS	accessible-for-notify
    DESCRIPTION
        "(U//FOUO) Implementation of this object can be as low
         as accessible-for-notify depending on which
         IS Objective or MIB desired requirements are
         not being met by the implementation.
        "

    OBJECT		ipv6InterfaceEnableStatus
    MIN-ACCESS	read-only
    DESCRIPTION
        "(U//FOUO) Implementation of this object can be as low
         as read-only depending on which
         IS Objective or MIB desired requirements are
         not being met by the implementation.
        "

    OBJECT		sysDescr
    MIN-ACCESS	read-only
    DESCRIPTION
        "(U//FOUO) Implementation of this object can be as low
         as read-only depending on which
         IS Objective or MIB desired requirements are
         not being met by the implementation.
        "

--    OBJECT		snmpEngine
--    MIN-ACCESS	read-write
--    DESCRIPTION
--        "(U//FOUO) Implementation of this object can be as low
--         as read-write depending on which
--         IS Objective or MIB desired requirements are
--         not being met by the implementation.
--        "

    OBJECT		hLocalCKListRowStatus
    MIN-ACCESS	read-write
    DESCRIPTION
        "(U//FOUO) Implementation of this object can be as low
         as read-write depending on which
         IS Objective or MIB desired requirements are
         not being met by the implementation.
        "

--    OBJECT		vacmMIBObjects
--    MIN-ACCESS	read-write
--    DESCRIPTION
--        "(U//FOUO) Implementation of this object can be as low
--         as read-write depending on which
--         IS Objective or MIB desired requirements are
--         not being met by the implementation.
--        "

--    OBJECT		snmpFrameworkMIB
--    MIN-ACCESS	read-write
--    DESCRIPTION
--        "(U//FOUO) Implementation of this object can be as low
--         as read-write depending on which
--         IS Objective or MIB desired requirements are
--         not being met by the implementation.
--        "

    OBJECT		usmUserStatus
    MIN-ACCESS	read-write
    DESCRIPTION
        "(U//FOUO) Implementation of this object can be as low
         as read-write depending on which
         IS Objective or MIB desired requirements are
         not being met by the implementation.
        "

    OBJECT		nlmLogContextName
    MIN-ACCESS	read-only
    DESCRIPTION
        "(U//FOUO) Implementation of this object can be as low
         as read-only depending on which
         IS Objective or MIB desired requirements are
         not being met by the implementation.
        "

    OBJECT		usmUserPrivKeyChange
    MIN-ACCESS	read-write
    DESCRIPTION
        "(U//FOUO) Implementation of this object can be as low
         as read-write depending on which
         IS Objective or MIB desired requirements are
         not being met by the implementation.
        "

    OBJECT		hBatteryOperStatus
    MIN-ACCESS	read-only
    DESCRIPTION
        "(U//FOUO) Implementation of this object can be as low
         as read-only depending on which
         IS Objective or MIB desired requirements are
         not being met by the implementation.
        "

    OBJECT		usmStatsUnsupportedSecLevels
    MIN-ACCESS	not-accessible
    DESCRIPTION
        "(U//FOUO) Implementation of this object can be as low
         as not-accessible depending on which
         IS Objective or MIB desired requirements are
         not being met by the implementation.
        "

    OBJECT		hIfv6HaipeTableLastChanged
    MIN-ACCESS	read-only
    DESCRIPTION
        "(U//FOUO) Implementation of this object can be as low
         as read-only depending on which
         IS Objective or MIB desired requirements are
         not being met by the implementation.
        "

    OBJECT		snmpNotifyFilterProfileRowStatus
    MIN-ACCESS	read-write
    DESCRIPTION
        "(U//FOUO) Implementation of this object can be as low
         as read-write depending on which
         IS Objective or MIB desired requirements are
         not being met by the implementation.
        "

    OBJECT		hDeviceVersionTableCount
    MIN-ACCESS	read-only
    DESCRIPTION
        "(U//FOUO) Implementation of this object can be as low
         as read-only depending on which
         IS Objective or MIB desired requirements are
         not being met by the implementation.
        "

    OBJECT		usmStatsNotInTimeWindows
    MIN-ACCESS	not-accessible
    DESCRIPTION
        "(U//FOUO) Implementation of this object can be as low
         as not-accessible depending on which
         IS Objective or MIB desired requirements are
         not being met by the implementation.
        "

    OBJECT		vacmViewSpinLock
    MIN-ACCESS	read-write
    DESCRIPTION
        "(U//FOUO) Implementation of this object can be as low
         as read-write depending on which
         IS Objective or MIB desired requirements are
         not being met by the implementation.
        "

    OBJECT		nlmLogVariableOidVal
    MIN-ACCESS	read-only
    DESCRIPTION
        "(U//FOUO) Implementation of this object can be as low
         as read-only depending on which
         IS Objective or MIB desired requirements are
         not being met by the implementation.
        "

    OBJECT		ipNetToPhysicalState
    MIN-ACCESS	read-only
    DESCRIPTION
        "(U//FOUO) Implementation of this object can be as low
         as read-only depending on which
         IS Objective or MIB desired requirements are
         not being met by the implementation.
        "

    OBJECT		ifType
    MIN-ACCESS	read-only
    DESCRIPTION
        "(U//FOUO) Implementation of this object can be as low
         as read-only depending on which
         IS Objective or MIB desired requirements are
         not being met by the implementation.
        "

    OBJECT		snmpNotifyStorageType
    MIN-ACCESS	read-write
    DESCRIPTION
        "(U//FOUO) Implementation of this object can be as low
         as read-write depending on which
         IS Objective or MIB desired requirements are
         not being met by the implementation.
        "

    OBJECT		hLocalCKListReason
    MIN-ACCESS	read-write
    DESCRIPTION
        "(U//FOUO) Implementation of this object can be as low
         as read-write depending on which
         IS Objective or MIB desired requirements are
         not being met by the implementation.
        "

    OBJECT		ifPhysAddress
    MIN-ACCESS	read-only
    DESCRIPTION
        "(U//FOUO) Implementation of this object can be as low
         as read-only depending on which
         IS Objective or MIB desired requirements are
         not being met by the implementation.
        "

    OBJECT		hDeviceVersionTableLastChanged
    MIN-ACCESS	read-only
    DESCRIPTION
        "(U//FOUO) Implementation of this object can be as low
         as read-only depending on which
         IS Objective or MIB desired requirements are
         not being met by the implementation.
        "

    OBJECT		ifDescr
    MIN-ACCESS	read-only
    DESCRIPTION
        "(U//FOUO) Implementation of this object can be as low
         as read-only depending on which
         IS Objective or MIB desired requirements are
         not being met by the implementation.
        "

    OBJECT		ifConnectorPresent
    MIN-ACCESS	read-only
    DESCRIPTION
        "(U//FOUO) Implementation of this object can be as low
         as read-only depending on which
         IS Objective or MIB desired requirements are
         not being met by the implementation.
        "

    OBJECT		nlmLogEngineTDomain
    MIN-ACCESS	read-only
    DESCRIPTION
        "(U//FOUO) Implementation of this object can be as low
         as read-only depending on which
         IS Objective or MIB desired requirements are
         not being met by the implementation.
        "

    OBJECT		snmpTargetParamsSecurityLevel
    MIN-ACCESS	read-write
    DESCRIPTION
        "(U//FOUO) Implementation of this object can be as low
         as read-write depending on which
         IS Objective or MIB desired requirements are
         not being met by the implementation.
        "

    OBJECT		hrSystemUptime
    MIN-ACCESS	not-accessible
    DESCRIPTION
        "(U//FOUO) Implementation of this object can be as low
         as not-accessible depending on which
         IS Objective or MIB desired requirements are
         not being met by the implementation.
        "

    OBJECT		snmpTargetAddrRetryCount
    MIN-ACCESS	read-write
    DESCRIPTION
        "(U//FOUO) Implementation of this object can be as low
         as read-write depending on which
         IS Objective or MIB desired requirements are
         not being met by the implementation.
        "

    OBJECT		hLocalCKListKMIDEnd
    MIN-ACCESS	read-only
    DESCRIPTION
        "(U//FOUO) Implementation of this object can be as low
         as read-only depending on which
         IS Objective or MIB desired requirements are
         not being met by the implementation.
        "

    OBJECT		snmpUnknownContexts
    MIN-ACCESS	not-accessible
    DESCRIPTION
        "(U//FOUO) Implementation of this object can be as low
         as not-accessible depending on which
         IS Objective or MIB desired requirements are
         not being met by the implementation.
        "

    OBJECT		snmpTargetAddrStorageType
    MIN-ACCESS	read-write
    DESCRIPTION
        "(U//FOUO) Implementation of this object can be as low
         as read-write depending on which
         IS Objective or MIB desired requirements are
         not being met by the implementation.
        "

    OBJECT		snmpEngineTime
    MIN-ACCESS	read-only
    DESCRIPTION
        "(U//FOUO) Implementation of this object can be as low
         as read-only depending on which
         IS Objective or MIB desired requirements are
         not being met by the implementation.
        "

--    OBJECT		usmHMACSHAAuthProtocol
--    MIN-ACCESS	read-write
--    DESCRIPTION
--        "(U//FOUO) Implementation of this object can be as low
--         as read-write depending on which
--         IS Objective or MIB desired requirements are
--         not being met by the implementation.
--        "

    OBJECT		usmStatsUnknownEngineIDs
    MIN-ACCESS	not-accessible
    DESCRIPTION
        "(U//FOUO) Implementation of this object can be as low
         as not-accessible depending on which
         IS Objective or MIB desired requirements are
         not being met by the implementation.
        "

    OBJECT		snmpTargetAddrTimeout
    MIN-ACCESS	read-write
    DESCRIPTION
        "(U//FOUO) Implementation of this object can be as low
         as read-write depending on which
         IS Objective or MIB desired requirements are
         not being met by the implementation.
        "

--    OBJECT		usmHMACMD5AuthProtocol
--    MIN-ACCESS	read-write
--    DESCRIPTION
--        "(U//FOUO) Implementation of this object can be as low
--         as read-write depending on which
--         IS Objective or MIB desired requirements are
--         not being met by the implementation.
--        "

    OBJECT		ifSpeed
    MIN-ACCESS	read-only
    DESCRIPTION
        "(U//FOUO) Implementation of this object can be as low
         as read-only depending on which
         IS Objective or MIB desired requirements are
         not being met by the implementation.
        "

    OBJECT		ifPromiscuousMode
    MIN-ACCESS	not-accessible
    DESCRIPTION
        "(U//FOUO) Implementation of this object can be as low
         as not-accessible depending on which
         IS Objective or MIB desired requirements are
         not being met by the implementation.
        "

    OBJECT		snmpTargetParamsSecurityModel
    MIN-ACCESS	read-write
    DESCRIPTION
        "(U//FOUO) Implementation of this object can be as low
         as read-write depending on which
         IS Objective or MIB desired requirements are
         not being met by the implementation.
        "

    OBJECT		ipv4InterfaceReasmMaxSize
    MIN-ACCESS	read-only
    DESCRIPTION
        "(U//FOUO) Implementation of this object can be as low
         as read-only depending on which
         IS Objective or MIB desired requirements are
         not being met by the implementation.
        "

    OBJECT		usmStatsWrongDigests
    MIN-ACCESS	not-accessible
    DESCRIPTION
        "(U//FOUO) Implementation of this object can be as low
         as not-accessible depending on which
         IS Objective or MIB desired requirements are
         not being met by the implementation.
        "

--    OBJECT		usmNoPrivProtocol
--    MIN-ACCESS	read-write
--    DESCRIPTION
--        "(U//FOUO) Implementation of this object can be as low
--         as read-write depending on which
--         IS Objective or MIB desired requirements are
--         not being met by the implementation.
--        "

    OBJECT		usmUserPublic
    MIN-ACCESS	read-write
    DESCRIPTION
        "(U//FOUO) Implementation of this object can be as low
         as read-write depending on which
         IS Objective or MIB desired requirements are
         not being met by the implementation.
        "

    OBJECT		hBatteryLevelPercentage
    MIN-ACCESS	read-only
    DESCRIPTION
        "(U//FOUO) Implementation of this object can be as low
         as read-only depending on which
         IS Objective or MIB desired requirements are
         not being met by the implementation.
        "

    OBJECT		ifOutMulticastPkts
    MIN-ACCESS	not-accessible
    DESCRIPTION
        "(U//FOUO) Implementation of this object can be as low
         as not-accessible depending on which
         IS Objective or MIB desired requirements are
         not being met by the implementation.
        "

    OBJECT		sysServices
    MIN-ACCESS	read-only
    DESCRIPTION
        "(U//FOUO) Implementation of this object can be as low
         as read-only depending on which
         IS Objective or MIB desired requirements are
         not being met by the implementation.
        "

    OBJECT		ipNetToPhysicalType
    MIN-ACCESS	read-only
    DESCRIPTION
        "(U//FOUO) Implementation of this object can be as low
         as read-only depending on which
         IS Objective or MIB desired requirements are
         not being met by the implementation.
        "

--    OBJECT		snmpFrameworkMIBConformance
--    MIN-ACCESS	read-write
--    DESCRIPTION
--        "(U//FOUO) Implementation of this object can be as low
--         as read-write depending on which
--         IS Objective or MIB desired requirements are
--         not being met by the implementation.
--        "

    OBJECT		ipNetToPhysicalPhysAddress
    MIN-ACCESS	read-only
    DESCRIPTION
        "(U//FOUO) Implementation of this object can be as low
         as read-only depending on which
         IS Objective or MIB desired requirements are
         not being met by the implementation.
        "

    OBJECT		usmUserCloneFrom
    MIN-ACCESS	read-write
    DESCRIPTION
        "(U//FOUO) Implementation of this object can be as low
         as read-write depending on which
         IS Objective or MIB desired requirements are
         not being met by the implementation.
        "

    OBJECT		usmUserSpinLock
    MIN-ACCESS	read-write
    DESCRIPTION
        "(U//FOUO) Implementation of this object can be as low
         as read-write depending on which
         IS Objective or MIB desired requirements are
         not being met by the implementation.
        "

    OBJECT		sysUpTime
    MIN-ACCESS	read-only
    DESCRIPTION
        "(U//FOUO) Implementation of this object can be as low
         as read-only depending on which
         IS Objective or MIB desired requirements are
         not being met by the implementation.
        "

    OBJECT		hLocalCKListKMIDBegin
    MIN-ACCESS	read-only
    DESCRIPTION
        "(U//FOUO) Implementation of this object can be as low
         as read-only depending on which
         IS Objective or MIB desired requirements are
         not being met by the implementation.
        "

    OBJECT		nlmLogVariableID
    MIN-ACCESS	read-only
    DESCRIPTION
        "(U//FOUO) Implementation of this object can be as low
         as read-only depending on which
         IS Objective or MIB desired requirements are
         not being met by the implementation.
        "

    OBJECT		snmpTargetParamsMPModel
    MIN-ACCESS	read-write
    DESCRIPTION
        "(U//FOUO) Implementation of this object can be as low
         as read-write depending on which
         IS Objective or MIB desired requirements are
         not being met by the implementation.
        "

    OBJECT		snmpSetSerialNo
    MIN-ACCESS	read-write
    DESCRIPTION
        "(U//FOUO) Implementation of this object can be as low
         as read-write depending on which
         IS Objective or MIB desired requirements are
         not being met by the implementation.
        "

    OBJECT		ifInBroadcastPkts
    MIN-ACCESS	not-accessible
    DESCRIPTION
        "(U//FOUO) Implementation of this object can be as low
         as not-accessible depending on which
         IS Objective or MIB desired requirements are
         not being met by the implementation.
        "

    OBJECT		ifHCInUcastPkts
    MIN-ACCESS	not-accessible
    DESCRIPTION
        "(U//FOUO) Implementation of this object can be as low
         as not-accessible depending on which
         IS Objective or MIB desired requirements are
         not being met by the implementation.
        "

    OBJECT		vacmGroupName
    MIN-ACCESS	read-write
    DESCRIPTION
        "(U//FOUO) Implementation of this object can be as low
         as read-write depending on which
         IS Objective or MIB desired requirements are
         not being met by the implementation.
        "

    OBJECT		hSecurityLevels
    MIN-ACCESS	read-only
    DESCRIPTION
        "(U//FOUO) Implementation of this object can be as low
         as read-only depending on which
         IS Objective or MIB desired requirements are
         not being met by the implementation.
        "

--    OBJECT		snmpFrameworkMIBCompliances
--    MIN-ACCESS	read-write
--    DESCRIPTION
--        "(U//FOUO) Implementation of this object can be as low
--         as read-write depending on which
--         IS Objective or MIB desired requirements are
--         not being met by the implementation.
--        "

    OBJECT		ipv6InterfaceReasmMaxSize
    MIN-ACCESS	read-only
    DESCRIPTION
        "(U//FOUO) Implementation of this object can be as low
         as read-only depending on which
         IS Objective or MIB desired requirements are
         not being met by the implementation.
        "

--    OBJECT		usmNoAuthProtocol
--    MIN-ACCESS	read-write
--    DESCRIPTION
--        "(U//FOUO) Implementation of this object can be as low
--         as read-write depending on which
--         IS Objective or MIB desired requirements are
--         not being met by the implementation.
--        "

    OBJECT		vacmAccessContextMatch
    MIN-ACCESS	read-write
    DESCRIPTION
        "(U//FOUO) Implementation of this object can be as low
         as read-write depending on which
         IS Objective or MIB desired requirements are
         not being met by the implementation.
        "

    OBJECT		ifCounterDiscontinuityTime
    MIN-ACCESS	not-accessible
    DESCRIPTION
        "(U//FOUO) Implementation of this object can be as low
         as not-accessible depending on which
         IS Objective or MIB desired requirements are
         not being met by the implementation.
        "

--    OBJECT		snmpFrameworkAdmin
--    MIN-ACCESS	read-write
--    DESCRIPTION
--        "(U//FOUO) Implementation of this object can be as low
--         as read-write depending on which
--         IS Objective or MIB desired requirements are
--         not being met by the implementation.
--        "

    OBJECT		hIfv4LastChanged
    MIN-ACCESS	read-only
    DESCRIPTION
        "(U//FOUO) Implementation of this object can be as low
         as read-only depending on which
         IS Objective or MIB desired requirements are
         not being met by the implementation.
        "

    OBJECT		ifHCOutMulticastPkts
    MIN-ACCESS	not-accessible
    DESCRIPTION
        "(U//FOUO) Implementation of this object can be as low
         as not-accessible depending on which
         IS Objective or MIB desired requirements are
         not being met by the implementation.
        "

    OBJECT		nlmLogEngineID
    MIN-ACCESS	read-only
    DESCRIPTION
        "(U//FOUO) Implementation of this object can be as low
         as read-only depending on which
         IS Objective or MIB desired requirements are
         not being met by the implementation.
        "

    OBJECT		snmpNotifyFilterMask
    MIN-ACCESS	read-write
    DESCRIPTION
        "(U//FOUO) Implementation of this object can be as low
         as read-write depending on which
         IS Objective or MIB desired requirements are
         not being met by the implementation.
        "

    OBJECT		snmpNotifyFilterProfileStorType
    MIN-ACCESS	read-write
    DESCRIPTION
        "(U//FOUO) Implementation of this object can be as low
         as read-write depending on which
         IS Objective or MIB desired requirements are
         not being met by the implementation.
        "

--    OBJECT		hBatteryOK
--    MIN-ACCESS	not-accessible
--    DESCRIPTION
--        "(U//FOUO) Implementation of this object can be as low
--         as not-accessible depending on which
--         IS Objective or MIB desired requirements are
--         not being met by the implementation.
--        "

--    OBJECT		vacmMIBViews
--    MIN-ACCESS	read-write
--    DESCRIPTION
--        "(U//FOUO) Implementation of this object can be as low
--         as read-write depending on which
--         IS Objective or MIB desired requirements are
--         not being met by the implementation.
--        "

--    OBJECT		snmpUsmAesMIB
--    MIN-ACCESS	read-only
--    DESCRIPTION
--        "(U//FOUO) Implementation of this object can be as low
--         as read-only depending on which
--         IS Objective or MIB desired requirements are
--         not being met by the implementation.
--        "

    OBJECT		nlmLogVariableOpaqueVal
    MIN-ACCESS	read-only
    DESCRIPTION
        "(U//FOUO) Implementation of this object can be as low
         as read-only depending on which
         IS Objective or MIB desired requirements are
         not being met by the implementation.
        "

    OBJECT		vacmAccessNotifyViewName
    MIN-ACCESS	read-write
    DESCRIPTION
        "(U//FOUO) Implementation of this object can be as low
         as read-write depending on which
         IS Objective or MIB desired requirements are
         not being met by the implementation.
        "

    OBJECT		hIfv4HaipeTableLastChanged
    MIN-ACCESS	read-only
    DESCRIPTION
        "(U//FOUO) Implementation of this object can be as low
         as read-only depending on which
         IS Objective or MIB desired requirements are
         not being met by the implementation.
        "

    OBJECT		ipNetToPhysicalLastUpdated
    MIN-ACCESS	read-only
    DESCRIPTION
        "(U//FOUO) Implementation of this object can be as low
         as read-only depending on which
         IS Objective or MIB desired requirements are
         not being met by the implementation.
        "

    OBJECT		nlmConfigGlobalEntryLimit
    MIN-ACCESS	read-write
    DESCRIPTION
        "(U//FOUO) Implementation of this object can be as low
         as read-write depending on which
         IS Objective or MIB desired requirements are
         not being met by the implementation.
        "

--    OBJECT		warmStart
--    MIN-ACCESS	accessible-for-notify
--    DESCRIPTION
--        "(U//FOUO) Implementation of this object can be as low
--         as accessible-for-notify depending on which
--         IS Objective or MIB desired requirements are
--         not being met by the implementation.
--        "

    OBJECT		snmpTargetAddrTagList
    MIN-ACCESS	read-write
    DESCRIPTION
        "(U//FOUO) Implementation of this object can be as low
         as read-write depending on which
         IS Objective or MIB desired requirements are
         not being met by the implementation.
        "

    OBJECT		hIfv4Side
    MIN-ACCESS	read-only
    DESCRIPTION
        "(U//FOUO) Implementation of this object can be as low
         as read-only depending on which
         IS Objective or MIB desired requirements are
         not being met by the implementation.
        "

--    OBJECT		snmpAuthProtocols
--    MIN-ACCESS	read-write
--    DESCRIPTION
--        "(U//FOUO) Implementation of this object can be as low
--         as read-write depending on which
--         IS Objective or MIB desired requirements are
--         not being met by the implementation.
--        "

    OBJECT		vacmAccessReadViewName
    MIN-ACCESS	read-write
    DESCRIPTION
        "(U//FOUO) Implementation of this object can be as low
         as read-write depending on which
         IS Objective or MIB desired requirements are
         not being met by the implementation.
        "

    OBJECT		hIfv6Side
    MIN-ACCESS	read-only
    DESCRIPTION
        "(U//FOUO) Implementation of this object can be as low
         as read-only depending on which
         IS Objective or MIB desired requirements are
         not being met by the implementation.
        "

    OBJECT		ipAddressSpinLock
    MIN-ACCESS	not-accessible
    DESCRIPTION
        "(U//FOUO) Implementation of this object can be as low
         as not-accessible depending on which
         IS Objective or MIB desired requirements are
         not being met by the implementation.
        "

    OBJECT		snmpNotifyRowStatus
    MIN-ACCESS	read-write
    DESCRIPTION
        "(U//FOUO) Implementation of this object can be as low
         as read-write depending on which
         IS Objective or MIB desired requirements are
         not being met by the implementation.
        "

    OBJECT		ipv6InterfaceIdentifier
    MIN-ACCESS	read-only
    DESCRIPTION
        "(U//FOUO) Implementation of this object can be as low
         as read-only depending on which
         IS Objective or MIB desired requirements are
         not being met by the implementation.
        "

    OBJECT		ifNumber
    MIN-ACCESS	read-only
    DESCRIPTION
        "(U//FOUO) Implementation of this object can be as low
         as read-only depending on which
         IS Objective or MIB desired requirements are
         not being met by the implementation.
        "

    OBJECT		ifName
    MIN-ACCESS	read-only
    DESCRIPTION
        "(U//FOUO) Implementation of this object can be as low
         as read-only depending on which
         IS Objective or MIB desired requirements are
         not being met by the implementation.
        "

    OBJECT		nlmLogVariableTimeTicksVal
    MIN-ACCESS	read-only
    DESCRIPTION
        "(U//FOUO) Implementation of this object can be as low
         as read-only depending on which
         IS Objective or MIB desired requirements are
         not being met by the implementation.
        "

    OBJECT		ifOutBroadcastPkts
    MIN-ACCESS	not-accessible
    DESCRIPTION
        "(U//FOUO) Implementation of this object can be as low
         as not-accessible depending on which
         IS Objective or MIB desired requirements are
         not being met by the implementation.
        "

    OBJECT		nlmLogTime
    MIN-ACCESS	read-only
    DESCRIPTION
        "(U//FOUO) Implementation of this object can be as low
         as read-only depending on which
         IS Objective or MIB desired requirements are
         not being met by the implementation.
        "

    OBJECT		hrSystemDate
    MIN-ACCESS	not-accessible
    DESCRIPTION
        "(U//FOUO) Implementation of this object can be as low
         as not-accessible depending on which
         IS Objective or MIB desired requirements are
         not being met by the implementation.
        "

    OBJECT		usmUserSecurityName
    MIN-ACCESS	read-only
    DESCRIPTION
        "(U//FOUO) Implementation of this object can be as low
         as read-only depending on which
         IS Objective or MIB desired requirements are
         not being met by the implementation.
        "

    OBJECT		sysORDescr
    MIN-ACCESS	not-accessible
    DESCRIPTION
        "(U//FOUO) Implementation of this object can be as low
         as not-accessible depending on which
         IS Objective or MIB desired requirements are
         not being met by the implementation.
        "

    OBJECT		hBatteryNumber
    MIN-ACCESS	read-only
    DESCRIPTION
        "(U//FOUO) Implementation of this object can be as low
         as read-only depending on which
         IS Objective or MIB desired requirements are
         not being met by the implementation.
        "

    OBJECT		ipDefaultTTL
    MIN-ACCESS	not-accessible
    DESCRIPTION
        "(U//FOUO) Implementation of this object can be as low
         as not-accessible depending on which
         IS Objective or MIB desired requirements are
         not being met by the implementation.
        "

--    OBJECT		vacmMIBCompliance
--    MIN-ACCESS	read-write
--    DESCRIPTION
--        "(U//FOUO) Implementation of this object can be as low
--         as read-write depending on which
--         IS Objective or MIB desired requirements are
--         not being met by the implementation.
--        "

    OBJECT		hHMISpinLock
    MIN-ACCESS	not-accessible
    DESCRIPTION
        "(U//FOUO) Implementation of this object can be as low
         as not-accessible depending on which
         IS Objective or MIB desired requirements are
         not being met by the implementation.
        "

    OBJECT		sysContact
    MIN-ACCESS	read-write
    DESCRIPTION
        "(U//FOUO) Implementation of this object can be as low
         as read-write depending on which
         IS Objective or MIB desired requirements are
         not being met by the implementation.
        "

    OBJECT		hLocalCKListUniversal
    MIN-ACCESS	read-only
    DESCRIPTION
        "(U//FOUO) Implementation of this object can be as low
         as read-only depending on which
         IS Objective or MIB desired requirements are
         not being met by the implementation.
        "

    OBJECT		ifHCInMulticastPkts
    MIN-ACCESS	not-accessible
    DESCRIPTION
        "(U//FOUO) Implementation of this object can be as low
         as not-accessible depending on which
         IS Objective or MIB desired requirements are
         not being met by the implementation.
        "

    OBJECT		ifAdminStatus
    MIN-ACCESS	read-write
    DESCRIPTION
        "(U//FOUO) Implementation of this object can be as low
         as read-write depending on which
         IS Objective or MIB desired requirements are
         not being met by the implementation.
        "

    OBJECT		snmpNotifyTag
    MIN-ACCESS	read-write
    DESCRIPTION
        "(U//FOUO) Implementation of this object can be as low
         as read-write depending on which
         IS Objective or MIB desired requirements are
         not being met by the implementation.
        "

    OBJECT		hIfv4HaipeTableCount
    MIN-ACCESS	read-only
    DESCRIPTION
        "(U//FOUO) Implementation of this object can be as low
         as read-only depending on which
         IS Objective or MIB desired requirements are
         not being met by the implementation.
        "

--    OBJECT		snmpFrameworkMIBCompliance
--    MIN-ACCESS	read-write
--    DESCRIPTION
--        "(U//FOUO) Implementation of this object can be as low
--         as read-write depending on which
--         IS Objective or MIB desired requirements are
--         not being met by the implementation.
--        "

    OBJECT		nlmLogContextEngineID
    MIN-ACCESS	read-only
    DESCRIPTION
        "(U//FOUO) Implementation of this object can be as low
         as read-only depending on which
         IS Objective or MIB desired requirements are
         not being met by the implementation.
        "

    OBJECT		snmpTrapEnterprise
    MIN-ACCESS	accessible-for-notify
    DESCRIPTION
        "(U//FOUO) Implementation of this object can be as low
         as accessible-for-notify depending on which
         IS Objective or MIB desired requirements are
         not being met by the implementation.
        "

    OBJECT		nlmLogVariableUnsigned32Val
    MIN-ACCESS	read-only
    DESCRIPTION
        "(U//FOUO) Implementation of this object can be as low
         as read-only depending on which
         IS Objective or MIB desired requirements are
         not being met by the implementation.
        "

    OBJECT		vacmViewTreeFamilyStorageType
    MIN-ACCESS	read-write
    DESCRIPTION
        "(U//FOUO) Implementation of this object can be as low
         as read-write depending on which
         IS Objective or MIB desired requirements are
         not being met by the implementation.
        "

--    OBJECT		vacmBasicGroup
--    MIN-ACCESS	read-write
--    DESCRIPTION
--        "(U//FOUO) Implementation of this object can be as low
--         as read-write depending on which
--         IS Objective or MIB desired requirements are
--         not being met by the implementation.
--        "

    OBJECT		snmpTargetParamsRowStatus
    MIN-ACCESS	read-write
    DESCRIPTION
        "(U//FOUO) Implementation of this object can be as low
         as read-write depending on which
         IS Objective or MIB desired requirements are
         not being met by the implementation.
        "

    OBJECT		nlmLogVariableInteger32Val
    MIN-ACCESS	read-only
    DESCRIPTION
        "(U//FOUO) Implementation of this object can be as low
         as read-only depending on which
         IS Objective or MIB desired requirements are
         not being met by the implementation.
        "

    OBJECT		snmpTargetParamsSecurityName
    MIN-ACCESS	read-write
    DESCRIPTION
        "(U//FOUO) Implementation of this object can be as low
         as read-write depending on which
         IS Objective or MIB desired requirements are
         not being met by the implementation.
        "

    OBJECT		snmpEngineID
    MIN-ACCESS	read-only
    DESCRIPTION
        "(U//FOUO) Implementation of this object can be as low
         as read-only depending on which
         IS Objective or MIB desired requirements are
         not being met by the implementation.
        "

    OBJECT		ifInMulticastPkts
    MIN-ACCESS	not-accessible
    DESCRIPTION
        "(U//FOUO) Implementation of this object can be as low
         as not-accessible depending on which
         IS Objective or MIB desired requirements are
         not being met by the implementation.
        "

    OBJECT		haipeSanitizeDevice
    MIN-ACCESS	read-write
    DESCRIPTION
        "(U//FOUO) Implementation of this object can be as low
         as read-write depending on which
         IS Objective or MIB desired requirements are
         not being met by the implementation.
        "

    OBJECT		ifHCInOctets
    MIN-ACCESS	not-accessible
    DESCRIPTION
        "(U//FOUO) Implementation of this object can be as low
         as not-accessible depending on which
         IS Objective or MIB desired requirements are
         not being met by the implementation.
        "

    OBJECT		snmpTargetAddrTAddress
    MIN-ACCESS	read-write
    DESCRIPTION
        "(U//FOUO) Implementation of this object can be as low
         as read-write depending on which
         IS Objective or MIB desired requirements are
         not being met by the implementation.
        "

    OBJECT		hSpinLock
    MIN-ACCESS	read-write
    DESCRIPTION
        "(U//FOUO) Implementation of this object can be as low
         as read-write depending on which
         IS Objective or MIB desired requirements are
         not being met by the implementation.
        "

    OBJECT		sysORLastChange
    MIN-ACCESS	read-only
    DESCRIPTION
        "(U//FOUO) Implementation of this object can be as low
         as read-only depending on which
         IS Objective or MIB desired requirements are
         not being met by the implementation.
        "

    OBJECT		usmUserPrivProtocol
    MIN-ACCESS	read-write
    DESCRIPTION
        "(U//FOUO) Implementation of this object can be as low
         as read-write depending on which
         IS Objective or MIB desired requirements are
         not being met by the implementation.
        "

    OBJECT		hLastChanged
    MIN-ACCESS	read-only
    DESCRIPTION
        "(U//FOUO) Implementation of this object can be as low
         as read-only depending on which
         IS Objective or MIB desired requirements are
         not being met by the implementation.
        "

    OBJECT		snmpNotifyType
    MIN-ACCESS	read-write
    DESCRIPTION
        "(U//FOUO) Implementation of this object can be as low
         as read-write depending on which
         IS Objective or MIB desired requirements are
         not being met by the implementation.
        "

    OBJECT		vacmAccessStorageType
    MIN-ACCESS	read-write
    DESCRIPTION
        "(U//FOUO) Implementation of this object can be as low
         as read-write depending on which
         IS Objective or MIB desired requirements are
         not being met by the implementation.
        "

    OBJECT		usmUserStorageType
    MIN-ACCESS	read-write
    DESCRIPTION
        "(U//FOUO) Implementation of this object can be as low
         as read-write depending on which
         IS Objective or MIB desired requirements are
         not being met by the implementation.
        "

    OBJECT		hLocalCKListUniversalEdition
    MIN-ACCESS	read-only
    DESCRIPTION
        "(U//FOUO) Implementation of this object can be as low
         as read-only depending on which
         IS Objective or MIB desired requirements are
         not being met by the implementation.
        "

    OBJECT		usmUserOwnPrivKeyChange
    MIN-ACCESS	read-write
    DESCRIPTION
        "(U//FOUO) Implementation of this object can be as low
         as read-write depending on which
         IS Objective or MIB desired requirements are
         not being met by the implementation.
        "

    OBJECT		snmpNotifyFilterRowStatus
    MIN-ACCESS	read-write
    DESCRIPTION
        "(U//FOUO) Implementation of this object can be as low
         as read-write depending on which
         IS Objective or MIB desired requirements are
         not being met by the implementation.
        "

    OBJECT		snmpUnavailableContexts
    MIN-ACCESS	not-accessible
    DESCRIPTION
        "(U//FOUO) Implementation of this object can be as low
         as not-accessible depending on which
         IS Objective or MIB desired requirements are
         not being met by the implementation.
        "

    OBJECT		snmpNotifyFilterType
    MIN-ACCESS	read-write
    DESCRIPTION
        "(U//FOUO) Implementation of this object can be as low
         as read-write depending on which
         IS Objective or MIB desired requirements are
         not being met by the implementation.
        "

    OBJECT		vacmViewTreeFamilyType
    MIN-ACCESS	read-write
    DESCRIPTION
        "(U//FOUO) Implementation of this object can be as low
         as read-write depending on which
         IS Objective or MIB desired requirements are
         not being met by the implementation.
        "

    OBJECT		vacmAccessStatus
    MIN-ACCESS	read-write
    DESCRIPTION
        "(U//FOUO) Implementation of this object can be as low
         as read-write depending on which
         IS Objective or MIB desired requirements are
         not being met by the implementation.
        "

--    OBJECT		authenticationFailure
--    MIN-ACCESS	accessible-for-notify
--    DESCRIPTION
--        "(U//FOUO) Implementation of this object can be as low
--         as accessible-for-notify depending on which
--         IS Objective or MIB desired requirements are
--         not being met by the implementation.
--        "

--    OBJECT		snmpVacmMIB
--    MIN-ACCESS	read-write
--    DESCRIPTION
--        "(U//FOUO) Implementation of this object can be as low
--         as read-write depending on which
--         IS Objective or MIB desired requirements are
--         not being met by the implementation.
--        "

    OBJECT		snmpNotifyFilterProfileName
    MIN-ACCESS	read-write
    DESCRIPTION
        "(U//FOUO) Implementation of this object can be as low
         as read-write depending on which
         IS Objective or MIB desired requirements are
         not being met by the implementation.
        "

    OBJECT		hStationID
    MIN-ACCESS	read-only
    DESCRIPTION
        "(U//FOUO) Implementation of this object can be as low
         as read-only depending on which
         IS Objective or MIB desired requirements are
         not being met by the implementation.
        "

    OBJECT		ifHighSpeed
    MIN-ACCESS	read-only
    DESCRIPTION
        "(U//FOUO) Implementation of this object can be as low
         as read-only depending on which
         IS Objective or MIB desired requirements are
         not being met by the implementation.
        "

--    OBJECT		snmpFrameworkMIBObjects
--    MIN-ACCESS	read-write
--    DESCRIPTION
--        "(U//FOUO) Implementation of this object can be as low
--         as read-write depending on which
--         IS Objective or MIB desired requirements are
--         not being met by the implementation.
--        "

    OBJECT		sysORUpTime
    MIN-ACCESS	not-accessible
    DESCRIPTION
        "(U//FOUO) Implementation of this object can be as low
         as not-accessible depending on which
         IS Objective or MIB desired requirements are
         not being met by the implementation.
        "

    OBJECT		snmpUnknownPDUHandlers
    MIN-ACCESS	not-accessible
    DESCRIPTION
        "(U//FOUO) Implementation of this object can be as low
         as not-accessible depending on which
         IS Objective or MIB desired requirements are
         not being met by the implementation.
        "

    OBJECT		hLocalCKListDate
    MIN-ACCESS	read-only
    DESCRIPTION
        "(U//FOUO) Implementation of this object can be as low
         as read-only depending on which
         IS Objective or MIB desired requirements are
         not being met by the implementation.
        "

    OBJECT		hdvVersion
    MIN-ACCESS	read-only
    DESCRIPTION
        "(U//FOUO) Implementation of this object can be as low
         as read-only depending on which
         IS Objective or MIB desired requirements are
         not being met by the implementation.
        "

    OBJECT		haipeResetDevice
    MIN-ACCESS	read-write
    DESCRIPTION
        "(U//FOUO) Implementation of this object can be as low
         as read-write depending on which
         IS Objective or MIB desired requirements are
         not being met by the implementation.
        "

--    OBJECT		hBatteryLow
--    MIN-ACCESS	accessible-for-notify
--    DESCRIPTION
--        "(U//FOUO) Implementation of this object can be as low
--         as accessible-for-notify depending on which
--         IS Objective or MIB desired requirements are
--         not being met by the implementation.
--        "

    OBJECT		hIfv6LastChanged
    MIN-ACCESS	read-only
    DESCRIPTION
        "(U//FOUO) Implementation of this object can be as low
         as read-only depending on which
         IS Objective or MIB desired requirements are
         not being met by the implementation.
        "

    OBJECT		usmUserAuthKeyChange
    MIN-ACCESS	read-write
    DESCRIPTION
        "(U//FOUO) Implementation of this object can be as low
         as read-write depending on which
         IS Objective or MIB desired requirements are
         not being met by the implementation.
        "

    OBJECT		snmpTargetParamsStorageType
    MIN-ACCESS	read-write
    DESCRIPTION
        "(U//FOUO) Implementation of this object can be as low
         as read-write depending on which
         IS Objective or MIB desired requirements are
         not being met by the implementation.
        "

    OBJECT		snmpEngineBoots
    MIN-ACCESS	read-only
    DESCRIPTION
        "(U//FOUO) Implementation of this object can be as low
         as read-only depending on which
         IS Objective or MIB desired requirements are
         not being met by the implementation.
        "

    OBJECT		vacmContextName
    MIN-ACCESS	read-only
    DESCRIPTION
        "(U//FOUO) Implementation of this object can be as low
         as read-only depending on which
         IS Objective or MIB desired requirements are
         not being met by the implementation.
        "

--    OBJECT		vacmMIBCompliances
--    MIN-ACCESS	read-write
--    DESCRIPTION
--        "(U//FOUO) Implementation of this object can be as low
--         as read-write depending on which
--         IS Objective or MIB desired requirements are
--         not being met by the implementation.
--        "

    OBJECT		vacmSecurityToGroupStatus
    MIN-ACCESS	read-write
    DESCRIPTION
        "(U//FOUO) Implementation of this object can be as low
         as read-write depending on which
         IS Objective or MIB desired requirements are
         not being met by the implementation.
        "

    OBJECT		hBatteryChangeDate
    MIN-ACCESS	read-only
    DESCRIPTION
        "(U//FOUO) Implementation of this object can be as low
         as read-only depending on which
         IS Objective or MIB desired requirements are
         not being met by the implementation.
        "
::= { haipeV030102Conformance 6 }

--
-- Objects referenced by the Legacy Discovery Document
--
hLegacyDiscoveryGroup OBJECT-GROUP
    OBJECTS {
                hDiscoveryEnabled,
                hDiscoveryProbeTimeout,
                hDiscoveryProbeRetry,
                hDiscoveryDeliveryTableCount,
                hDiscoveryDeliveryTableLastChanged,
                hDiscSearchAddressType,
                hDiscSearchStartAddress,
                hDiscSearchEndAddress,
                hDiscDelivPriority,
                hDiscDelivType,
                hDiscDelivPTAddressType,
                hDiscDelivPTAddress,
                hDiscDelivPTPort,
                hDiscDelivStatus,
                hRemoteEnclaveTableCount,
                hRemoteEnclaveTableLastChanged,
                hRemoteEnclaveDestHostAddrType,
                hRemoteEnclaveDestHost,
                hRemoteEnclaveDestHostPTPfxLen,
                hRemoteEnclaveDestHaipePTAddrType,
                hRemoteEnclaveDestHaipePTAddr,
                hRemoteEnclaveDestHaipeCTAddrType,
                hRemoteEnclaveDestHaipeCTAddr,
                hRemoteEnclaveDestHaipeNATAddr,
                hRemoteEnclaveDestHaipeNATPort,
                hRemoteEnclaveDestAdminCost,
                hRemoteEnclaveMethod,
                hRemoteEnclaveLifetime,
                hRemoteEnclaveRowStatus,
                hPreplacedKeyTableCount,
                hPreplacedKeyTableCapacity,
                hPreplacedKeyTableLastChanged,
                hPPKUsageType,
                hPPKEffectiveDate,
                hPPKSecurityLevel,
                hPPKZeroizeKey,
                hPPKRegister,
                hPPKLastChanged,
                hPPKTrafficIntegrityAlgorithm,
                hPPKTrafficEncryptAlgorithm,
                hTPSATableCount,
                hTPSATableLastChanged,
                hTPSAspi,
                hTPSAAddressType,
                hTPSALocalCTAddress,
                hTPSARemoteCTAddress,
                hTPSAPTAddressType,
                hTPSALocalPTAddress,
                hTPSARemotePTAddress,
                hTPSADirection,
                hTPSASelectorNextHeaderStart,
                hTPSASelectorNextHeaderEnd,
                hTPSASelectorNextHeaderOpt1Start,
                hTPSASelectorNextHeaderOpt1End,
                hTPSASelectorNextHeaderOpt2Start,
                hTPSASelectorNextHeaderOpt2End,
                hTPSAConnectionType,
                hTPSASecurityPayloadType,
                hTPSAStartTime,
                hTPSAEndTime,
                hTPSAPPK,
                hTPSACreationReason,
                hTPSAEncryptAlgorithm,
                hTPSAIntegrityAlgorithm,
                hTPSACryptoBlockSize,
                hTPSADSCP,
                hTPSADSCPValue,
                hTPSAPMTU,
                hTPSAECN,
                hTPSAFlowLabel,
                hTPSAFlowLabelValue,
                hTPSADecrementTTL,
                hTPSADIndexType,
                hTPSAPDUNEnabled,
                hTPSAPHRDRate,
                hTPSADFBit,
                hTPSARetryICMPCount,
                hTPSAHCOctets,
                hTPSAHCUcastPkts,
                hTPSAHCMcastPkts,
                hTPSAHCBrdcastPkts,
                hTPSARowStatus,
                hTPSALocalCredentialID,
                hTPSALocalCredentialType,
                hTPSALocalCAName,
                hTPSARemoteCredentialID,
                hTPSARemoteCredentialType,
                hTPSARemoteCAName
            }
    STATUS    current
    DESCRIPTION
        "(U//FOUO) Objects for the 'Legacy Discovery' document"
    ::= { haipeV030102Groups 7 }

--
-- Conformance levels required by the 'Legacy Discovery' document
--
hLegacyDiscoveryCompliance MODULE-COMPLIANCE
    STATUS    current
    DESCRIPTION
        "(U//FOUO) Compliance levels for objects required by the
          'Legacy Discovery' document"
    MODULE -- this module
    MANDATORY-GROUPS { hLegacyDiscoveryGroup }

    OBJECT		hTPSADecrementTTL
    MIN-ACCESS	read-only
    DESCRIPTION
        "(U//FOUO) Implementation of this object can be as low
         as read-only depending on which
         IS Objective or MIB desired requirements are
         not being met by the implementation.
        "

    OBJECT		hRemoteEnclaveDestHaipeNATPort
    MIN-ACCESS	read-write
    DESCRIPTION
        "(U//FOUO) Implementation of this object can be as low
         as read-write depending on which
         IS Objective or MIB desired requirements are
         not being met by the implementation.
        "

    OBJECT		hTPSARemoteCredentialType
    MIN-ACCESS	read-only
    DESCRIPTION
        "(U//FOUO) Implementation of this object can be as low
         as read-only depending on which
         IS Objective or MIB desired requirements are
         not being met by the implementation.
        "

    OBJECT		hRemoteEnclaveDestHaipeCTAddrType
    MIN-ACCESS	read-write
    DESCRIPTION
        "(U//FOUO) Implementation of this object can be as low
         as read-write depending on which
         IS Objective or MIB desired requirements are
         not being met by the implementation.
        "

    OBJECT		hRemoteEnclaveDestHostPTPfxLen
    MIN-ACCESS	read-write
    DESCRIPTION
        "(U//FOUO) Implementation of this object can be as low
         as read-write depending on which
         IS Objective or MIB desired requirements are
         not being met by the implementation.
        "

    OBJECT		hRemoteEnclaveTableLastChanged
    MIN-ACCESS	read-only
    DESCRIPTION
        "(U//FOUO) Implementation of this object can be as low
         as read-only depending on which
         IS Objective or MIB desired requirements are
         not being met by the implementation.
        "

    OBJECT		hRemoteEnclaveLifetime
    MIN-ACCESS	read-write
    DESCRIPTION
        "(U//FOUO) Implementation of this object can be as low
         as read-write depending on which
         IS Objective or MIB desired requirements are
         not being met by the implementation.
        "

    OBJECT		hTPSAIntegrityAlgorithm
    MIN-ACCESS	read-write
    DESCRIPTION
        "(U//FOUO) Implementation of this object can be as low
         as read-write depending on which
         IS Objective or MIB desired requirements are
         not being met by the implementation.
        "

    OBJECT		hDiscSearchStartAddress
    MIN-ACCESS	read-write
    DESCRIPTION
        "(U//FOUO) Implementation of this object can be as low
         as read-write depending on which
         IS Objective or MIB desired requirements are
         not being met by the implementation.
        "

    OBJECT		hRemoteEnclaveMethod
    MIN-ACCESS	read-write
    DESCRIPTION
        "(U//FOUO) Implementation of this object can be as low
         as read-write depending on which
         IS Objective or MIB desired requirements are
         not being met by the implementation.
        "

    OBJECT		hPPKEffectiveDate
    MIN-ACCESS	read-only
    DESCRIPTION
        "(U//FOUO) Implementation of this object can be as low
         as read-only depending on which
         IS Objective or MIB desired requirements are
         not being met by the implementation.
        "

    OBJECT		hTPSAEndTime
    MIN-ACCESS	read-write
    DESCRIPTION
        "(U//FOUO) Implementation of this object can be as low
         as read-write depending on which
         IS Objective or MIB desired requirements are
         not being met by the implementation.
        "

    OBJECT		hTPSAHCMcastPkts
    MIN-ACCESS	not-accessible
    DESCRIPTION
        "(U//FOUO) Implementation of this object can be as low
         as not-accessible depending on which
         IS Objective or MIB desired requirements are
         not being met by the implementation.
        "

    OBJECT		hTPSADSCP
    MIN-ACCESS	read-write
    DESCRIPTION
        "(U//FOUO) Implementation of this object can be as low
         as read-write depending on which
         IS Objective or MIB desired requirements are
         not being met by the implementation.
        "

    OBJECT		hTPSAspi
    MIN-ACCESS	read-write
    DESCRIPTION
        "(U//FOUO) Implementation of this object can be as low
         as read-write depending on which
         IS Objective or MIB desired requirements are
         not being met by the implementation.
        "

    OBJECT		hPPKTrafficIntegrityAlgorithm
    MIN-ACCESS	read-only
    DESCRIPTION
        "(U//FOUO) Implementation of this object can be as low
         as read-only depending on which
         IS Objective or MIB desired requirements are
         not being met by the implementation.
        "

    OBJECT		hTPSARemoteCAName
    MIN-ACCESS	read-only
    DESCRIPTION
        "(U//FOUO) Implementation of this object can be as low
         as read-only depending on which
         IS Objective or MIB desired requirements are
         not being met by the implementation.
        "

    OBJECT		hTPSALocalCAName
    MIN-ACCESS	read-only
    DESCRIPTION
        "(U//FOUO) Implementation of this object can be as low
         as read-only depending on which
         IS Objective or MIB desired requirements are
         not being met by the implementation.
        "

    OBJECT		hTPSASelectorNextHeaderOpt2Start
    MIN-ACCESS	not-accessible
    DESCRIPTION
        "(U//FOUO) Implementation of this object can be as low
         as not-accessible depending on which
         IS Objective or MIB desired requirements are
         not being met by the implementation.
        "

    OBJECT		hTPSALocalPTAddress
    MIN-ACCESS	read-write
    DESCRIPTION
        "(U//FOUO) Implementation of this object can be as low
         as read-write depending on which
         IS Objective or MIB desired requirements are
         not being met by the implementation.
        "

    OBJECT		hDiscDelivType
    MIN-ACCESS	read-write
    DESCRIPTION
        "(U//FOUO) Implementation of this object can be as low
         as read-write depending on which
         IS Objective or MIB desired requirements are
         not being met by the implementation.
        "

    OBJECT		hTPSAPTAddressType
    MIN-ACCESS	read-write
    DESCRIPTION
        "(U//FOUO) Implementation of this object can be as low
         as read-write depending on which
         IS Objective or MIB desired requirements are
         not being met by the implementation.
        "

    OBJECT		hTPSAECN
    MIN-ACCESS	read-write
    DESCRIPTION
        "(U//FOUO) Implementation of this object can be as low
         as read-write depending on which
         IS Objective or MIB desired requirements are
         not being met by the implementation.
        "

    OBJECT		hRemoteEnclaveDestAdminCost
    MIN-ACCESS	read-write
    DESCRIPTION
        "(U//FOUO) Implementation of this object can be as low
         as read-write depending on which
         IS Objective or MIB desired requirements are
         not being met by the implementation.
        "

    OBJECT		hTPSADFBit
    MIN-ACCESS	read-write
    DESCRIPTION
        "(U//FOUO) Implementation of this object can be as low
         as read-write depending on which
         IS Objective or MIB desired requirements are
         not being met by the implementation.
        "

    OBJECT		hDiscDelivPriority
    MIN-ACCESS	read-write
    DESCRIPTION
        "(U//FOUO) Implementation of this object can be as low
         as read-write depending on which
         IS Objective or MIB desired requirements are
         not being met by the implementation.
        "

    OBJECT		hTPSARetryICMPCount
    MIN-ACCESS	read-write
    DESCRIPTION
        "(U//FOUO) Implementation of this object can be as low
         as read-write depending on which
         IS Objective or MIB desired requirements are
         not being met by the implementation.
        "

    OBJECT		hTPSAConnectionType
    MIN-ACCESS	read-write
    DESCRIPTION
        "(U//FOUO) Implementation of this object can be as low
         as read-write depending on which
         IS Objective or MIB desired requirements are
         not being met by the implementation.
        "

    OBJECT		hTPSASelectorNextHeaderOpt2End
    MIN-ACCESS	not-accessible
    DESCRIPTION
        "(U//FOUO) Implementation of this object can be as low
         as not-accessible depending on which
         IS Objective or MIB desired requirements are
         not being met by the implementation.
        "

    OBJECT		hTPSADSCPValue
    MIN-ACCESS	read-write
    DESCRIPTION
        "(U//FOUO) Implementation of this object can be as low
         as read-write depending on which
         IS Objective or MIB desired requirements are
         not being met by the implementation.
        "

    OBJECT		hPreplacedKeyTableCapacity
    MIN-ACCESS	read-only
    DESCRIPTION
        "(U//FOUO) Implementation of this object can be as low
         as read-only depending on which
         IS Objective or MIB desired requirements are
         not being met by the implementation.
        "

    OBJECT		hRemoteEnclaveDestHaipePTAddrType
    MIN-ACCESS	read-write
    DESCRIPTION
        "(U//FOUO) Implementation of this object can be as low
         as read-write depending on which
         IS Objective or MIB desired requirements are
         not being met by the implementation.
        "

    OBJECT		hTPSARemoteCTAddress
    MIN-ACCESS	read-write
    DESCRIPTION
        "(U//FOUO) Implementation of this object can be as low
         as read-write depending on which
         IS Objective or MIB desired requirements are
         not being met by the implementation.
        "

    OBJECT		hPPKRegister
    MIN-ACCESS	not-accessible
    DESCRIPTION
        "(U//FOUO) Implementation of this object can be as low
         as not-accessible depending on which
         IS Objective or MIB desired requirements are
         not being met by the implementation.
        "

    OBJECT		hTPSALocalCredentialType
    MIN-ACCESS	read-only
    DESCRIPTION
        "(U//FOUO) Implementation of this object can be as low
         as read-only depending on which
         IS Objective or MIB desired requirements are
         not being met by the implementation.
        "

    OBJECT		hTPSAFlowLabelValue
    MIN-ACCESS	read-write
    DESCRIPTION
        "(U//FOUO) Implementation of this object can be as low
         as read-write depending on which
         IS Objective or MIB desired requirements are
         not being met by the implementation.
        "

    OBJECT		hTPSAEncryptAlgorithm
    MIN-ACCESS	read-only
    DESCRIPTION
        "(U//FOUO) Implementation of this object can be as low
         as read-only depending on which
         IS Objective or MIB desired requirements are
         not being met by the implementation.
        "

    OBJECT		hTPSARemotePTAddress
    MIN-ACCESS	read-write
    DESCRIPTION
        "(U//FOUO) Implementation of this object can be as low
         as read-write depending on which
         IS Objective or MIB desired requirements are
         not being met by the implementation.
        "

    OBJECT		hDiscoveryEnabled
    MIN-ACCESS	read-write
    DESCRIPTION
        "(U//FOUO) Implementation of this object can be as low
         as read-write depending on which
         IS Objective or MIB desired requirements are
         not being met by the implementation.
        "

    OBJECT		hTPSALocalCTAddress
    MIN-ACCESS	read-write
    DESCRIPTION
        "(U//FOUO) Implementation of this object can be as low
         as read-write depending on which
         IS Objective or MIB desired requirements are
         not being met by the implementation.
        "

    OBJECT		hTPSAPDUNEnabled
    MIN-ACCESS	read-write
    DESCRIPTION
        "(U//FOUO) Implementation of this object can be as low
         as read-write depending on which
         IS Objective or MIB desired requirements are
         not being met by the implementation.
        "

    OBJECT		hRemoteEnclaveDestHaipeCTAddr
    MIN-ACCESS	read-write
    DESCRIPTION
        "(U//FOUO) Implementation of this object can be as low
         as read-write depending on which
         IS Objective or MIB desired requirements are
         not being met by the implementation.
        "

    OBJECT		hTPSASelectorNextHeaderEnd
    MIN-ACCESS	not-accessible
    DESCRIPTION
        "(U//FOUO) Implementation of this object can be as low
         as not-accessible depending on which
         IS Objective or MIB desired requirements are
         not being met by the implementation.
        "

    OBJECT		hDiscoveryDeliveryTableLastChanged
    MIN-ACCESS	read-only
    DESCRIPTION
        "(U//FOUO) Implementation of this object can be as low
         as read-only depending on which
         IS Objective or MIB desired requirements are
         not being met by the implementation.
        "

    OBJECT		hPreplacedKeyTableLastChanged
    MIN-ACCESS	read-only
    DESCRIPTION
        "(U//FOUO) Implementation of this object can be as low
         as read-only depending on which
         IS Objective or MIB desired requirements are
         not being met by the implementation.
        "

    OBJECT		hPPKSecurityLevel
    MIN-ACCESS	read-only
    DESCRIPTION
        "(U//FOUO) Implementation of this object can be as low
         as read-only depending on which
         IS Objective or MIB desired requirements are
         not being met by the implementation.
        "

    OBJECT		hTPSATableCount
    MIN-ACCESS	read-only
    DESCRIPTION
        "(U//FOUO) Implementation of this object can be as low
         as read-only depending on which
         IS Objective or MIB desired requirements are
         not being met by the implementation.
        "

    OBJECT		hPreplacedKeyTableCount
    MIN-ACCESS	read-only
    DESCRIPTION
        "(U//FOUO) Implementation of this object can be as low
         as read-only depending on which
         IS Objective or MIB desired requirements are
         not being met by the implementation.
        "

    OBJECT		hTPSACryptoBlockSize
    MIN-ACCESS	read-write
    DESCRIPTION
        "(U//FOUO) Implementation of this object can be as low
         as read-write depending on which
         IS Objective or MIB desired requirements are
         not being met by the implementation.
        "

    OBJECT		hTPSACreationReason
    MIN-ACCESS	read-only
    DESCRIPTION
        "(U//FOUO) Implementation of this object can be as low
         as read-only depending on which
         IS Objective or MIB desired requirements are
         not being met by the implementation.
        "

    OBJECT		hTPSADirection
    MIN-ACCESS	read-write
    DESCRIPTION
        "(U//FOUO) Implementation of this object can be as low
         as read-write depending on which
         IS Objective or MIB desired requirements are
         not being met by the implementation.
        "

    OBJECT		hTPSAFlowLabel
    MIN-ACCESS	read-write
    DESCRIPTION
        "(U//FOUO) Implementation of this object can be as low
         as read-write depending on which
         IS Objective or MIB desired requirements are
         not being met by the implementation.
        "

    OBJECT		hTPSALocalCredentialID
    MIN-ACCESS	read-only
    DESCRIPTION
        "(U//FOUO) Implementation of this object can be as low
         as read-only depending on which
         IS Objective or MIB desired requirements are
         not being met by the implementation.
        "

    OBJECT		hTPSAHCOctets
    MIN-ACCESS	not-accessible
    DESCRIPTION
        "(U//FOUO) Implementation of this object can be as low
         as not-accessible depending on which
         IS Objective or MIB desired requirements are
         not being met by the implementation.
        "

    OBJECT		hTPSAPMTU
    MIN-ACCESS	read-only
    DESCRIPTION
        "(U//FOUO) Implementation of this object can be as low
         as read-only depending on which
         IS Objective or MIB desired requirements are
         not being met by the implementation.
        "

    OBJECT		hTPSAStartTime
    MIN-ACCESS	read-write
    DESCRIPTION
        "(U//FOUO) Implementation of this object can be as low
         as read-write depending on which
         IS Objective or MIB desired requirements are
         not being met by the implementation.
        "

    OBJECT		hRemoteEnclaveDestHaipeNATAddr
    MIN-ACCESS	read-write
    DESCRIPTION
        "(U//FOUO) Implementation of this object can be as low
         as read-write depending on which
         IS Objective or MIB desired requirements are
         not being met by the implementation.
        "

    OBJECT		hPPKZeroizeKey
    MIN-ACCESS	read-write
    DESCRIPTION
        "(U//FOUO) Implementation of this object can be as low
         as read-write depending on which
         IS Objective or MIB desired requirements are
         not being met by the implementation.
        "

    OBJECT		hTPSAHCUcastPkts
    MIN-ACCESS	not-accessible
    DESCRIPTION
        "(U//FOUO) Implementation of this object can be as low
         as not-accessible depending on which
         IS Objective or MIB desired requirements are
         not being met by the implementation.
        "

    OBJECT		hTPSADIndexType
    MIN-ACCESS	read-write
    DESCRIPTION
        "(U//FOUO) Implementation of this object can be as low
         as read-write depending on which
         IS Objective or MIB desired requirements are
         not being met by the implementation.
        "

    OBJECT		hRemoteEnclaveTableCount
    MIN-ACCESS	read-only
    DESCRIPTION
        "(U//FOUO) Implementation of this object can be as low
         as read-only depending on which
         IS Objective or MIB desired requirements are
         not being met by the implementation.
        "

    OBJECT		hTPSASelectorNextHeaderOpt1End
    MIN-ACCESS	not-accessible
    DESCRIPTION
        "(U//FOUO) Implementation of this object can be as low
         as not-accessible depending on which
         IS Objective or MIB desired requirements are
         not being met by the implementation.
        "

    OBJECT		hTPSASelectorNextHeaderOpt1Start
    MIN-ACCESS	not-accessible
    DESCRIPTION
        "(U//FOUO) Implementation of this object can be as low
         as not-accessible depending on which
         IS Objective or MIB desired requirements are
         not being met by the implementation.
        "

    OBJECT		hRemoteEnclaveDestHostAddrType
    MIN-ACCESS	read-write
    DESCRIPTION
        "(U//FOUO) Implementation of this object can be as low
         as read-write depending on which
         IS Objective or MIB desired requirements are
         not being met by the implementation.
        "

    OBJECT		hTPSATableLastChanged
    MIN-ACCESS	read-only
    DESCRIPTION
        "(U//FOUO) Implementation of this object can be as low
         as read-only depending on which
         IS Objective or MIB desired requirements are
         not being met by the implementation.
        "

    OBJECT		hDiscDelivPTAddress
    MIN-ACCESS	read-write
    DESCRIPTION
        "(U//FOUO) Implementation of this object can be as low
         as read-write depending on which
         IS Objective or MIB desired requirements are
         not being met by the implementation.
        "

    OBJECT		hDiscDelivStatus
    MIN-ACCESS	read-write
    DESCRIPTION
        "(U//FOUO) Implementation of this object can be as low
         as read-write depending on which
         IS Objective or MIB desired requirements are
         not being met by the implementation.
        "

    OBJECT		hDiscoveryProbeRetry
    MIN-ACCESS	read-only
    DESCRIPTION
        "(U//FOUO) Implementation of this object can be as low
         as read-only depending on which
         IS Objective or MIB desired requirements are
         not being met by the implementation.
        "

    OBJECT		hDiscSearchEndAddress
    MIN-ACCESS	read-write
    DESCRIPTION
        "(U//FOUO) Implementation of this object can be as low
         as read-write depending on which
         IS Objective or MIB desired requirements are
         not being met by the implementation.
        "

    OBJECT		hPPKTrafficEncryptAlgorithm
    MIN-ACCESS	read-only
    DESCRIPTION
        "(U//FOUO) Implementation of this object can be as low
         as read-only depending on which
         IS Objective or MIB desired requirements are
         not being met by the implementation.
        "

    OBJECT		hTPSARemoteCredentialID
    MIN-ACCESS	read-only
    DESCRIPTION
        "(U//FOUO) Implementation of this object can be as low
         as read-only depending on which
         IS Objective or MIB desired requirements are
         not being met by the implementation.
        "

    OBJECT		hDiscoveryProbeTimeout
    MIN-ACCESS	read-only
    DESCRIPTION
        "(U//FOUO) Implementation of this object can be as low
         as read-only depending on which
         IS Objective or MIB desired requirements are
         not being met by the implementation.
        "

    OBJECT		hRemoteEnclaveDestHaipePTAddr
    MIN-ACCESS	read-write
    DESCRIPTION
        "(U//FOUO) Implementation of this object can be as low
         as read-write depending on which
         IS Objective or MIB desired requirements are
         not being met by the implementation.
        "

    OBJECT		hPPKLastChanged
    MIN-ACCESS	read-only
    DESCRIPTION
        "(U//FOUO) Implementation of this object can be as low
         as read-only depending on which
         IS Objective or MIB desired requirements are
         not being met by the implementation.
        "

    OBJECT		hTPSAPPK
    MIN-ACCESS	read-write
    DESCRIPTION
        "(U//FOUO) Implementation of this object can be as low
         as read-write depending on which
         IS Objective or MIB desired requirements are
         not being met by the implementation.
        "

    OBJECT		hTPSAHCBrdcastPkts
    MIN-ACCESS	not-accessible
    DESCRIPTION
        "(U//FOUO) Implementation of this object can be as low
         as not-accessible depending on which
         IS Objective or MIB desired requirements are
         not being met by the implementation.
        "

    OBJECT		hRemoteEnclaveRowStatus
    MIN-ACCESS	read-write
    DESCRIPTION
        "(U//FOUO) Implementation of this object can be as low
         as read-write depending on which
         IS Objective or MIB desired requirements are
         not being met by the implementation.
        "

    OBJECT		hDiscDelivPTPort
    MIN-ACCESS	read-write
    DESCRIPTION
        "(U//FOUO) Implementation of this object can be as low
         as read-write depending on which
         IS Objective or MIB desired requirements are
         not being met by the implementation.
        "

    OBJECT		hTPSARowStatus
    MIN-ACCESS	read-write
    DESCRIPTION
        "(U//FOUO) Implementation of this object can be as low
         as read-write depending on which
         IS Objective or MIB desired requirements are
         not being met by the implementation.
        "

    OBJECT		hTPSASecurityPayloadType
    MIN-ACCESS	read-only
    DESCRIPTION
        "(U//FOUO) Implementation of this object can be as low
         as read-only depending on which
         IS Objective or MIB desired requirements are
         not being met by the implementation.
        "

    OBJECT		hDiscSearchAddressType
    MIN-ACCESS	read-write
    DESCRIPTION
        "(U//FOUO) Implementation of this object can be as low
         as read-write depending on which
         IS Objective or MIB desired requirements are
         not being met by the implementation.
        "

    OBJECT		hRemoteEnclaveDestHost
    MIN-ACCESS	read-write
    DESCRIPTION
        "(U//FOUO) Implementation of this object can be as low
         as read-write depending on which
         IS Objective or MIB desired requirements are
         not being met by the implementation.
        "

    OBJECT		hTPSAAddressType
    MIN-ACCESS	read-write
    DESCRIPTION
        "(U//FOUO) Implementation of this object can be as low
         as read-write depending on which
         IS Objective or MIB desired requirements are
         not being met by the implementation.
        "

    OBJECT		hTPSAPHRDRate
    MIN-ACCESS	read-write
    DESCRIPTION
        "(U//FOUO) Implementation of this object can be as low
         as read-write depending on which
         IS Objective or MIB desired requirements are
         not being met by the implementation.
        "

    OBJECT		hTPSASelectorNextHeaderStart
    MIN-ACCESS	not-accessible
    DESCRIPTION
        "(U//FOUO) Implementation of this object can be as low
         as not-accessible depending on which
         IS Objective or MIB desired requirements are
         not being met by the implementation.
        "

    OBJECT		hDiscDelivPTAddressType
    MIN-ACCESS	read-write
    DESCRIPTION
        "(U//FOUO) Implementation of this object can be as low
         as read-write depending on which
         IS Objective or MIB desired requirements are
         not being met by the implementation.
        "

    OBJECT		hDiscoveryDeliveryTableCount
    MIN-ACCESS	read-only
    DESCRIPTION
        "(U//FOUO) Implementation of this object can be as low
         as read-only depending on which
         IS Objective or MIB desired requirements are
         not being met by the implementation.
        "

    OBJECT		hPPKUsageType
    MIN-ACCESS	read-write
    DESCRIPTION
        "(U//FOUO) Implementation of this object can be as low
         as read-write depending on which
         IS Objective or MIB desired requirements are
         not being met by the implementation.
        "
::= { haipeV030102Conformance 7 }

--
-- Objects referenced by the Remote Provisioning Authority Document
--
hRemoteProvisioningAuthorityGroup OBJECT-GROUP
    OBJECTS {
                hKTLoadedKeyTableCount,
                hKTLoadedKeyTableLastChanged,
                hKTLoadedKeyShortTitle,
                hKTLoadedKeyEdition,
                hKTLoadedKeySegment,
                hKTLoadedKeyRegister,
                hKTLoadedKeyUse,
                hKTLoadedKeyClassification,
                hKTLoadedKeyText,
                hKTLoadedKeyAction,
                hKTLoadedKeyRowStatus,
                hKTOOBTFTPDesiredTimeoutInterval,
                hKTOOBClientsTableCount,
                hKTOOBClientsTableLastChanged,
                hKTOOBClientName,
                hKTOOBClientAddressType,
                hKTOOBClientAddress,
                hKTOOBClientKeyFile,
                hKTOOBClientPath,
                hKTOOBClientPushKey,
                hKTOOBClientRowStatus,
                hKTOOBKeyFileName,
                hKTOOBKeyFileNum,
                hKTOOBKeyFileShortTitle,
                hKTOOBKeyFileEdition,
                hKTOOBKeyFileSegment,
                hKTOOBKeyFileRegister,
                hKTOOBKeyFileRowStatus,
                hKTIBClientsTableCount,
                hKTIBClientsTableLastChanged,
                hKTIBClientAddressType,
                hKTIBClientAddress,
                hKTIBClientPPKShortTitle,
                hKTIBClientPPKEdition,
                hKTIBClientPPKSegment,
                hKTIBClientPPKRegister,
                hKTIBClientTransferTime,
                hKTIBClientRetries,
                hKTIBClientRetryPeriod,
                hKTIBClientEffectiveDate,
                hKTIBClientRowStatus,
--                hKTOOBControllerTFTPErrorReceived,
--                hKTOOBControllerKeyFileMissingKeyError,
--                hKTOOBLoadedKeyDeletedUsedPPKError,
                hKTOOBNotificationErrorCode,
--                hKTIBLoadedKeyDeletedUsedPPKError,
--                hKTIBControllerMissingKeyError,
                hPPKEffectiveDate
            }
    STATUS    current
    DESCRIPTION
        "(U//FOUO) Objects for the 'Remote Provisioning Authority' document"
    ::= { haipeV030102Groups 8 }

--
-- Conformance levels required by the 'Remote Provisioning Authority' document
--
hRemoteProvisioningAuthorityCompliance MODULE-COMPLIANCE
    STATUS    current
    DESCRIPTION
        "(U//FOUO) Compliance levels for objects required by the
          'Remote Provisioning Authority' document"
    MODULE -- this module
    MANDATORY-GROUPS { hRemoteProvisioningAuthorityGroup }

    OBJECT		hKTOOBClientsTableLastChanged
    MIN-ACCESS	read-only
    DESCRIPTION
        "(U//FOUO) Implementation of this object can be as low
         as read-only depending on which
         IS Objective or MIB desired requirements are
         not being met by the implementation.
        "

    OBJECT		hKTOOBNotificationErrorCode
    MIN-ACCESS	not-accessible
    DESCRIPTION
        "(U//FOUO) Implementation of this object can be as low
         as not-accessible depending on which
         IS Objective or MIB desired requirements are
         not being met by the implementation.
        "

    OBJECT		hKTOOBKeyFileSegment
    MIN-ACCESS	read-write
    DESCRIPTION
        "(U//FOUO) Implementation of this object can be as low
         as read-write depending on which
         IS Objective or MIB desired requirements are
         not being met by the implementation.
        "

    OBJECT		hKTIBClientPPKRegister
    MIN-ACCESS	read-write
    DESCRIPTION
        "(U//FOUO) Implementation of this object can be as low
         as read-write depending on which
         IS Objective or MIB desired requirements are
         not being met by the implementation.
        "

    OBJECT		hKTLoadedKeyTableCount
    MIN-ACCESS	read-only
    DESCRIPTION
        "(U//FOUO) Implementation of this object can be as low
         as read-only depending on which
         IS Objective or MIB desired requirements are
         not being met by the implementation.
        "

    OBJECT		hKTIBClientAddressType
    MIN-ACCESS	read-write
    DESCRIPTION
        "(U//FOUO) Implementation of this object can be as low
         as read-write depending on which
         IS Objective or MIB desired requirements are
         not being met by the implementation.
        "

    OBJECT		hPPKEffectiveDate
    MIN-ACCESS	read-only
    DESCRIPTION
        "(U//FOUO) Implementation of this object can be as low
         as read-only depending on which
         IS Objective or MIB desired requirements are
         not being met by the implementation.
        "

    OBJECT		hKTOOBKeyFileNum
    MIN-ACCESS	read-write
    DESCRIPTION
        "(U//FOUO) Implementation of this object can be as low
         as read-write depending on which
         IS Objective or MIB desired requirements are
         not being met by the implementation.
        "

--    OBJECT		hKTOOBControllerKeyFileMissingKeyError
--    MIN-ACCESS	not-accessible
--    DESCRIPTION
--        "(U//FOUO) Implementation of this object can be as low
--         as not-accessible depending on which
--         IS Objective or MIB desired requirements are
--         not being met by the implementation.
--        "

    OBJECT		hKTLoadedKeyShortTitle
    MIN-ACCESS	read-only
    DESCRIPTION
        "(U//FOUO) Implementation of this object can be as low
         as read-only depending on which
         IS Objective or MIB desired requirements are
         not being met by the implementation.
        "

    OBJECT		hKTIBClientsTableLastChanged
    MIN-ACCESS	read-only
    DESCRIPTION
        "(U//FOUO) Implementation of this object can be as low
         as read-only depending on which
         IS Objective or MIB desired requirements are
         not being met by the implementation.
        "

    OBJECT		hKTIBClientEffectiveDate
    MIN-ACCESS	read-write
    DESCRIPTION
        "(U//FOUO) Implementation of this object can be as low
         as read-write depending on which
         IS Objective or MIB desired requirements are
         not being met by the implementation.
        "

    OBJECT		hKTLoadedKeyEdition
    MIN-ACCESS	read-only
    DESCRIPTION
        "(U//FOUO) Implementation of this object can be as low
         as read-only depending on which
         IS Objective or MIB desired requirements are
         not being met by the implementation.
        "

    OBJECT		hKTOOBKeyFileName
    MIN-ACCESS	read-write
    DESCRIPTION
        "(U//FOUO) Implementation of this object can be as low
         as read-write depending on which
         IS Objective or MIB desired requirements are
         not being met by the implementation.
        "

    OBJECT		hKTOOBClientPushKey
    MIN-ACCESS	read-write
    DESCRIPTION
        "(U//FOUO) Implementation of this object can be as low
         as read-write depending on which
         IS Objective or MIB desired requirements are
         not being met by the implementation.
        "

    OBJECT		hKTOOBKeyFileEdition
    MIN-ACCESS	read-write
    DESCRIPTION
        "(U//FOUO) Implementation of this object can be as low
         as read-write depending on which
         IS Objective or MIB desired requirements are
         not being met by the implementation.
        "

    OBJECT		hKTOOBClientRowStatus
    MIN-ACCESS	read-write
    DESCRIPTION
        "(U//FOUO) Implementation of this object can be as low
         as read-write depending on which
         IS Objective or MIB desired requirements are
         not being met by the implementation.
        "

    OBJECT		hKTIBClientTransferTime
    MIN-ACCESS	read-write
    DESCRIPTION
        "(U//FOUO) Implementation of this object can be as low
         as read-write depending on which
         IS Objective or MIB desired requirements are
         not being met by the implementation.
        "

    OBJECT		hKTLoadedKeySegment
    MIN-ACCESS	read-only
    DESCRIPTION
        "(U//FOUO) Implementation of this object can be as low
         as read-only depending on which
         IS Objective or MIB desired requirements are
         not being met by the implementation.
        "

--    OBJECT		hKTIBControllerMissingKeyError
--    MIN-ACCESS	not-accessible
--    DESCRIPTION
--        "(U//FOUO) Implementation of this object can be as low
--         as not-accessible depending on which
--         IS Objective or MIB desired requirements are
--         not being met by the implementation.
--        "

--    OBJECT		hKTOOBControllerTFTPErrorReceived
--    MIN-ACCESS	not-accessible
--    DESCRIPTION
--        "(U//FOUO) Implementation of this object can be as low
--         as not-accessible depending on which
--         IS Objective or MIB desired requirements are
--         not being met by the implementation.
--        "

    OBJECT		hKTLoadedKeyRegister
    MIN-ACCESS	read-only
    DESCRIPTION
        "(U//FOUO) Implementation of this object can be as low
         as read-only depending on which
         IS Objective or MIB desired requirements are
         not being met by the implementation.
        "

    OBJECT		hKTOOBClientName
    MIN-ACCESS	read-write
    DESCRIPTION
        "(U//FOUO) Implementation of this object can be as low
         as read-write depending on which
         IS Objective or MIB desired requirements are
         not being met by the implementation.
        "

    OBJECT		hKTOOBClientAddress
    MIN-ACCESS	read-write
    DESCRIPTION
        "(U//FOUO) Implementation of this object can be as low
         as read-write depending on which
         IS Objective or MIB desired requirements are
         not being met by the implementation.
        "

    OBJECT		hKTOOBTFTPDesiredTimeoutInterval
    MIN-ACCESS	read-write
    DESCRIPTION
        "(U//FOUO) Implementation of this object can be as low
         as read-write depending on which
         IS Objective or MIB desired requirements are
         not being met by the implementation.
        "

    OBJECT		hKTIBClientAddress
    MIN-ACCESS	read-write
    DESCRIPTION
        "(U//FOUO) Implementation of this object can be as low
         as read-write depending on which
         IS Objective or MIB desired requirements are
         not being met by the implementation.
        "

    OBJECT		hKTIBClientRetries
    MIN-ACCESS	read-write
    DESCRIPTION
        "(U//FOUO) Implementation of this object can be as low
         as read-write depending on which
         IS Objective or MIB desired requirements are
         not being met by the implementation.
        "

    OBJECT		hKTLoadedKeyTableLastChanged
    MIN-ACCESS	read-only
    DESCRIPTION
        "(U//FOUO) Implementation of this object can be as low
         as read-only depending on which
         IS Objective or MIB desired requirements are
         not being met by the implementation.
        "

    OBJECT		hKTOOBClientKeyFile
    MIN-ACCESS	read-write
    DESCRIPTION
        "(U//FOUO) Implementation of this object can be as low
         as read-write depending on which
         IS Objective or MIB desired requirements are
         not being met by the implementation.
        "

    OBJECT		hKTOOBClientPath
    MIN-ACCESS	read-write
    DESCRIPTION
        "(U//FOUO) Implementation of this object can be as low
         as read-write depending on which
         IS Objective or MIB desired requirements are
         not being met by the implementation.
        "

    OBJECT		hKTLoadedKeyAction
    MIN-ACCESS	read-write
    DESCRIPTION
        "(U//FOUO) Implementation of this object can be as low
         as read-write depending on which
         IS Objective or MIB desired requirements are
         not being met by the implementation.
        "

    OBJECT		hKTLoadedKeyRowStatus
    MIN-ACCESS	read-write
    DESCRIPTION
        "(U//FOUO) Implementation of this object can be as low
         as read-write depending on which
         IS Objective or MIB desired requirements are
         not being met by the implementation.
        "

    OBJECT		hKTIBClientPPKEdition
    MIN-ACCESS	read-write
    DESCRIPTION
        "(U//FOUO) Implementation of this object can be as low
         as read-write depending on which
         IS Objective or MIB desired requirements are
         not being met by the implementation.
        "

    OBJECT		hKTIBClientPPKSegment
    MIN-ACCESS	read-write
    DESCRIPTION
        "(U//FOUO) Implementation of this object can be as low
         as read-write depending on which
         IS Objective or MIB desired requirements are
         not being met by the implementation.
        "

    OBJECT		hKTLoadedKeyClassification
    MIN-ACCESS	read-only
    DESCRIPTION
        "(U//FOUO) Implementation of this object can be as low
         as read-only depending on which
         IS Objective or MIB desired requirements are
         not being met by the implementation.
        "

    OBJECT		hKTOOBKeyFileRegister
    MIN-ACCESS	read-write
    DESCRIPTION
        "(U//FOUO) Implementation of this object can be as low
         as read-write depending on which
         IS Objective or MIB desired requirements are
         not being met by the implementation.
        "

--    OBJECT		hKTOOBLoadedKeyDeletedUsedPPKError
--    MIN-ACCESS	not-accessible
--    DESCRIPTION
--        "(U//FOUO) Implementation of this object can be as low
--         as not-accessible depending on which
--         IS Objective or MIB desired requirements are
--         not being met by the implementation.
--        "

    OBJECT		hKTLoadedKeyUse
    MIN-ACCESS	read-only
    DESCRIPTION
        "(U//FOUO) Implementation of this object can be as low
         as read-only depending on which
         IS Objective or MIB desired requirements are
         not being met by the implementation.
        "

    OBJECT		hKTIBClientPPKShortTitle
    MIN-ACCESS	read-write
    DESCRIPTION
        "(U//FOUO) Implementation of this object can be as low
         as read-write depending on which
         IS Objective or MIB desired requirements are
         not being met by the implementation.
        "

    OBJECT		hKTLoadedKeyText
    MIN-ACCESS	read-only
    DESCRIPTION
        "(U//FOUO) Implementation of this object can be as low
         as read-only depending on which
         IS Objective or MIB desired requirements are
         not being met by the implementation.
        "

    OBJECT		hKTOOBKeyFileShortTitle
    MIN-ACCESS	read-write
    DESCRIPTION
        "(U//FOUO) Implementation of this object can be as low
         as read-write depending on which
         IS Objective or MIB desired requirements are
         not being met by the implementation.
        "

    OBJECT		hKTOOBKeyFileRowStatus
    MIN-ACCESS	read-write
    DESCRIPTION
        "(U//FOUO) Implementation of this object can be as low
         as read-write depending on which
         IS Objective or MIB desired requirements are
         not being met by the implementation.
        "

--    OBJECT		hKTIBLoadedKeyDeletedUsedPPKError
--    MIN-ACCESS	not-accessible
--    DESCRIPTION
--        "(U//FOUO) Implementation of this object can be as low
--         as not-accessible depending on which
--         IS Objective or MIB desired requirements are
--         not being met by the implementation.
--        "

    OBJECT		hKTIBClientRetryPeriod
    MIN-ACCESS	read-write
    DESCRIPTION
        "(U//FOUO) Implementation of this object can be as low
         as read-write depending on which
         IS Objective or MIB desired requirements are
         not being met by the implementation.
        "

    OBJECT		hKTOOBClientAddressType
    MIN-ACCESS	read-write
    DESCRIPTION
        "(U//FOUO) Implementation of this object can be as low
         as read-write depending on which
         IS Objective or MIB desired requirements are
         not being met by the implementation.
        "

    OBJECT		hKTIBClientsTableCount
    MIN-ACCESS	read-only
    DESCRIPTION
        "(U//FOUO) Implementation of this object can be as low
         as read-only depending on which
         IS Objective or MIB desired requirements are
         not being met by the implementation.
        "

    OBJECT		hKTOOBClientsTableCount
    MIN-ACCESS	read-only
    DESCRIPTION
        "(U//FOUO) Implementation of this object can be as low
         as read-only depending on which
         IS Objective or MIB desired requirements are
         not being met by the implementation.
        "

    OBJECT		hKTIBClientRowStatus
    MIN-ACCESS	read-write
    DESCRIPTION
        "(U//FOUO) Implementation of this object can be as low
         as read-write depending on which
         IS Objective or MIB desired requirements are
         not being met by the implementation.
        "
::= { haipeV030102Conformance 8 }

--
-- Objects referenced by the Remote Provisioning Document
--
hRemoteProvisioningGroup OBJECT-GROUP
    OBJECTS {
                hKTOOBTFTPDesiredTimeoutInterval,
                hKTOOBAuthControllersTableCount,
                hKTOOBAuthControllersTableLastChanged,
                hKTOOBACName,
                hKTOOBACAddressType,
                hKTOOBACAddress,
                hKTOOBACRowStatus,
                hStationID,
                hTFTPDesiredBlockSize,
                hTFTPDesiredTimeoutInterval,
                hTFTPMaximumFileTransferSize,
                hFirmwareDownloadServersTableCount,
                hFirmwareDownloadServersTableLastChanged,
                hFdsPriority,
                hFdsURI,
                hFdsSide,
                hFdsLoginName,
                hFdsPassword,
                hFdsLastChanged,
                hFdsRowStatus,
                hFirmwareDownloadAdminStatus,
                hFirmwareDownloadOperStatus,
--                hFirmwareDownloadError,
--                hFirmwareDownloadSuccess,
--                hFirmwareInstallFailed,
--                hFirmwareInstallSucceeded,
                hFdErrorCode,
                hFdErrorDetail,
                hrSystemDate
            }
    STATUS    current
    DESCRIPTION
        "(U//FOUO) Objects for the 'Remote Provisioning' document"
    ::= { haipeV030102Groups 9 }

--
-- Conformance levels required by the 'Remote Provisioning' document
--
hRemoteProvisioningCompliance MODULE-COMPLIANCE
    STATUS    current
    DESCRIPTION
        "(U//FOUO) Compliance levels for objects required by the
          'Remote Provisioning' document"
    MODULE -- this module
    MANDATORY-GROUPS { hRemoteProvisioningGroup }

    OBJECT		hFirmwareDownloadOperStatus
    MIN-ACCESS	read-only
    DESCRIPTION
        "(U//FOUO) Implementation of this object can be as low
         as read-only depending on which
         IS Objective or MIB desired requirements are
         not being met by the implementation.
        "

--    OBJECT		hFirmwareInstallSucceeded
--    MIN-ACCESS	accessible-for-notify
--    DESCRIPTION
--        "(U//FOUO) Implementation of this object can be as low
--         as accessible-for-notify depending on which
--         IS Objective or MIB desired requirements are
--         not being met by the implementation.
--        "

    OBJECT		hKTOOBTFTPDesiredTimeoutInterval
    MIN-ACCESS	read-write
    DESCRIPTION
        "(U//FOUO) Implementation of this object can be as low
         as read-write depending on which
         IS Objective or MIB desired requirements are
         not being met by the implementation.
        "

    OBJECT		hFdsPassword
    MIN-ACCESS	read-write
    DESCRIPTION
        "(U//FOUO) Implementation of this object can be as low
         as read-write depending on which
         IS Objective or MIB desired requirements are
         not being met by the implementation.
        "

    OBJECT		hTFTPDesiredBlockSize
    MIN-ACCESS	read-write
    DESCRIPTION
        "(U//FOUO) Implementation of this object can be as low
         as read-write depending on which
         IS Objective or MIB desired requirements are
         not being met by the implementation.
        "

    OBJECT		hKTOOBACAddressType
    MIN-ACCESS	read-write
    DESCRIPTION
        "(U//FOUO) Implementation of this object can be as low
         as read-write depending on which
         IS Objective or MIB desired requirements are
         not being met by the implementation.
        "

    OBJECT		hFdsLoginName
    MIN-ACCESS	read-write
    DESCRIPTION
        "(U//FOUO) Implementation of this object can be as low
         as read-write depending on which
         IS Objective or MIB desired requirements are
         not being met by the implementation.
        "

    OBJECT		hFirmwareDownloadServersTableCount
    MIN-ACCESS	read-only
    DESCRIPTION
        "(U//FOUO) Implementation of this object can be as low
         as read-only depending on which
         IS Objective or MIB desired requirements are
         not being met by the implementation.
        "

    OBJECT		hKTOOBACAddress
    MIN-ACCESS	read-write
    DESCRIPTION
        "(U//FOUO) Implementation of this object can be as low
         as read-write depending on which
         IS Objective or MIB desired requirements are
         not being met by the implementation.
        "

    OBJECT		hFdsRowStatus
    MIN-ACCESS	read-write
    DESCRIPTION
        "(U//FOUO) Implementation of this object can be as low
         as read-write depending on which
         IS Objective or MIB desired requirements are
         not being met by the implementation.
        "

    OBJECT		hTFTPMaximumFileTransferSize
    MIN-ACCESS	read-write
    DESCRIPTION
        "(U//FOUO) Implementation of this object can be as low
         as read-write depending on which
         IS Objective or MIB desired requirements are
         not being met by the implementation.
        "

    OBJECT		hFdsPriority
    MIN-ACCESS	read-write
    DESCRIPTION
        "(U//FOUO) Implementation of this object can be as low
         as read-write depending on which
         IS Objective or MIB desired requirements are
         not being met by the implementation.
        "

    OBJECT		hFdErrorCode
    MIN-ACCESS	accessible-for-notify
    DESCRIPTION
        "(U//FOUO) Implementation of this object can be as low
         as accessible-for-notify depending on which
         IS Objective or MIB desired requirements are
         not being met by the implementation.
        "

    OBJECT		hFdsLastChanged
    MIN-ACCESS	read-only
    DESCRIPTION
        "(U//FOUO) Implementation of this object can be as low
         as read-only depending on which
         IS Objective or MIB desired requirements are
         not being met by the implementation.
        "

    OBJECT		hTFTPDesiredTimeoutInterval
    MIN-ACCESS	read-write
    DESCRIPTION
        "(U//FOUO) Implementation of this object can be as low
         as read-write depending on which
         IS Objective or MIB desired requirements are
         not being met by the implementation.
        "

--    OBJECT		hFirmwareDownloadSuccess
--    MIN-ACCESS	accessible-for-notify
--    DESCRIPTION
--        "(U//FOUO) Implementation of this object can be as low
--         as accessible-for-notify depending on which
--         IS Objective or MIB desired requirements are
--         not being met by the implementation.
--        "

    OBJECT		hStationID
    MIN-ACCESS	accessible-for-notify
    DESCRIPTION
        "(U//FOUO) Implementation of this object can be as low
         as accessible-for-notify depending on which
         IS Objective or MIB desired requirements are
         not being met by the implementation.
        "

    OBJECT		hFirmwareDownloadAdminStatus
    MIN-ACCESS	read-write
    DESCRIPTION
        "(U//FOUO) Implementation of this object can be as low
         as read-write depending on which
         IS Objective or MIB desired requirements are
         not being met by the implementation.
        "

    OBJECT		hFdsURI
    MIN-ACCESS	read-write
    DESCRIPTION
        "(U//FOUO) Implementation of this object can be as low
         as read-write depending on which
         IS Objective or MIB desired requirements are
         not being met by the implementation.
        "

    OBJECT		hKTOOBACName
    MIN-ACCESS	read-write
    DESCRIPTION
        "(U//FOUO) Implementation of this object can be as low
         as read-write depending on which
         IS Objective or MIB desired requirements are
         not being met by the implementation.
        "

--    OBJECT		hFirmwareInstallFailed
--    MIN-ACCESS	accessible-for-notify
--    DESCRIPTION
--        "(U//FOUO) Implementation of this object can be as low
--         as accessible-for-notify depending on which
--         IS Objective or MIB desired requirements are
--         not being met by the implementation.
--        "

    OBJECT		hKTOOBACRowStatus
    MIN-ACCESS	read-write
    DESCRIPTION
        "(U//FOUO) Implementation of this object can be as low
         as read-write depending on which
         IS Objective or MIB desired requirements are
         not being met by the implementation.
        "

    OBJECT		hFirmwareDownloadServersTableLastChanged
    MIN-ACCESS	read-only
    DESCRIPTION
        "(U//FOUO) Implementation of this object can be as low
         as read-only depending on which
         IS Objective or MIB desired requirements are
         not being met by the implementation.
        "

    OBJECT		hrSystemDate
    MIN-ACCESS	accessible-for-notify
    DESCRIPTION
        "(U//FOUO) Implementation of this object can be as low
         as accessible-for-notify depending on which
         IS Objective or MIB desired requirements are
         not being met by the implementation.
        "

    OBJECT		hKTOOBAuthControllersTableLastChanged
    MIN-ACCESS	read-only
    DESCRIPTION
        "(U//FOUO) Implementation of this object can be as low
         as read-only depending on which
         IS Objective or MIB desired requirements are
         not being met by the implementation.
        "

    OBJECT		hKTOOBAuthControllersTableCount
    MIN-ACCESS	read-only
    DESCRIPTION
        "(U//FOUO) Implementation of this object can be as low
         as read-only depending on which
         IS Objective or MIB desired requirements are
         not being met by the implementation.
        "

    OBJECT		hFdsSide
    MIN-ACCESS	read-write
    DESCRIPTION
        "(U//FOUO) Implementation of this object can be as low
         as read-write depending on which
         IS Objective or MIB desired requirements are
         not being met by the implementation.
        "

--    OBJECT		hFirmwareDownloadError
--    MIN-ACCESS	accessible-for-notify
--    DESCRIPTION
--        "(U//FOUO) Implementation of this object can be as low
--         as accessible-for-notify depending on which
--         IS Objective or MIB desired requirements are
--         not being met by the implementation.
--        "

    OBJECT		hFdErrorDetail
    MIN-ACCESS	accessible-for-notify
    DESCRIPTION
        "(U//FOUO) Implementation of this object can be as low
         as accessible-for-notify depending on which
         IS Objective or MIB desired requirements are
         not being met by the implementation.
        "
::= { haipeV030102Conformance 9 }

--
-- Objects referenced by the Gateway Document
--
hGatewayGroup OBJECT-GROUP
    OBJECTS {
                hIfv6Side,
                hIfv6AddressAutoConfig,
                hIfv6DupAddressDetection,
                hIfv6DupAddressRecoveryID,
                hIfv6UseDepAddress,
                hIfv6RouterSolicitation,
                hIfv6DiscardUnauthRed,
                hIfv6LowPMTUThreshold,
                hIfv6PMTUResetPeriod,
                hIfv6LastChanged,
                hIfv6MTU,
                hIfv6HopLimit,
                hIfv6BaseReachableTime,
                hIfv6ReachableTime,
                hIfv6RetransmitTime,
                hIfv6NextHeaderSkipList,
                hIfv6InterfaceIdentifier,
                hv6AddressPrefixTableCount,
                hv6AddressPrefixTableLastChanged,
                hv6APAddressPrefixOrigin,
                hv6APAddressPrefixOnLinkFlag,
                hv6APAddressPrefixAutonomousFlag,
                hv6APAddressPrefixAdvPreferredLifetime,
                hv6APAddressPrefixAdvValidLifetime,
                hv6APAdvertisePrefix,
                hv6APRowStatus,
                hv6APLastChanged,
                hiaaInterface,
                hiaaType,
                hiaaAddress,
                hiaaPrefixLen,
                hiaaRowStatus,
                hIGMPMode,
                hMLDMode,
                hIPhFFSADSCP,
                hIPhFFSADSCPValue,
                hIPhFFSAECN,
                hIPhFFSADFBit,
                hIPhFFSAConnectionType,
                hTPSAConnectionType,
                hTPSADSCP,
                hTPSADSCPValue,
                hTPSAECN,
                hTPSAFlowLabel,
                hTPSADFBit,
                hTPAddMapCTAddress,
                hTPAddMapLastChanged,
                hTPAddMapRowStatus,
                hTPTransportMapTableCount,
                hTPTransportMapTableLastChanged,
                hTPTransMapDestPTAddress,
                hTPTransMapSourcePTAddress,
                hTPTransMapLastChanged,
                hTPTransMapRowStatus,
                ifNumber,
                ifIndex,
                ifDescr,
                ifType,
                ifMtu,
                ifSpeed,
                ifPhysAddress,
                ifAdminStatus,
                ifOperStatus,
                ifLastChange,
                ifIndex,
                ifName,
                ifInMulticastPkts,
                ifInBroadcastPkts,
                ifOutMulticastPkts,
                ifOutBroadcastPkts,
                ifHCInOctets,
                ifHCInUcastPkts,
                ifHCInMulticastPkts,
                ifHCInBroadcastPkts,
                ifHCOutOctets,
                ifHCOutUcastPkts,
                ifHCOutMulticastPkts,
                ifHCOutBroadcastPkts,
                ifLinkUpDownTrapEnable,
                ifHighSpeed,
                ifPromiscuousMode,
                ifConnectorPresent,
                ifAlias,
                ifCounterDiscontinuityTime,
                ifIndex,
                ifIndex,
                inetCidrRouteNumber,
                inetCidrRouteIfIndex,
                inetCidrRouteType,
                inetCidrRouteProto,
                inetCidrRouteAge,
                inetCidrRouteNextHopAS,
                inetCidrRouteMetric1,
                inetCidrRouteMetric2,
                inetCidrRouteMetric3,
                inetCidrRouteMetric4,
                inetCidrRouteMetric5,
                inetCidrRouteStatus,
                inetCidrRouteDiscards,
                ipv6InterfaceReasmMaxSize,
                ipv6InterfaceIdentifier,
                ipv6InterfaceEnableStatus,
                ipv6InterfaceReachableTime,
                ipv6InterfaceRetransmitTime,
                ipv6InterfaceForwarding,
                ipAddressIfIndex,
                ipAddressType,
                ipAddressPrefix,
                ipAddressOrigin,
                ipAddressStatus,
                ipAddressCreated,
                ipAddressLastChanged,
                ipAddressRowStatus,
                ipAddressStorageType,
                ipv6ScopeZoneIndexLinkLocal,
                ipv6ScopeZoneIndex3,
                ipv6ScopeZoneIndexAdminLocal,
                ipv6ScopeZoneIndexSiteLocal,
                ipv6ScopeZoneIndex6,
                ipv6ScopeZoneIndex7,
                ipv6ScopeZoneIndexOrganizationLocal,
                ipv6ScopeZoneIndex9,
                ipv6ScopeZoneIndexA,
                ipv6ScopeZoneIndexB,
                ipv6ScopeZoneIndexC,
                ipv6ScopeZoneIndexD,
                ipv6RouterAdvertSpinLock,
                ipv6RouterAdvertSendAdverts,
                ipv6RouterAdvertMaxInterval,
                ipv6RouterAdvertMinInterval,
                ipv6RouterAdvertManagedFlag,
                ipv6RouterAdvertOtherConfigFlag,
                ipv6RouterAdvertLinkMTU,
                ipv6RouterAdvertReachableTime,
                ipv6RouterAdvertRetransmitTime,
                ipv6RouterAdvertCurHopLimit,
                ipv6RouterAdvertDefaultLifetime,
                ipv6RouterAdvertRowStatus
            }
    STATUS    current
    DESCRIPTION
        "(U//FOUO) Objects for the 'Gateway' document"
    ::= { haipeV030102Groups 10 }

--
-- Conformance levels required by the 'Gateway' document
--
hGatewayCompliance MODULE-COMPLIANCE
    STATUS    current
    DESCRIPTION
        "(U//FOUO) Compliance levels for objects required by the
          'Gateway' document"
    MODULE -- this module
    MANDATORY-GROUPS { hGatewayGroup }

    OBJECT		hMLDMode
    MIN-ACCESS	read-write
    DESCRIPTION
        "(U//FOUO) Implementation of this object can be as low
         as read-write depending on which
         IS Objective or MIB desired requirements are
         not being met by the implementation.
        "

    OBJECT		hv6APAddressPrefixOrigin
    MIN-ACCESS	read-write
    DESCRIPTION
        "(U//FOUO) Implementation of this object can be as low
         as read-write depending on which
         IS Objective or MIB desired requirements are
         not being met by the implementation.
        "

    OBJECT		inetCidrRouteNumber
    MIN-ACCESS	read-only
    DESCRIPTION
        "(U//FOUO) Implementation of this object can be as low
         as read-only depending on which
         IS Objective or MIB desired requirements are
         not being met by the implementation.
        "

    OBJECT		ipv6RouterAdvertDefaultLifetime
    MIN-ACCESS	read-write
    DESCRIPTION
        "(U//FOUO) Implementation of this object can be as low
         as read-write depending on which
         IS Objective or MIB desired requirements are
         not being met by the implementation.
        "

    OBJECT		ipv6ScopeZoneIndexSiteLocal
    MIN-ACCESS	read-only
    DESCRIPTION
        "(U//FOUO) Implementation of this object can be as low
         as read-only depending on which
         IS Objective or MIB desired requirements are
         not being met by the implementation.
        "

    OBJECT		ifHCOutOctets
    MIN-ACCESS	not-accessible
    DESCRIPTION
        "(U//FOUO) Implementation of this object can be as low
         as not-accessible depending on which
         IS Objective or MIB desired requirements are
         not being met by the implementation.
        "

    OBJECT		hIfv6InterfaceIdentifier
    MIN-ACCESS	read-write
    DESCRIPTION
        "(U//FOUO) Implementation of this object can be as low
         as read-write depending on which
         IS Objective or MIB desired requirements are
         not being met by the implementation.
        "

    OBJECT		hIfv6DupAddressRecoveryID
    MIN-ACCESS	read-write
    DESCRIPTION
        "(U//FOUO) Implementation of this object can be as low
         as read-write depending on which
         IS Objective or MIB desired requirements are
         not being met by the implementation.
        "

    OBJECT		ipv6RouterAdvertManagedFlag
    MIN-ACCESS	read-write
    DESCRIPTION
        "(U//FOUO) Implementation of this object can be as low
         as read-write depending on which
         IS Objective or MIB desired requirements are
         not being met by the implementation.
        "

    OBJECT		ifAlias
    MIN-ACCESS	read-only
    DESCRIPTION
        "(U//FOUO) Implementation of this object can be as low
         as read-only depending on which
         IS Objective or MIB desired requirements are
         not being met by the implementation.
        "

    OBJECT		hTPSAConnectionType
    MIN-ACCESS	read-write
    DESCRIPTION
        "(U//FOUO) Implementation of this object can be as low
         as read-write depending on which
         IS Objective or MIB desired requirements are
         not being met by the implementation.
        "

    OBJECT		hIPhFFSADFBit
    MIN-ACCESS	read-write
    DESCRIPTION
        "(U//FOUO) Implementation of this object can be as low
         as read-write depending on which
         IS Objective or MIB desired requirements are
         not being met by the implementation.
        "

    OBJECT		ifMtu
    MIN-ACCESS	read-only
    DESCRIPTION
        "(U//FOUO) Implementation of this object can be as low
         as read-only depending on which
         IS Objective or MIB desired requirements are
         not being met by the implementation.
        "

    OBJECT		hTPSADSCPValue
    MIN-ACCESS	read-write
    DESCRIPTION
        "(U//FOUO) Implementation of this object can be as low
         as read-write depending on which
         IS Objective or MIB desired requirements are
         not being met by the implementation.
        "

    OBJECT		ipv6ScopeZoneIndexA
    MIN-ACCESS	read-only
    DESCRIPTION
        "(U//FOUO) Implementation of this object can be as low
         as read-only depending on which
         IS Objective or MIB desired requirements are
         not being met by the implementation.
        "

    OBJECT		ipv6InterfaceForwarding
    MIN-ACCESS	read-only
    DESCRIPTION
        "(U//FOUO) Implementation of this object can be as low
         as read-only depending on which
         IS Objective or MIB desired requirements are
         not being met by the implementation.
        "

    OBJECT		ipv6InterfaceRetransmitTime
    MIN-ACCESS	read-only
    DESCRIPTION
        "(U//FOUO) Implementation of this object can be as low
         as read-only depending on which
         IS Objective or MIB desired requirements are
         not being met by the implementation.
        "

    OBJECT		ipAddressIfIndex
    MIN-ACCESS	read-only
    DESCRIPTION
        "(U//FOUO) Implementation of this object can be as low
         as read-only depending on which
         IS Objective or MIB desired requirements are
         not being met by the implementation.
        "

    OBJECT		hTPTransportMapTableLastChanged
    MIN-ACCESS	read-only
    DESCRIPTION
        "(U//FOUO) Implementation of this object can be as low
         as read-only depending on which
         IS Objective or MIB desired requirements are
         not being met by the implementation.
        "

    OBJECT		ifLastChange
    MIN-ACCESS	read-only
    DESCRIPTION
        "(U//FOUO) Implementation of this object can be as low
         as read-only depending on which
         IS Objective or MIB desired requirements are
         not being met by the implementation.
        "

    OBJECT		ifLinkUpDownTrapEnable
    MIN-ACCESS	not-accessible
    DESCRIPTION
        "(U//FOUO) Implementation of this object can be as low
         as not-accessible depending on which
         IS Objective or MIB desired requirements are
         not being met by the implementation.
        "

    OBJECT		ifHCOutBroadcastPkts
    MIN-ACCESS	not-accessible
    DESCRIPTION
        "(U//FOUO) Implementation of this object can be as low
         as not-accessible depending on which
         IS Objective or MIB desired requirements are
         not being met by the implementation.
        "

    OBJECT		inetCidrRouteMetric1
    MIN-ACCESS	read-write
    DESCRIPTION
        "(U//FOUO) Implementation of this object can be as low
         as read-write depending on which
         IS Objective or MIB desired requirements are
         not being met by the implementation.
        "

    OBJECT		inetCidrRouteStatus
    MIN-ACCESS	read-write
    DESCRIPTION
        "(U//FOUO) Implementation of this object can be as low
         as read-write depending on which
         IS Objective or MIB desired requirements are
         not being met by the implementation.
        "

    OBJECT		hIfv6DupAddressDetection
    MIN-ACCESS	read-write
    DESCRIPTION
        "(U//FOUO) Implementation of this object can be as low
         as read-write depending on which
         IS Objective or MIB desired requirements are
         not being met by the implementation.
        "

    OBJECT		ipv6ScopeZoneIndexLinkLocal
    MIN-ACCESS	read-only
    DESCRIPTION
        "(U//FOUO) Implementation of this object can be as low
         as read-only depending on which
         IS Objective or MIB desired requirements are
         not being met by the implementation.
        "

    OBJECT		ipv6InterfaceReachableTime
    MIN-ACCESS	read-only
    DESCRIPTION
        "(U//FOUO) Implementation of this object can be as low
         as read-only depending on which
         IS Objective or MIB desired requirements are
         not being met by the implementation.
        "

    OBJECT		ipv6RouterAdvertCurHopLimit
    MIN-ACCESS	read-write
    DESCRIPTION
        "(U//FOUO) Implementation of this object can be as low
         as read-write depending on which
         IS Objective or MIB desired requirements are
         not being met by the implementation.
        "

    OBJECT		ifHCInBroadcastPkts
    MIN-ACCESS	not-accessible
    DESCRIPTION
        "(U//FOUO) Implementation of this object can be as low
         as not-accessible depending on which
         IS Objective or MIB desired requirements are
         not being met by the implementation.
        "

    OBJECT		ipv6RouterAdvertReachableTime
    MIN-ACCESS	read-write
    DESCRIPTION
        "(U//FOUO) Implementation of this object can be as low
         as read-write depending on which
         IS Objective or MIB desired requirements are
         not being met by the implementation.
        "

    OBJECT		hTPSAFlowLabel
    MIN-ACCESS	read-write
    DESCRIPTION
        "(U//FOUO) Implementation of this object can be as low
         as read-write depending on which
         IS Objective or MIB desired requirements are
         not being met by the implementation.
        "

    OBJECT		ifOperStatus
    MIN-ACCESS	read-only
    DESCRIPTION
        "(U//FOUO) Implementation of this object can be as low
         as read-only depending on which
         IS Objective or MIB desired requirements are
         not being met by the implementation.
        "

    OBJECT		inetCidrRouteProto
    MIN-ACCESS	read-only
    DESCRIPTION
        "(U//FOUO) Implementation of this object can be as low
         as read-only depending on which
         IS Objective or MIB desired requirements are
         not being met by the implementation.
        "

    OBJECT		ifHCOutUcastPkts
    MIN-ACCESS	not-accessible
    DESCRIPTION
        "(U//FOUO) Implementation of this object can be as low
         as not-accessible depending on which
         IS Objective or MIB desired requirements are
         not being met by the implementation.
        "

    OBJECT		ipv6RouterAdvertRowStatus
    MIN-ACCESS	read-write
    DESCRIPTION
        "(U//FOUO) Implementation of this object can be as low
         as read-write depending on which
         IS Objective or MIB desired requirements are
         not being met by the implementation.
        "

    OBJECT		hIfv6BaseReachableTime
    MIN-ACCESS	read-write
    DESCRIPTION
        "(U//FOUO) Implementation of this object can be as low
         as read-write depending on which
         IS Objective or MIB desired requirements are
         not being met by the implementation.
        "

    OBJECT		hiaaType
    MIN-ACCESS	read-write
    DESCRIPTION
        "(U//FOUO) Implementation of this object can be as low
         as read-write depending on which
         IS Objective or MIB desired requirements are
         not being met by the implementation.
        "

    OBJECT		ipv6RouterAdvertMaxInterval
    MIN-ACCESS	read-write
    DESCRIPTION
        "(U//FOUO) Implementation of this object can be as low
         as read-write depending on which
         IS Objective or MIB desired requirements are
         not being met by the implementation.
        "

    OBJECT		ifIndex
    MIN-ACCESS	read-only
    DESCRIPTION
        "(U//FOUO) Implementation of this object can be as low
         as read-only depending on which
         IS Objective or MIB desired requirements are
         not being met by the implementation.
        "

    OBJECT		ipv6InterfaceEnableStatus
    MIN-ACCESS	read-only
    DESCRIPTION
        "(U//FOUO) Implementation of this object can be as low
         as read-only depending on which
         IS Objective or MIB desired requirements are
         not being met by the implementation.
        "

    OBJECT		hTPTransMapDestPTAddress
    MIN-ACCESS	read-write
    DESCRIPTION
        "(U//FOUO) Implementation of this object can be as low
         as read-write depending on which
         IS Objective or MIB desired requirements are
         not being met by the implementation.
        "

    OBJECT		ipAddressStorageType
    MIN-ACCESS	read-only
    DESCRIPTION
        "(U//FOUO) Implementation of this object can be as low
         as read-only depending on which
         IS Objective or MIB desired requirements are
         not being met by the implementation.
        "

    OBJECT		ipAddressStatus
    MIN-ACCESS	read-only
    DESCRIPTION
        "(U//FOUO) Implementation of this object can be as low
         as read-only depending on which
         IS Objective or MIB desired requirements are
         not being met by the implementation.
        "

    OBJECT		inetCidrRouteAge
    MIN-ACCESS	read-only
    DESCRIPTION
        "(U//FOUO) Implementation of this object can be as low
         as read-only depending on which
         IS Objective or MIB desired requirements are
         not being met by the implementation.
        "

    OBJECT		hIPhFFSAConnectionType
    MIN-ACCESS	read-write
    DESCRIPTION
        "(U//FOUO) Implementation of this object can be as low
         as read-write depending on which
         IS Objective or MIB desired requirements are
         not being met by the implementation.
        "

    OBJECT		hv6APAddressPrefixAdvValidLifetime
    MIN-ACCESS	read-write
    DESCRIPTION
        "(U//FOUO) Implementation of this object can be as low
         as read-write depending on which
         IS Objective or MIB desired requirements are
         not being met by the implementation.
        "

    OBJECT		hiaaPrefixLen
    MIN-ACCESS	read-write
    DESCRIPTION
        "(U//FOUO) Implementation of this object can be as low
         as read-write depending on which
         IS Objective or MIB desired requirements are
         not being met by the implementation.
        "

    OBJECT		hIGMPMode
    MIN-ACCESS	read-write
    DESCRIPTION
        "(U//FOUO) Implementation of this object can be as low
         as read-write depending on which
         IS Objective or MIB desired requirements are
         not being met by the implementation.
        "

    OBJECT		ifType
    MIN-ACCESS	read-only
    DESCRIPTION
        "(U//FOUO) Implementation of this object can be as low
         as read-only depending on which
         IS Objective or MIB desired requirements are
         not being met by the implementation.
        "

    OBJECT		ipv6RouterAdvertSpinLock
    MIN-ACCESS	not-accessible
    DESCRIPTION
        "(U//FOUO) Implementation of this object can be as low
         as not-accessible depending on which
         IS Objective or MIB desired requirements are
         not being met by the implementation.
        "

    OBJECT		ifPhysAddress
    MIN-ACCESS	read-only
    DESCRIPTION
        "(U//FOUO) Implementation of this object can be as low
         as read-only depending on which
         IS Objective or MIB desired requirements are
         not being met by the implementation.
        "

    OBJECT		hv6AddressPrefixTableLastChanged
    MIN-ACCESS	read-only
    DESCRIPTION
        "(U//FOUO) Implementation of this object can be as low
         as read-only depending on which
         IS Objective or MIB desired requirements are
         not being met by the implementation.
        "

    OBJECT		ifDescr
    MIN-ACCESS	read-only
    DESCRIPTION
        "(U//FOUO) Implementation of this object can be as low
         as read-only depending on which
         IS Objective or MIB desired requirements are
         not being met by the implementation.
        "

    OBJECT		ifConnectorPresent
    MIN-ACCESS	read-only
    DESCRIPTION
        "(U//FOUO) Implementation of this object can be as low
         as read-only depending on which
         IS Objective or MIB desired requirements are
         not being met by the implementation.
        "

    OBJECT		ipv6ScopeZoneIndexC
    MIN-ACCESS	read-only
    DESCRIPTION
        "(U//FOUO) Implementation of this object can be as low
         as read-only depending on which
         IS Objective or MIB desired requirements are
         not being met by the implementation.
        "

    OBJECT		ipAddressOrigin
    MIN-ACCESS	read-only
    DESCRIPTION
        "(U//FOUO) Implementation of this object can be as low
         as read-only depending on which
         IS Objective or MIB desired requirements are
         not being met by the implementation.
        "

    OBJECT		hIPhFFSADSCP
    MIN-ACCESS	read-write
    DESCRIPTION
        "(U//FOUO) Implementation of this object can be as low
         as read-write depending on which
         IS Objective or MIB desired requirements are
         not being met by the implementation.
        "

    OBJECT		ipv6ScopeZoneIndex7
    MIN-ACCESS	read-only
    DESCRIPTION
        "(U//FOUO) Implementation of this object can be as low
         as read-only depending on which
         IS Objective or MIB desired requirements are
         not being met by the implementation.
        "

    OBJECT		hIPhFFSAECN
    MIN-ACCESS	read-write
    DESCRIPTION
        "(U//FOUO) Implementation of this object can be as low
         as read-write depending on which
         IS Objective or MIB desired requirements are
         not being met by the implementation.
        "

    OBJECT		hIfv6PMTUResetPeriod
    MIN-ACCESS	not-accessible
    DESCRIPTION
        "(U//FOUO) Implementation of this object can be as low
         as not-accessible depending on which
         IS Objective or MIB desired requirements are
         not being met by the implementation.
        "

    OBJECT		ifSpeed
    MIN-ACCESS	read-only
    DESCRIPTION
        "(U//FOUO) Implementation of this object can be as low
         as read-only depending on which
         IS Objective or MIB desired requirements are
         not being met by the implementation.
        "

    OBJECT		ipv6RouterAdvertLinkMTU
    MIN-ACCESS	read-write
    DESCRIPTION
        "(U//FOUO) Implementation of this object can be as low
         as read-write depending on which
         IS Objective or MIB desired requirements are
         not being met by the implementation.
        "

    OBJECT		ifPromiscuousMode
    MIN-ACCESS	not-accessible
    DESCRIPTION
        "(U//FOUO) Implementation of this object can be as low
         as not-accessible depending on which
         IS Objective or MIB desired requirements are
         not being met by the implementation.
        "

    OBJECT		hTPTransportMapTableCount
    MIN-ACCESS	read-only
    DESCRIPTION
        "(U//FOUO) Implementation of this object can be as low
         as read-only depending on which
         IS Objective or MIB desired requirements are
         not being met by the implementation.
        "

    OBJECT		inetCidrRouteMetric5
    MIN-ACCESS	read-write
    DESCRIPTION
        "(U//FOUO) Implementation of this object can be as low
         as read-write depending on which
         IS Objective or MIB desired requirements are
         not being met by the implementation.
        "

    OBJECT		hIPhFFSADSCPValue
    MIN-ACCESS	read-write
    DESCRIPTION
        "(U//FOUO) Implementation of this object can be as low
         as read-write depending on which
         IS Objective or MIB desired requirements are
         not being met by the implementation.
        "

    OBJECT		hv6APRowStatus
    MIN-ACCESS	read-write
    DESCRIPTION
        "(U//FOUO) Implementation of this object can be as low
         as read-write depending on which
         IS Objective or MIB desired requirements are
         not being met by the implementation.
        "

    OBJECT		hTPTransMapRowStatus
    MIN-ACCESS	read-write
    DESCRIPTION
        "(U//FOUO) Implementation of this object can be as low
         as read-write depending on which
         IS Objective or MIB desired requirements are
         not being met by the implementation.
        "

    OBJECT		ipv6ScopeZoneIndexAdminLocal
    MIN-ACCESS	read-only
    DESCRIPTION
        "(U//FOUO) Implementation of this object can be as low
         as read-only depending on which
         IS Objective or MIB desired requirements are
         not being met by the implementation.
        "

    OBJECT		ipv6ScopeZoneIndex9
    MIN-ACCESS	read-only
    DESCRIPTION
        "(U//FOUO) Implementation of this object can be as low
         as read-only depending on which
         IS Objective or MIB desired requirements are
         not being met by the implementation.
        "

    OBJECT		ifOutMulticastPkts
    MIN-ACCESS	not-accessible
    DESCRIPTION
        "(U//FOUO) Implementation of this object can be as low
         as not-accessible depending on which
         IS Objective or MIB desired requirements are
         not being met by the implementation.
        "

    OBJECT		ipv6ScopeZoneIndex6
    MIN-ACCESS	read-only
    DESCRIPTION
        "(U//FOUO) Implementation of this object can be as low
         as read-only depending on which
         IS Objective or MIB desired requirements are
         not being met by the implementation.
        "

    OBJECT		hTPAddMapCTAddress
    MIN-ACCESS	read-write
    DESCRIPTION
        "(U//FOUO) Implementation of this object can be as low
         as read-write depending on which
         IS Objective or MIB desired requirements are
         not being met by the implementation.
        "

    OBJECT		hTPSADSCP
    MIN-ACCESS	read-write
    DESCRIPTION
        "(U//FOUO) Implementation of this object can be as low
         as read-write depending on which
         IS Objective or MIB desired requirements are
         not being met by the implementation.
        "

    OBJECT		hv6APLastChanged
    MIN-ACCESS	read-only
    DESCRIPTION
        "(U//FOUO) Implementation of this object can be as low
         as read-only depending on which
         IS Objective or MIB desired requirements are
         not being met by the implementation.
        "

    OBJECT		ifInBroadcastPkts
    MIN-ACCESS	not-accessible
    DESCRIPTION
        "(U//FOUO) Implementation of this object can be as low
         as not-accessible depending on which
         IS Objective or MIB desired requirements are
         not being met by the implementation.
        "

    OBJECT		ifHCInUcastPkts
    MIN-ACCESS	not-accessible
    DESCRIPTION
        "(U//FOUO) Implementation of this object can be as low
         as not-accessible depending on which
         IS Objective or MIB desired requirements are
         not being met by the implementation.
        "

    OBJECT		hTPSAECN
    MIN-ACCESS	read-write
    DESCRIPTION
        "(U//FOUO) Implementation of this object can be as low
         as read-write depending on which
         IS Objective or MIB desired requirements are
         not being met by the implementation.
        "

    OBJECT		hTPAddMapRowStatus
    MIN-ACCESS	read-write
    DESCRIPTION
        "(U//FOUO) Implementation of this object can be as low
         as read-write depending on which
         IS Objective or MIB desired requirements are
         not being met by the implementation.
        "

    OBJECT		ipv6InterfaceReasmMaxSize
    MIN-ACCESS	read-only
    DESCRIPTION
        "(U//FOUO) Implementation of this object can be as low
         as read-only depending on which
         IS Objective or MIB desired requirements are
         not being met by the implementation.
        "

    OBJECT		hIfv6RetransmitTime
    MIN-ACCESS	read-write
    DESCRIPTION
        "(U//FOUO) Implementation of this object can be as low
         as read-write depending on which
         IS Objective or MIB desired requirements are
         not being met by the implementation.
        "

    OBJECT		hTPSADFBit
    MIN-ACCESS	read-write
    DESCRIPTION
        "(U//FOUO) Implementation of this object can be as low
         as read-write depending on which
         IS Objective or MIB desired requirements are
         not being met by the implementation.
        "

    OBJECT		ifCounterDiscontinuityTime
    MIN-ACCESS	not-accessible
    DESCRIPTION
        "(U//FOUO) Implementation of this object can be as low
         as not-accessible depending on which
         IS Objective or MIB desired requirements are
         not being met by the implementation.
        "

    OBJECT		hIfv6LowPMTUThreshold
    MIN-ACCESS	not-accessible
    DESCRIPTION
        "(U//FOUO) Implementation of this object can be as low
         as not-accessible depending on which
         IS Objective or MIB desired requirements are
         not being met by the implementation.
        "

    OBJECT		ifHCOutMulticastPkts
    MIN-ACCESS	not-accessible
    DESCRIPTION
        "(U//FOUO) Implementation of this object can be as low
         as not-accessible depending on which
         IS Objective or MIB desired requirements are
         not being met by the implementation.
        "

    OBJECT		inetCidrRouteNextHopAS
    MIN-ACCESS	read-write
    DESCRIPTION
        "(U//FOUO) Implementation of this object can be as low
         as read-write depending on which
         IS Objective or MIB desired requirements are
         not being met by the implementation.
        "

    OBJECT		hIfv6RouterSolicitation
    MIN-ACCESS	read-write
    DESCRIPTION
        "(U//FOUO) Implementation of this object can be as low
         as read-write depending on which
         IS Objective or MIB desired requirements are
         not being met by the implementation.
        "

    OBJECT		hiaaAddress
    MIN-ACCESS	read-write
    DESCRIPTION
        "(U//FOUO) Implementation of this object can be as low
         as read-write depending on which
         IS Objective or MIB desired requirements are
         not being met by the implementation.
        "

    OBJECT		hTPTransMapSourcePTAddress
    MIN-ACCESS	read-write
    DESCRIPTION
        "(U//FOUO) Implementation of this object can be as low
         as read-write depending on which
         IS Objective or MIB desired requirements are
         not being met by the implementation.
        "

    OBJECT		hIfv6Side
    MIN-ACCESS	read-only
    DESCRIPTION
        "(U//FOUO) Implementation of this object can be as low
         as read-only depending on which
         IS Objective or MIB desired requirements are
         not being met by the implementation.
        "

    OBJECT		hTPAddMapLastChanged
    MIN-ACCESS	read-only
    DESCRIPTION
        "(U//FOUO) Implementation of this object can be as low
         as read-only depending on which
         IS Objective or MIB desired requirements are
         not being met by the implementation.
        "

    OBJECT		ipAddressLastChanged
    MIN-ACCESS	read-only
    DESCRIPTION
        "(U//FOUO) Implementation of this object can be as low
         as read-only depending on which
         IS Objective or MIB desired requirements are
         not being met by the implementation.
        "

    OBJECT		ipAddressRowStatus
    MIN-ACCESS	read-only
    DESCRIPTION
        "(U//FOUO) Implementation of this object can be as low
         as read-only depending on which
         IS Objective or MIB desired requirements are
         not being met by the implementation.
        "

    OBJECT		ipAddressType
    MIN-ACCESS	read-only
    DESCRIPTION
        "(U//FOUO) Implementation of this object can be as low
         as read-only depending on which
         IS Objective or MIB desired requirements are
         not being met by the implementation.
        "

    OBJECT		inetCidrRouteMetric4
    MIN-ACCESS	read-write
    DESCRIPTION
        "(U//FOUO) Implementation of this object can be as low
         as read-write depending on which
         IS Objective or MIB desired requirements are
         not being met by the implementation.
        "

    OBJECT		ipv6InterfaceIdentifier
    MIN-ACCESS	read-only
    DESCRIPTION
        "(U//FOUO) Implementation of this object can be as low
         as read-only depending on which
         IS Objective or MIB desired requirements are
         not being met by the implementation.
        "

    OBJECT		ifNumber
    MIN-ACCESS	read-only
    DESCRIPTION
        "(U//FOUO) Implementation of this object can be as low
         as read-only depending on which
         IS Objective or MIB desired requirements are
         not being met by the implementation.
        "

    OBJECT		ifName
    MIN-ACCESS	read-only
    DESCRIPTION
        "(U//FOUO) Implementation of this object can be as low
         as read-only depending on which
         IS Objective or MIB desired requirements are
         not being met by the implementation.
        "

    OBJECT		ifOutBroadcastPkts
    MIN-ACCESS	not-accessible
    DESCRIPTION
        "(U//FOUO) Implementation of this object can be as low
         as not-accessible depending on which
         IS Objective or MIB desired requirements are
         not being met by the implementation.
        "

    OBJECT		hv6APAddressPrefixAutonomousFlag
    MIN-ACCESS	read-write
    DESCRIPTION
        "(U//FOUO) Implementation of this object can be as low
         as read-write depending on which
         IS Objective or MIB desired requirements are
         not being met by the implementation.
        "

    OBJECT		ipv6RouterAdvertMinInterval
    MIN-ACCESS	read-write
    DESCRIPTION
        "(U//FOUO) Implementation of this object can be as low
         as read-write depending on which
         IS Objective or MIB desired requirements are
         not being met by the implementation.
        "

    OBJECT		hIfv6UseDepAddress
    MIN-ACCESS	read-write
    DESCRIPTION
        "(U//FOUO) Implementation of this object can be as low
         as read-write depending on which
         IS Objective or MIB desired requirements are
         not being met by the implementation.
        "

    OBJECT		ipv6ScopeZoneIndex3
    MIN-ACCESS	read-only
    DESCRIPTION
        "(U//FOUO) Implementation of this object can be as low
         as read-only depending on which
         IS Objective or MIB desired requirements are
         not being met by the implementation.
        "

    OBJECT		hIfv6ReachableTime
    MIN-ACCESS	read-only
    DESCRIPTION
        "(U//FOUO) Implementation of this object can be as low
         as read-only depending on which
         IS Objective or MIB desired requirements are
         not being met by the implementation.
        "

    OBJECT		inetCidrRouteType
    MIN-ACCESS	read-write
    DESCRIPTION
        "(U//FOUO) Implementation of this object can be as low
         as read-write depending on which
         IS Objective or MIB desired requirements are
         not being met by the implementation.
        "

    OBJECT		inetCidrRouteIfIndex
    MIN-ACCESS	read-write
    DESCRIPTION
        "(U//FOUO) Implementation of this object can be as low
         as read-write depending on which
         IS Objective or MIB desired requirements are
         not being met by the implementation.
        "

    OBJECT		ifAdminStatus
    MIN-ACCESS	read-write
    DESCRIPTION
        "(U//FOUO) Implementation of this object can be as low
         as read-write depending on which
         IS Objective or MIB desired requirements are
         not being met by the implementation.
        "

    OBJECT		ifHCInMulticastPkts
    MIN-ACCESS	not-accessible
    DESCRIPTION
        "(U//FOUO) Implementation of this object can be as low
         as not-accessible depending on which
         IS Objective or MIB desired requirements are
         not being met by the implementation.
        "

    OBJECT		hIfv6NextHeaderSkipList
    MIN-ACCESS	read-only
    DESCRIPTION
        "(U//FOUO) Implementation of this object can be as low
         as read-only depending on which
         IS Objective or MIB desired requirements are
         not being met by the implementation.
        "

    OBJECT		hTPTransMapLastChanged
    MIN-ACCESS	read-only
    DESCRIPTION
        "(U//FOUO) Implementation of this object can be as low
         as read-only depending on which
         IS Objective or MIB desired requirements are
         not being met by the implementation.
        "

    OBJECT		inetCidrRouteMetric2
    MIN-ACCESS	read-write
    DESCRIPTION
        "(U//FOUO) Implementation of this object can be as low
         as read-write depending on which
         IS Objective or MIB desired requirements are
         not being met by the implementation.
        "

    OBJECT		ipv6RouterAdvertOtherConfigFlag
    MIN-ACCESS	read-write
    DESCRIPTION
        "(U//FOUO) Implementation of this object can be as low
         as read-write depending on which
         IS Objective or MIB desired requirements are
         not being met by the implementation.
        "

    OBJECT		ipAddressPrefix
    MIN-ACCESS	read-only
    DESCRIPTION
        "(U//FOUO) Implementation of this object can be as low
         as read-only depending on which
         IS Objective or MIB desired requirements are
         not being met by the implementation.
        "

    OBJECT		ipv6ScopeZoneIndexD
    MIN-ACCESS	read-only
    DESCRIPTION
        "(U//FOUO) Implementation of this object can be as low
         as read-only depending on which
         IS Objective or MIB desired requirements are
         not being met by the implementation.
        "

    OBJECT		ipv6RouterAdvertRetransmitTime
    MIN-ACCESS	read-write
    DESCRIPTION
        "(U//FOUO) Implementation of this object can be as low
         as read-write depending on which
         IS Objective or MIB desired requirements are
         not being met by the implementation.
        "

    OBJECT		ipv6RouterAdvertSendAdverts
    MIN-ACCESS	read-write
    DESCRIPTION
        "(U//FOUO) Implementation of this object can be as low
         as read-write depending on which
         IS Objective or MIB desired requirements are
         not being met by the implementation.
        "

    OBJECT		inetCidrRouteDiscards
    MIN-ACCESS	not-accessible
    DESCRIPTION
        "(U//FOUO) Implementation of this object can be as low
         as not-accessible depending on which
         IS Objective or MIB desired requirements are
         not being met by the implementation.
        "

    OBJECT		hv6APAdvertisePrefix
    MIN-ACCESS	read-write
    DESCRIPTION
        "(U//FOUO) Implementation of this object can be as low
         as read-write depending on which
         IS Objective or MIB desired requirements are
         not being met by the implementation.
        "

    OBJECT		ipAddressCreated
    MIN-ACCESS	read-only
    DESCRIPTION
        "(U//FOUO) Implementation of this object can be as low
         as read-only depending on which
         IS Objective or MIB desired requirements are
         not being met by the implementation.
        "

    OBJECT		hIfv6HopLimit
    MIN-ACCESS	read-only
    DESCRIPTION
        "(U//FOUO) Implementation of this object can be as low
         as read-only depending on which
         IS Objective or MIB desired requirements are
         not being met by the implementation.
        "

    OBJECT		hIfv6MTU
    MIN-ACCESS	read-write
    DESCRIPTION
        "(U//FOUO) Implementation of this object can be as low
         as read-write depending on which
         IS Objective or MIB desired requirements are
         not being met by the implementation.
        "

    OBJECT		ifInMulticastPkts
    MIN-ACCESS	not-accessible
    DESCRIPTION
        "(U//FOUO) Implementation of this object can be as low
         as not-accessible depending on which
         IS Objective or MIB desired requirements are
         not being met by the implementation.
        "

    OBJECT		ifHCInOctets
    MIN-ACCESS	not-accessible
    DESCRIPTION
        "(U//FOUO) Implementation of this object can be as low
         as not-accessible depending on which
         IS Objective or MIB desired requirements are
         not being met by the implementation.
        "

    OBJECT		ipv6ScopeZoneIndexOrganizationLocal
    MIN-ACCESS	read-only
    DESCRIPTION
        "(U//FOUO) Implementation of this object can be as low
         as read-only depending on which
         IS Objective or MIB desired requirements are
         not being met by the implementation.
        "

    OBJECT		hv6APAddressPrefixAdvPreferredLifetime
    MIN-ACCESS	read-write
    DESCRIPTION
        "(U//FOUO) Implementation of this object can be as low
         as read-write depending on which
         IS Objective or MIB desired requirements are
         not being met by the implementation.
        "

    OBJECT		hv6APAddressPrefixOnLinkFlag
    MIN-ACCESS	read-write
    DESCRIPTION
        "(U//FOUO) Implementation of this object can be as low
         as read-write depending on which
         IS Objective or MIB desired requirements are
         not being met by the implementation.
        "

    OBJECT		hIfv6AddressAutoConfig
    MIN-ACCESS	read-write
    DESCRIPTION
        "(U//FOUO) Implementation of this object can be as low
         as read-write depending on which
         IS Objective or MIB desired requirements are
         not being met by the implementation.
        "

    OBJECT		inetCidrRouteMetric3
    MIN-ACCESS	read-write
    DESCRIPTION
        "(U//FOUO) Implementation of this object can be as low
         as read-write depending on which
         IS Objective or MIB desired requirements are
         not being met by the implementation.
        "

    OBJECT		ipv6ScopeZoneIndexB
    MIN-ACCESS	read-only
    DESCRIPTION
        "(U//FOUO) Implementation of this object can be as low
         as read-only depending on which
         IS Objective or MIB desired requirements are
         not being met by the implementation.
        "

    OBJECT		hv6AddressPrefixTableCount
    MIN-ACCESS	read-only
    DESCRIPTION
        "(U//FOUO) Implementation of this object can be as low
         as read-only depending on which
         IS Objective or MIB desired requirements are
         not being met by the implementation.
        "

    OBJECT		ifHighSpeed
    MIN-ACCESS	read-only
    DESCRIPTION
        "(U//FOUO) Implementation of this object can be as low
         as read-only depending on which
         IS Objective or MIB desired requirements are
         not being met by the implementation.
        "

    OBJECT		hiaaInterface
    MIN-ACCESS	read-write
    DESCRIPTION
        "(U//FOUO) Implementation of this object can be as low
         as read-write depending on which
         IS Objective or MIB desired requirements are
         not being met by the implementation.
        "

    OBJECT		hIfv6DiscardUnauthRed
    MIN-ACCESS	read-only
    DESCRIPTION
        "(U//FOUO) Implementation of this object can be as low
         as read-only depending on which
         IS Objective or MIB desired requirements are
         not being met by the implementation.
        "

    OBJECT		hiaaRowStatus
    MIN-ACCESS	read-write
    DESCRIPTION
        "(U//FOUO) Implementation of this object can be as low
         as read-write depending on which
         IS Objective or MIB desired requirements are
         not being met by the implementation.
        "

    OBJECT		hIfv6LastChanged
    MIN-ACCESS	read-only
    DESCRIPTION
        "(U//FOUO) Implementation of this object can be as low
         as read-only depending on which
         IS Objective or MIB desired requirements are
         not being met by the implementation.
        "
::= { haipeV030102Conformance 10 }

END
