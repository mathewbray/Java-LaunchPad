--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-V4-MANAGEMENT-MIB  DEFINITIONS  ::= BEGIN

IMPORTS
    hv4Management                       FROM HAIPE-V4-FEATURE-HIERARCHY-MIB
    OBJECT-TYPE, Unsigned32, Integer32,
    MODULE-IDENTITY, TimeTicks          FROM SNMPv2-SMI
    SnmpAdminString                     FROM SNMP-FRAMEWORK-MIB
    RowStatus, TruthValue, DateAndTime,
    TimeStamp, TestAndIncr              FROM SNMPv2-TC
    IPAddress,
    HaipeStationID, HaipeShortTitle64,
    HaipeDeviceSide                     FROM HAIPE-V4-TEXTUAL-CONVENTIONS-MIB;

haipev4ManagementMIB MODULE-IDENTITY
    LAST-UPDATED "201006231600Z"
    ORGANIZATION "HAIPE PO"
    CONTACT-INFO
        "(U//FOUO) Not Available"
    DESCRIPTION
        "(U//FOUO) This MIB defines the HAIPE management MIB objects."
    REVISION     "201006231600Z"
    DESCRIPTION  "(U//FOUO) MIB 4.1.0 FINAL Release"		
    ::= { hv4Management 1 }

hManagementControlObjects     OBJECT IDENTIFIER ::= { haipev4ManagementMIB 1 }
hManagementGlobalScalars      OBJECT IDENTIFIER ::= { haipev4ManagementMIB 2 }

hHMI                          OBJECT IDENTIFIER ::= { haipev4ManagementMIB 3 }
hDeviceVersInformation        OBJECT IDENTIFIER ::= { hHMI 1 }
hFirmwareDownloadInformation  OBJECT IDENTIFIER ::= { hHMI 2 }
hFwKeys                       OBJECT IDENTIFIER ::= { hHMI 3 }

hKeyTransferNotifications     OBJECT IDENTIFIER ::= { haipev4ManagementMIB 4 }

-- **********************************************************************
-- Management Control Objects
-- **********************************************************************

hResetDevice OBJECT-TYPE
    SYNTAX     TruthValue
    MAX-ACCESS read-write
    STATUS     current
    DESCRIPTION
        "(U//FOUO) The indication of whether a device should be reset.  
	 Setting this object to 'true' will perform a reset operation 
	 of the device. This must not affect the state of any 
	 persistent configuration data, zeroize any of the key 
	 material or raw strings used to generate key material, or erase 
	 the audit log.  When read this object should return false.  
	 When set to false this object must not perform any operation 
	 but should accept this as a valid SET operation."
    ::= { hManagementControlObjects 1 }

hSanitizeDevice OBJECT-TYPE
    SYNTAX     TruthValue
    MAX-ACCESS read-write
    STATUS     current
    DESCRIPTION
        "(U//FOUO) The indication of whether persistent data should be 
	 erased. Setting this object to 'true' will erase all 
	 persistent data and return the box to an unitialized state. 
	 It will zeroize all keying data, all user entered raw strings 
	 used to generate keying material, and erase all persistent 
	 storage and auditing information. Setting this object will 
	 certainly render the HAIPE unreachable from distant managers 
	 since it will be unconfigured. When read this object should 
	 return false. When set to false this object must not perform 
	 any operation but should accept this as a valid SET operation."
    ::= { hManagementControlObjects 2 }

hZeroizeAllKeysAndAlgorithms OBJECT-TYPE
    SYNTAX     TruthValue
    MAX-ACCESS read-write
    STATUS     current
    DESCRIPTION
        "(U//FOUO) Setting this object to 'true' will zeroize all the 
	 keys and sensitive crypto information within the device, 
	 including the raw strings used to generate keying material. If 
	 this object is set to the same value as the current value, 
	 the device must not perform any operation but should accept 
	 this as a valid SET operation."
    ::= { hManagementControlObjects 3 }

-- **********************************************************************
-- Management Global Scalars
-- **********************************************************************

hStationIdentifier OBJECT-TYPE
    SYNTAX     HaipeStationID
    MAX-ACCESS read-only
    STATUS     current
    DESCRIPTION
        "(U//FOUO) The ASCII-encoded HAIPE IS station identifier of this HAIPE
         device.

         (U//FOUO) Note, this column must use the format specified in
         0N716929. Lastly, this object is not required to match the chassis serial
         number of this device."
    ::= { hManagementGlobalScalars 1 }

hSystemDate OBJECT-TYPE
    SYNTAX     DateAndTime
    MAX-ACCESS read-write
    STATUS     current
    DESCRIPTION
        "(U//FOUO) The host's notion of the local date and time."
    ::= { hManagementGlobalScalars 2 }

hSystemUpTime OBJECT-TYPE
    SYNTAX     TimeTicks
    MAX-ACCESS read-only
    STATUS     current
    DESCRIPTION
        "(U//FOUO) The time (in hundredths of a second) since the network
         management portion of the system was last re-initialized. This value is
         used to derive all Last Changed scalars."
    ::= { hManagementGlobalScalars 3 }

hObjectLastChanged OBJECT-TYPE
    SYNTAX     TimeStamp
    MAX-ACCESS read-only
    STATUS     current
    DESCRIPTION
        "(U//FOUO) The value of hSystemUpTime the last time any configurable object
         within the MIBs supported by the HAIPE has been modified by either SNMP
         or any other management method (e.g., via an HMI).

         (U//FOUO) Managers can use this object to ensure that no changes to
         any configuration within the device have happened since the last time
         it examined the device.

         (U//FOUO) A value of 0 indicates that no objects have been changed since
         the agent initialized."
    ::= { hManagementGlobalScalars 4 }

hTFTPDesiredBlkSize OBJECT-TYPE
    SYNTAX     Unsigned32 (8..65464)
    MAX-ACCESS read-write
    STATUS     current
    DESCRIPTION
        "(U//FOUO) The desired block size in octets to use for TFTP.
        
        (U//FOUO) It is recommended that a default value of 512 is 
        used for this object." 
    ::= { hManagementGlobalScalars 5 }

hTFTPDesiredTimeout OBJECT-TYPE
    SYNTAX     Unsigned32 (1..255)
    MAX-ACCESS read-write
    STATUS     current
    DESCRIPTION
        "(U//FOUO) The desired timeout interval, in seconds, to be 
        used for TFTP. 

        (U//FOUO) It is recommended that a default value of 5 is used 
        for this object." 
    ::= { hManagementGlobalScalars 6 }

hFirmwareDwnldAdminStatus OBJECT-TYPE
    SYNTAX     INTEGER { downloadFirmware(1), downloadAndInstall(2),
                         installFirmware(3), discardDownload(4),
                         allowFirmwareDownloadAction(5) }
    MAX-ACCESS read-write
    STATUS     current
    DESCRIPTION
        "(U//FOUO) This scalar controls the firmware download process. When
         read, it will return allowFirmwareDownloadAction if the last action
         succeeded, or the last requested action, if an action failed or is
         still in progress. The value discardDownload will never be returned, as
         that action should always succeed immediately.

         (U//FOUO) The values which may be set depend on the current value of
         this object and the hFirmwareDwnldStatus object.

         (U//FOUO) To initiate a new download, this object must contain the
         value allowFirmwareDownloadAction, and the hFirmwareDwnldStatus must
         be completeFromMgt. If the requested action is downloadFirmware or
         downloadAndInstall, the hFirmwareDwnldStatus should transition to
         inProgress and the HAIPE will begin the process of attempting to
         transfer a firmware image from the servers listed in the
         hFwDwnldServersTable. The servers are ordered in this table,
         and the transfer attempts will continue based off the priority field
         until a download succeeds or all servers have been tried. A lower
         value in the priority field indicates a higher preference.

         (U//FOUO) While a download is in progress, or if the download fails
         (indicated by a hFirmwareDwnldStatus value of downloadFailed), this
         object will return an inconsistentValue error for any new value except
         discardDownload (which will cancel the current download). If the
         download fails, this object must be set to discardDownload before a
         new download or install may be attempted.

         (U//FOUO) If the download succeeded and the requested action was
         downloadFirmware, the hFirmwareDwnldStatus value transitions to
         downloadedFirmware and any new value other than installFirmware or
         discardDownload will return an inconsistentValue error.

         (U//FOUO) If the download succeeded and the requested action was
         downloadAndInstall, the hFirmwareDwnldStatus value remains inProgress
         and the device attempts to install the firmware immediately.

         (U//FOUO) While the firmware is being installed, all new values will
         return inconsistentValue error (i.e. the install process can not be
         aborted). If the install fails, the hFirmwareDwnldStatus will
         transition to installFailed, and this object must be set to
         discardDownload before a new download or install may be attempted.
         During the installation process the HAIPE will likely need to change
         states in such a way as to prevent communication with the manager.

         (U//FOUO) A summary of allowed values, based on the value of
         hFirmwareDwnldStatus, is included in the description of the
         hFirmwareDwnldStatus object."
    ::= { hManagementGlobalScalars 7 }

hFirmwareDwnldStatus OBJECT-TYPE
    SYNTAX     INTEGER { inProgress(1), downloadedFirmware(2),
                         completeFromMgt(3), downloadFailed(4),
                         installFailed(5) }
    MAX-ACCESS read-only
    STATUS     current
    DESCRIPTION
        "(U//FOUO) This scalar indicates the current state of a firmware
         download.

         (U//FOUO) [inProgress] indicates that a download is underway, or new
         firmware image is being installed.

         (U//FOUO) [downloadedFirmare] indicates that a download was successful
         but it has not yet been installed.

         (U//FOUO) [completeFromMgt] indicates that the last requested firmware
         action was sucessful.

         (U//FOUO) [downloadFailed] indicates that the last attempted download
         failed.

         (U//FOUO) [installFailed] indicates that the installation of an
         image failed."
    ::= { hManagementGlobalScalars 8 }

-- **********************************************************************
-- Device Version Information
-- **********************************************************************

-- =========
-- Device Version Table
-- =========

hDeviceVersTableCount OBJECT-TYPE
    SYNTAX     Unsigned32
    MAX-ACCESS read-only
    STATUS     current
    DESCRIPTION
        "(U//FOUO) The number of rows in the hDeviceVersTable."
    ::= { hDeviceVersInformation 1 }

hDeviceVersTableLastChanged OBJECT-TYPE
    SYNTAX     TimeStamp
    MAX-ACCESS read-only
    STATUS     current
    DESCRIPTION
        "(U//FOUO) The value of hSystemUpTime the last time any entry in the
         hDeviceVersTable was modified, created, or deleted by either SNMP or
         other management method (e.g. via an HMI).

         (U//FOUO) Managers can use this object to ensure that no changes to
         configuration of this table have happened since the last time it
         examined the table.

         (U//FOUO) A value of 0 indicates that no entry has been changed since
         the agent initialized."
    ::= { hDeviceVersInformation 2 }

hDeviceVersTable OBJECT-TYPE
    SYNTAX     SEQUENCE OF HDeviceVersTableEntry
    MAX-ACCESS not-accessible
    STATUS     current
    DESCRIPTION
        "(U//FOUO) The table containing a description of the specification
         versions of components or specifications supported by the HAIPE. Note
         that it is possible for multiple versions of a given specification to
         be registered within the table."
    ::= { hDeviceVersInformation 3 }

hDeviceVersTableEntry OBJECT-TYPE
    SYNTAX     HDeviceVersTableEntry
    MAX-ACCESS not-accessible
    STATUS     current
    DESCRIPTION
        "(U//FOUO) A row containing a module descriptive name and its
         version that is in current use by this device."
    INDEX  { hDvName, hDvVersion }
    ::= { hDeviceVersTable 1 }

HDeviceVersTableEntry ::= SEQUENCE
{
   hDvName                         SnmpAdminString,
   hDvVersion                      SnmpAdminString,
   hDvRowStatus                    RowStatus
}

hDvName OBJECT-TYPE
    SYNTAX     SnmpAdminString (SIZE(1..32))
    MAX-ACCESS not-accessible
    STATUS     current
    DESCRIPTION
        "(U//FOUO) The module name or specification name. The string value to
         be used in this field should be documented in the text of the
         specification a given row is reporting information on.

         (U//FOUO) Specification names beginning with a prefix of 'vendor-' are
         reserved for private use by the vendor of the device.

         (U//FOUO) The string 'device' (exact) is reserved for vendors to
         register a software revision version of the device.

         (U//FOUO) The string 'hardware' (exact) is reserved for vendors to
         register a model number of the hardware of the HAIPE.

         (U//FOUO) For HAIPE IS features, the hDvName legal values 
         are: Core, LegacyESP, GenericDiscoveryClient, 
         LegacyDiscovery, Reachability, RemoteProvisioning, 
         RemoteProvisioningAuthority, RemoteConfigurationMonitoring, 
         IMPEPD, Gateway, AutomatedSA, AutomatedSA-IKEv2, 
         BandwidthManagement, and HeaderCompression.

         (U//FOUO) All other prefix strings are reserved for use by the NSA."
    ::= { hDeviceVersTableEntry 1 }

hDvVersion OBJECT-TYPE
    SYNTAX     SnmpAdminString (SIZE(1..32))
    MAX-ACCESS not-accessible
    STATUS     current
    DESCRIPTION
        "(U//FOUO) The version of the specification or component name listed
         in the hDvName object field in this row. The string value to be used
         in this field should be documented in the text of a specification, of
         the device, or elsewhere.  If the hDvName begins with a 'vendor-'
         prefix, the format of this field is vendor specific.

         (U//FOUO) For HAIPE IS extensions, the three digit extension number
         must be used. For example, 4.0.0."
    ::= { hDeviceVersTableEntry 2 }

hDvRowStatus OBJECT-TYPE
    SYNTAX     RowStatus
    MAX-ACCESS read-write
    STATUS     current
    DESCRIPTION
        "(U//FOUO) The status of this row by which existing entries can be
         viewed or set to a status of notReady or notInService.

         (U//FOUO) All entries in this able are static entries that are  
         managed by the agent; a user is not allowed to create or destroy 
         entries in this table.

         (U//FOUO) At a minimum, implementations must support the enumeration
         value of active. Support for notInService and notReady management
         functions is optional. Implementations must not support 
         createAndWait, createAndGo, and destroy management functions for 
         this object."  
    ::= { hDeviceVersTableEntry 3 }


-- **********************************************************************
-- Firmware Download Information
-- **********************************************************************

-- =========
-- Firmware Download Servers Table
-- =========

hFwDwnldServerTableCount OBJECT-TYPE
    SYNTAX     Unsigned32
    MAX-ACCESS read-only
    STATUS     current
    DESCRIPTION
        "(U//FOUO) The number of rows in the hFirmwareDwnldServerTable."
    ::= { hFirmwareDownloadInformation 1 }

hFwDwnldServerTableLastChanged OBJECT-TYPE
    SYNTAX     TimeStamp
    MAX-ACCESS read-only
    STATUS     current
    DESCRIPTION
        "(U//FOUO) The value of hSystemUpTime the last time any entry in the
         hFirmwareDwnldServerTable was modified, created, or deleted by either
         SNMP or other management method (e.g. via an HMI).

         (U//FOUO) Managers can use this object to ensure that no changes to
         configuration of this table have happened since the last time it
         examined the table.

         (U//FOUO) A value of 0 indicates that no entry has been changed since
         the agent initialized."
    ::= { hFirmwareDownloadInformation 2 }

hFwDwnldServerTable OBJECT-TYPE
    SYNTAX     SEQUENCE OF HFwDwnldServerTableEntry
    MAX-ACCESS not-accessible
    STATUS     current
    DESCRIPTION
        "(U//FOUO) The table containing configuration information about
         firmware download servers. Firmware Download servers are listed in
         this table in a prioritized manner: the lower the priority being the
         most preferred."
    ::= { hFirmwareDownloadInformation 3 }

hFwDwnldServerTableEntry OBJECT-TYPE
    SYNTAX     HFwDwnldServerTableEntry
    MAX-ACCESS not-accessible
    STATUS     current
    DESCRIPTION
        "(U//FOUO) A row describing the particular information associated with
         a firmware download server."
    INDEX  { hFwDwnldServerPriority }
    ::= { hFwDwnldServerTable 1 }

HFwDwnldServerTableEntry ::= SEQUENCE
{
    hFwDwnldServerPriority                    Unsigned32,
    hFwDwnldServerURI                         SnmpAdminString,
    hFwDwnldServerSide                        HaipeDeviceSide,
    hFwDwnldServerRowStatus                   RowStatus
}

hFwDwnldServerPriority OBJECT-TYPE
    SYNTAX      Unsigned32
    MAX-ACCESS  not-accessible
    STATUS      current
    DESCRIPTION
        "(U//FOUO) A unique numeric index that identifies the firmware
         download server.

         (U//FOUO) This column is also used to administratively assign the 
         priority level of the given server. Servers with a lower priority     
         level should be used first when attempting a new firmware download."
    ::= { hFwDwnldServerTableEntry 1 }

hFwDwnldServerURI OBJECT-TYPE
    SYNTAX     SnmpAdminString
    MAX-ACCESS read-create
    STATUS     current
    DESCRIPTION
        "(U//FOUO) The URI to indicate a download server or path from which to 
         pull a firmware image from.

         (U//FOUO) It is important to note that devices may or may not support
         DNS name resolution and thus some devices may only support URIs
         containing IP addresses.

         (U//FOUO) It is also important to note that some protocols may be
         restricted in the size of the URI they can handle, in which case a
         wrongValue exception should be returned when an illegally long URI is
         requested."
    ::= { hFwDwnldServerTableEntry 2 }

hFwDwnldServerSide OBJECT-TYPE
    SYNTAX      HaipeDeviceSide
    MAX-ACCESS  read-create
    STATUS      current
    DESCRIPTION 
        "(U//FOUO) The network side the hFwDwnldServerURI exists in. 
        
         (1) CT: The cipher-text side, where encrypted traffic is 
         generally sent and received.

         (2) PT: The plain-text side. Note this could be a local or
         remote PT network. 

         (3) other: An interface that isn't responsible for
         processing traffic between networks, e.g., a management
         interface or some other secondary interface." 
    ::= { hFwDwnldServerTableEntry 3 }    
    
hFwDwnldServerRowStatus OBJECT-TYPE
    SYNTAX     RowStatus
    MAX-ACCESS read-create
    STATUS     current
    DESCRIPTION
        "(U//FOUO) The status of the row, by which new entries may be created,
         or old entries deleted from this table.

         (U//FOUO) Entries created within this table may not become active 
         unless all read-create columns in this table have valid values, as 
         detailed by each individual column's description.

         (U//FOUO) At a minimum, implementations must support createAndGo and
         destroy management functions. Support for createAndWait, active,
         notInService, and notReady management functions is optional."
    ::= { hFwDwnldServerTableEntry 4 }


-- **********************************************************************
-- Firmware Download Keys
-- **********************************************************************

-- =========
-- Firmware Keys Table
-- =========

hFwKeysTableCount OBJECT-TYPE
        SYNTAX      Unsigned32
        MAX-ACCESS  read-only
        STATUS      current
        DESCRIPTION
            "(U//FOUO) The number of rows in the hFwKeysTable."
        ::= { hFwKeys 1 }

hFwKeysTableLastChanged OBJECT-TYPE
        SYNTAX      TimeStamp
        MAX-ACCESS  read-only
        STATUS      current
        DESCRIPTION
            "(U//FOUO) The value of hSystemUpTime is the last time any entry in
            the hFwKeysTable was created or deleted by either SNMP
            or other management method (e.g., via an HMI).

            (U//FOUO) Managers can use this object to ensure that no
            changes to configuration of this table have happened since
            the last time it examined the table.

            (U//FOUO) A value of 0 indicates that no entry has been
            changed since the agent initialized."
        ::= { hFwKeys 2 }

hFwKeysTable OBJECT-TYPE
        SYNTAX      SEQUENCE OF HFwKeysEntry
        MAX-ACCESS  not-accessible
        STATUS      current
        DESCRIPTION
            "(U//FOUO) The table containing information used to
            validate firmware downloads."
        ::= { hFwKeys 3 }

hFwKeysEntry OBJECT-TYPE
        SYNTAX      HFwKeysEntry
        MAX-ACCESS  not-accessible
        STATUS      current
        DESCRIPTION
            "(U//FOUO) A row containing parameters related to the
            keys used to validate a firmware download."
        INDEX   { hFwKeysKMID }
        ::= { hFwKeysTable 1 }

HFwKeysEntry ::= SEQUENCE
    {
        hFwKeysKMID                OCTET STRING,
        hFwKeysAppVer              HaipeShortTitle64
    }

hFwKeysKMID OBJECT-TYPE
    SYNTAX      OCTET STRING (SIZE(6))
    MAX-ACCESS  not-accessible
    STATUS      current
    DESCRIPTION
        "(U//FOUO) The tag (KMID) of S1 CSC."
    ::= { hFwKeysEntry 1 }

hFwKeysAppVer OBJECT-TYPE
    SYNTAX      HaipeShortTitle64
    MAX-ACCESS  read-only
    STATUS      current
    DESCRIPTION
        "(U//FOUO) The ASCII App/Ver (Short Title) from the
        CSC Sector 1 of S1."
    ::= { hFwKeysEntry 2 }

END
