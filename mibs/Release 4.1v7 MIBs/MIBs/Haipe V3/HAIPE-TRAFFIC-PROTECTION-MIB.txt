--
--                 Unclassified//For Official Use Only
--
-- This entire document, which defines SNMP MIB objects in the SMIv2
-- language should be considered U//FOUO.
--
-- The data that will be transmitted on the wire as a result of
-- accessing these MIB objects MUST NOT BE CONSIDERED U//FOUO and is
-- subject to separate classification.  The classification level of this
-- data is not defined or within the scope of this document.
--

HAIPE-TRAFFIC-PROTECTION-MIB  DEFINITIONS  ::= BEGIN

IMPORTS
    OBJECT-TYPE, Unsigned32,
    NOTIFICATION-TYPE, Counter64,
    MODULE-IDENTITY                     FROM SNMPv2-SMI
    hrSystemDate                        FROM HOST-RESOURCES-MIB
    SnmpAdminString                     FROM SNMP-FRAMEWORK-MIB
    RowPointer, RowStatus, DateAndTime,
    TruthValue,
    TEXTUAL-CONVENTION, TimeStamp       FROM SNMPv2-TC
    hStationID                          FROM HAIPE-MANAGEMENT-MIB
    hTrafficProtection                  FROM HAIPE-FEATURE-HIERARCHY-MIB
    HaipeSecurityLevels,
    HaipeSecurityLevel,
    HaipeSecurityAuthority, 
    ShortTitle64                        FROM HAIPE-TC-MIB
    InetAddressType, InetAddress        FROM INET-ADDRESS-MIB
    InterfaceIndex                      FROM IF-MIB;

haipeTrafficProtectionMIB MODULE-IDENTITY
    LAST-UPDATED "200810031500Z"
    ORGANIZATION "HAIPE PO"
    CONTACT-INFO
         "(U//FOUO) Not Available"
    DESCRIPTION
        "(U//FOUO) This MIB defines the HAIPE traffic protection MIB objects."
    ::= { hTrafficProtection 1 }

-- **********************************************************************
-- Traffic Protection Information Segments
-- **********************************************************************

hTPCryptography          OBJECT IDENTIFIER ::= { hTrafficProtection 2 }
hTPIke                   OBJECT IDENTIFIER ::= { hTrafficProtection 3 }
hTPNotifications         OBJECT IDENTIFIER ::= { hTrafficProtection 4 }
hTPPolicyObjects         OBJECT IDENTIFIER ::= { hTrafficProtection 5 }

hCryptoControl           OBJECT IDENTIFIER ::= { hTPCryptography 1 }

hKeyInformation             OBJECT IDENTIFIER ::= { hTPCryptography 2 }
hFFKeyInformation           OBJECT IDENTIFIER ::= { hKeyInformation 1 }
hPPKInformation             OBJECT IDENTIFIER ::= { hKeyInformation 2 }
hDePACModuliInformation     OBJECT IDENTIFIER ::= { hKeyInformation 3 }
hAPPKTrustAnchorInformation OBJECT IDENTIFIER ::= { hKeyInformation 4 }

hPPKKeyInformation       OBJECT IDENTIFIER ::= { hPPKInformation 1 }
hPPKTrafficInformation   OBJECT IDENTIFIER ::= { hPPKInformation 2 }
hPPKEKInformation        OBJECT IDENTIFIER ::= { hPPKInformation 3 }
hPPKChainInformation     OBJECT IDENTIFIER ::= { hPPKInformation 4 }

hCKLInformation          OBJECT IDENTIFIER ::= { hTPCryptography 4 }
hUniversalCKLInformation OBJECT IDENTIFIER ::= { hCKLInformation  1 }
hFFLocalCKLInformation   OBJECT IDENTIFIER ::= { hCKLInformation  2 }

-- hTPPolicyObjects tree
hTPPolicyManageObjects     OBJECT IDENTIFIER ::= { hTPPolicyObjects 1 }
hTPPolicyNotifications     OBJECT IDENTIFIER ::= { hTPPolicyObjects 2 }

-- hTPPolicyManageObjects tree
hTPPolicyPacketProcessing  OBJECT IDENTIFIER ::= { hTPPolicyManageObjects 1 }
hTPSecurityPolicyDatabase  OBJECT IDENTIFIER ::= { hTPPolicyManageObjects 2 }
hTPSecurityAssocDatabase   OBJECT IDENTIFIER ::= { hTPPolicyManageObjects 3 }
hTPMapping                 OBJECT IDENTIFIER ::= { hTPPolicyManageObjects 4 }
hTPTFC                     OBJECT IDENTIFIER ::= { hTPPolicyManageObjects 5 }

-- hTPPolicyNotifications tree
hTPPolicyNotifs            OBJECT IDENTIFIER ::= { hTPPolicyNotifications 0 }
hTPPolicyNotifObjects      OBJECT IDENTIFIER ::= { hTPPolicyNotifications 1 }



-- **********************************************************************
-- Textual conventions
-- **********************************************************************

FFUniversalID ::= TEXTUAL-CONVENTION
        STATUS  current
        DESCRIPTION
            "(U//FOUO) The universal ID uniquely identifying a FF
            universal.  This is an ASCII encoded number from
            0000-9999, as defined by the HAIPE IS."
        SYNTAX   OCTET STRING (SIZE(4))

KMID ::= TEXTUAL-CONVENTION
        DISPLAY-HINT "6d"
        STATUS  current
        DESCRIPTION
            "(U//FOUO) The Key Material ID of a Firefly key.

            (U//FOUO) Current convention is that the left more 16 bits
            will be 0 value only.  However, implementations should be
            prepared to use full 48 bit values for use in the future.
            It is possible that future values and/or values assigned
            by other organizations may be larger than 32 bits so
            storing these values as a 32bit integer and prepending
            zeros is not a recommended implementation."
        SYNTAX   OCTET STRING (SIZE (6))

KMIDOrBlank ::= TEXTUAL-CONVENTION
        DISPLAY-HINT "6d"
        STATUS  current
        DESCRIPTION
            "(U//FOUO) The Key Material ID or an empty string.  This is a
            duplicate of the KMID TEXTUAL-CONVENTION, but allows for
            the case where no KMID is appropriate for the given object
            and thus a 0-length string is an acceptable value."
        SYNTAX   OCTET STRING (SIZE (0|6))

PartitionCode ::= TEXTUAL-CONVENTION
        DISPLAY-HINT "6d"
        STATUS  current
        DESCRIPTION
            "(U//FOUO) The partition code for segmenting a universal
            into separate networks.

            (U//FOUO) Note that current convention is that values for
            partition codes limit the left 16 bits to 0 values
            only. Only the right 32 bits will vary (EKS322).  However,
            implementers should be aware that this could change in the
            future."
        SYNTAX   OCTET STRING (SIZE (6))

FireFlyExpirationDate ::= TEXTUAL-CONVENTION
        DISPLAY-HINT "2d-1d-1d"
        STATUS   current
        DESCRIPTION
            "(U//FOUO) The expiration date of a Firefly key.

            (U//FOUO) Firefly keys expire at 2400 (UTC) on the date given.
            Note that for use within HAIPE, the day value for this object
            must be the last day of the month.  Time is

                (U//FOUO) 
                field  octets  contents                  range
                -----  ------  --------                  -----
                  1      1-2   year*                     0..65536
                  2       3    month                     1..12
                  3       4    day                       1..31

                * (U//FOUO) Notes:
                - Much of this format is similar to the DateAndTime TC
                  from the SNMPv2-TC MIB (RFC2579) but the unneeded
                  portions were removed.
                - the value of year is in network-byte order
                "
        SYNTAX   OCTET STRING (SIZE(4))

PPKShortTitle ::= TEXTUAL-CONVENTION
        DISPLAY-HINT "18x"
        STATUS   current
        DESCRIPTION
            "(U//FOUO) The short title for a pre-placed key (PPK).  It
            is sent as the 24 character, six-bit encoded ShortTitle
            field extracted from the key itself without modification
            (see EKMS308C).  "
        SYNTAX   OCTET STRING (SIZE (18))

PPKEdition ::= TEXTUAL-CONVENTION
        STATUS   current
        DESCRIPTION
            "(U//FOUO) The HAIPE edition for a pre-placed key (PPK).
            This field is encoded using the six-bit encoding as
            specified in EKMS308C.  It is 36 bits wide, and the right
            most 4 bits in this field SHOULD be set to 0 and MUST be
            ignored by implementations expecting only exactly 36 bits."
        SYNTAX   OCTET STRING (SIZE (5))

HaipeSegment ::= TEXTUAL-CONVENTION
        DISPLAY-HINT "d"
        STATUS   current
        DESCRIPTION
            "(U//FOUO) The HAIPE segment number for a pre-placed key (PPK)."
        SYNTAX   Unsigned32 (0..255)

HaipeEncryptionAlgorithm ::= TEXTUAL-CONVENTION
        STATUS  current
        DESCRIPTION
            "(U//FOUO) An encryption algorithm."
        SYNTAX   INTEGER { unassigned(0),
                           baton(1), 
                           medley(2),
                           aes(3)
                         }

HaipeIntegrityAlgorithm ::= TEXTUAL-CONVENTION
        STATUS  current
        DESCRIPTION
            "(U//FOUO) A data integrity algorithm.  It is possible
            that in some situations it will not be possible to
            determine the correct algorithm to return since more than
            one are in use for a given key (for example).  For these
            cases the multiple(7) value should be returned."
        SYNTAX   INTEGER { unassigned(0),
                           gcm0(1), 
                           gcm32(2),
                           gcm64(3),
                           gcm96(4),
                           gcm128(5),
                           bip32(6),
                           multiple(7)
                         }

HaipeHashAlgorithm ::= TEXTUAL-CONVENTION
        STATUS  current
        DESCRIPTION
            "(U//FOUO) A hash alogrithm."
        SYNTAX   INTEGER { unassigned(0),
                           sha1(1),
                           sha384(2)
                         }

HaipeAuthenticationAlgorithm ::= TEXTUAL-CONVENTION
        STATUS  current
        DESCRIPTION
            "(U//FOUO) A authentication alogrithm."
        SYNTAX   INTEGER { bff(0),
                           eff(1),
                           mqvDerived(2)
                         }

HaipeCredentialType ::= TEXTUAL-CONVENTION
        STATUS current
        DESCRIPTION
            "(U//FOUO) (U//FOUO) A public-key authentication system
            certificate type."
        SYNTAX INTEGER {
                 reserved(0),
                 unknown(1),
                 ekms322(2)
               }

-- **********************************************************************
-- Control objects
-- **********************************************************************

haipeZeroizeAllKeys OBJECT-TYPE
        SYNTAX      TruthValue
        MAX-ACCESS  read-write
        STATUS      current
        DESCRIPTION
            "(U//FOUO) Setting this object to 'true' will zeroize all
            the keys contained within the device.  It must not modify
            any other information in the device such as the persistent
            storage or the audit log.  Also see the
            HAIPE-MANAGEMENT-MIB::haipeSanitizeDevice object.  When
            read this object should return false.  When set to false
            this object must not perform any operation but should
            accept this as a valid SET operation."
        ::= { hCryptoControl 1 }

-- **********************************************************************
-- firefly information
-- **********************************************************************


hFireflyTableCount      OBJECT-TYPE
        SYNTAX          Unsigned32
        MAX-ACCESS	 read-only
        STATUS		 current
        DESCRIPTION
            "(U//FOUO) The number of rows in the hFireflyTable."
        ::= { hFFKeyInformation 1 }

hFireflyTableLastChanged OBJECT-TYPE
    SYNTAX      TimeStamp
    MAX-ACCESS	 read-only
    STATUS		 current
    DESCRIPTION
        "(U//FOUO) The value of sysUpTime the last time any entry in
        the hFireflyTable was modified, created, or deleted by either
        SNMP or other management method (e.g. via an HMI).

        (U//FOUO) Managers can use this object to ensure that no
        changes to configuration of this table have happened since
        the last time it examined the table.

        (U//FOUO) A value of 0 indicates that no entry has been
        changed since the agent initialized."
    ::= { hFFKeyInformation 2 }

hFireflyTable           OBJECT-TYPE
        SYNTAX          SEQUENCE OF HFireflyEntry
        MAX-ACCESS      not-accessible
        STATUS		 current
        DESCRIPTION
            "(U//FOUO) The table containing a list of loaded Firefly keys."
        ::= { hFFKeyInformation 3 }

hFireflyEntry           OBJECT-TYPE
        SYNTAX          HFireflyEntry
        MAX-ACCESS      not-accessible
        STATUS		 current
        DESCRIPTION
            "(U//FOUO) A row describing the information about a Firefly key."
        INDEX   { hFFKMID, hFFUniversalID, hFFUniversalEdition }
        ::= { hFireflyTable 1 }

HFireflyEntry ::= SEQUENCE
    {
	hFFKMID                          KMID,
	hFFUniversalID                   FFUniversalID,
	hFFUniversalEdition              OCTET STRING,
	hFFAlgorithmPrivilege            BITS,
	hFFSecurityLevels                HaipeSecurityLevels,
	hFFMaterialType                  INTEGER,
	hFFExpiration                    FireFlyExpirationDate,
	hFFNextVector                    RowPointer,
	hFFPartitionCode                 PartitionCode,
	hFFLastChanged                   TimeStamp,
	hFFZeroizeKey                    TruthValue,
	hFFAuthority                     HaipeSecurityAuthority,
	hFFASCIIID                       OCTET STRING,
	hFFIsTestKey                     TruthValue,
	hFFEnhancedFFTag                 INTEGER,
	hFFShortTitleName                OCTET STRING
    }

hFFKMID                 OBJECT-TYPE
        SYNTAX          KMID
        MAX-ACCESS	 read-only
        STATUS		 current
        DESCRIPTION
            "(U//FOUO) The Firefly Key Material ID for this Firefly key."
        ::= { hFireflyEntry 1 }

hFFUniversalID          OBJECT-TYPE
        SYNTAX          FFUniversalID
        MAX-ACCESS	 read-only
        STATUS		 current
        DESCRIPTION
            "(U//FOUO) The universal ID of this Firefly key"
        ::= { hFireflyEntry 2 }

hFFUniversalEdition     OBJECT-TYPE
        SYNTAX          OCTET STRING (SIZE(2))
        MAX-ACCESS	 read-only
        STATUS		 current
        DESCRIPTION
            "(U//FOUO) The universal edition of this Firefly key.  This is
            an ASCII encoded number from 01-99, as defined by the
            HAIPE IS."
        ::= { hFireflyEntry 3 }

hFFAlgorithmPrivilege   OBJECT-TYPE
        SYNTAX          BITS { ff91(0), ff171(1) }
        MAX-ACCESS	 read-only
        STATUS       deprecated
        DESCRIPTION
            "(U//FOUO) The algorithms usable by this Firefly key."
        ::= { hFireflyEntry 4 }

hFFSecurityLevels       OBJECT-TYPE
        SYNTAX          HaipeSecurityLevels
        MAX-ACCESS	 read-only
        STATUS		 current
        DESCRIPTION
            "(U//FOUO) The security levels usable with this Firefly key."
        ::= { hFireflyEntry 5 }

hFFMaterialType         OBJECT-TYPE
        SYNTAX          INTEGER { seed(1), operational(2), oneTimeUse(3) }
        MAX-ACCESS	 read-only
        STATUS		 current
        DESCRIPTION
            "(U//FOUO)  The material type of this Firefly key."
        ::= { hFireflyEntry 6 }

hFFExpiration           OBJECT-TYPE
        SYNTAX          FireFlyExpirationDate
        MAX-ACCESS	 read-only
        STATUS		 current
        DESCRIPTION
            "(U//FOUO) The expiration date of this Firefly key."
        ::= { hFireflyEntry 7 }

hFFNextVector           OBJECT-TYPE
        SYNTAX          RowPointer
        MAX-ACCESS	 read-only
        STATUS		 current
        DESCRIPTION
            "(U//FOUO) A row pointer into the hFireflyTable indicating
            the next Firefly key to be used.  If no next vector set is
            available for the given Firefly key, then a ZeroDotZero
            value (0.0) is returned."
        ::= { hFireflyEntry 8 }

hFFPartitionCode        OBJECT-TYPE
        SYNTAX          PartitionCode
        MAX-ACCESS	 read-only
        STATUS		 current
        DESCRIPTION
            "(U//FOUO) The partition code of this Firefly key."
        ::= { hFireflyEntry 9 }

hFFLastChanged          OBJECT-TYPE
        SYNTAX          TimeStamp
        MAX-ACCESS	 read-only
        STATUS		 current
        DESCRIPTION
            "(U//FOUO) The value of sysUpTime the last time any value
            in this row was modified, created, or deleted by either
            SNMP or other management method (e.g., via an HMI).

            (U//FOUO) Managers can use this object to ensure that no
            changes to configuration of this row have happened since
            the last time it examined the row.

            (U//FOUO) A value of 0 indicates that no value has been
            changed since the agent initialized."
        ::= { hFireflyEntry 10 }

hFFZeroizeKey OBJECT-TYPE
        SYNTAX      TruthValue
        MAX-ACCESS  read-write
        STATUS		 current
        DESCRIPTION
            "(U//FOUO) Setting this object to 'true' will zeroize this
            key.  It must not modify any other information in the
            device including the audit log.  When read this object
            should return true if the key has been zeroized, or false
            otherwise.  If this object is set to the same value as the
            current value, the device must not perform any operation
            but should accept this as a valid SET operation. Once the
            value is set to true, it may not be set back to false.

            (U//FOUO) It is beyond the scope of the MIB model to
            indicate whether zeroized keys are even reported in this
            table or not, but this text allows for this condition
            should an implementation choose to do so.  "
        ::= { hFireflyEntry 11 }

hFFAuthority OBJECT-TYPE
        SYNTAX       HaipeSecurityAuthority
        MAX-ACCESS	 read-only
        STATUS       deprecated
        DESCRIPTION
            "(U//FOUO) This object is deprecated and should not be
            implemented."
        ::= { hFireflyEntry 12 }

hFFASCIIID OBJECT-TYPE
        SYNTAX       OCTET STRING (SIZE(0|65|115))
        MAX-ACCESS	 read-only
        STATUS		 current
        DESCRIPTION
            "(U//FOUO) The ASCII ID of the key.  This should be a
            zero-length string if the key contains no ASCII ID
            information or if the HAIPE doesn't support reading it
            from the key."
        ::= { hFireflyEntry 13 }

hFFIsTestKey OBJECT-TYPE
        SYNTAX       TruthValue
        MAX-ACCESS	 read-only
        STATUS		 current
        DESCRIPTION
            "(U//FOUO) Whether this key is a test or operational key.
            If true, this key is for use in test networks only."
        ::= { hFireflyEntry 14 }

hFFEnhancedFFTag   OBJECT-TYPE
        SYNTAX       INTEGER { transition(0), enhanced(1), basic(2) }
        MAX-ACCESS	 read-only
        STATUS		 current
        DESCRIPTION
            "(U//FOUO) The usage potential of the key as dictaded by
            the EFT flag.  In older versions of EKMS322 this was the
            MPF flag."
        ::= { hFireflyEntry 15 }

hFFShortTitleName     OBJECT-TYPE
       SYNTAX         OCTET STRING (SIZE (18))
       MAX-ACCESS     read-only
       STATUS         current
       DESCRIPTION
          "(U//FOUO) The short title for a FF/EFF Vector Set (FFVS).
          It is sent as the 24 character, six-bit encoded ShortTitle
          field extracted from the key itself without modification."
       REFERENCE "EKMS322"
       ::= { hFireflyEntry 16 }

--
-- compromised keys known to the HAIPE device.
--
--
-- global CKL list information
--

hUniversalTableCount    OBJECT-TYPE
        SYNTAX          Unsigned32
        MAX-ACCESS      read-only
        STATUS          current
        DESCRIPTION
            "(U//FOUO) The number of rows in the hUniversalTable."
        ::= { hUniversalCKLInformation 1 }

hUniversalTableLastChanged OBJECT-TYPE
        SYNTAX      TimeStamp
        MAX-ACCESS  read-only
        STATUS      current
        DESCRIPTION
            "(U//FOUO) The value of sysUpTime the last time any
            entry in the universalTable was modified.

            (U//FOUO) Managers can use this object to ensure that no
            changes to this table has happened since the last time
            it examined the table.

            (U//FOUO) A value of 0 indicates that no entry has been
            changed since the agent initialized."
        ::= { hUniversalCKLInformation 2 }

hUniversalTable         OBJECT-TYPE
        SYNTAX          SEQUENCE OF HUniversalEntry
        MAX-ACCESS      not-accessible
        STATUS          current
        DESCRIPTION
            "(U//FOUO) The table containing a list of universals
            known to the HAIPE by way of keying and Central Facility
            (CF) based Compromised Key List (CKL) data loaded into
            the device."
        ::= { hUniversalCKLInformation 3 }

hUniversalEntry         OBJECT-TYPE
        SYNTAX          HUniversalEntry
        MAX-ACCESS      not-accessible
        STATUS          current
        DESCRIPTION
            "(U//FOUO) A row describing the information known about
            a given universal."
        INDEX   { hUniversalID }
        ::= { hUniversalTable 1 }

HUniversalEntry ::= SEQUENCE
    {
	hUniversalID                     FFUniversalID,
	hUniversalCKLDate                DateAndTime,
	hUniversalCKLVersion             OCTET STRING
    }

hUniversalID            OBJECT-TYPE
        SYNTAX          FFUniversalID
        MAX-ACCESS      read-only
        STATUS          current
        DESCRIPTION
            "(U//FOUO) The universal ID of the universal."
        ::= { hUniversalEntry 1 }

hUniversalCKLDate       OBJECT-TYPE
        SYNTAX          DateAndTime
        MAX-ACCESS      read-only
        STATUS          current
        DESCRIPTION
            "(U//FOUO) The date of the current Compromised Key List
            from the central facility contained within the device
            for this universal.  If no CKL is loaded for this
            universal then this column should be 'non-existent' and
            thus should return a noSuchInstance exception for GET
            requests and should be skipped for GETNEXT and GETBULK
            requests."
        ::= { hUniversalEntry 2 }

hUniversalCKLVersion    OBJECT-TYPE
        SYNTAX          OCTET STRING (SIZE(2))
        MAX-ACCESS      read-only
        STATUS          current
        DESCRIPTION
            "(U//FOUO) The version of the current Compromised Key
            List from the central facility contained within the
            device for this universal.  If no CKL is loaded for this
            universal then this column should be 'non-existent' and
            thus should return a noSuchInstance exception for GET
            requests and should be skipped for GETNEXT and GETBULK
            requests."
        ::= { hUniversalEntry 3 }

--
-- local CKL list information
--

--
-- hLocalCompromisedKeyTable
-- hLocalCompromisedKeyTable is an older table for handle local CKL
-- lists.  Use of the Newer hLocalCompromisedKeyListTable is
-- recommended instead.
--

hLocalCompromisedKeyTableCount OBJECT-TYPE
        SYNTAX      Unsigned32
        MAX-ACCESS  read-only
        STATUS      current
        DESCRIPTION
            "(U//FOUO) The number of rows in the
            localCompromisedKeyTable."
        ::= { hFFLocalCKLInformation 1 }

hLocalCompromisedKeyTableLastChanged OBJECT-TYPE
        SYNTAX      TimeStamp
        MAX-ACCESS  read-only
        STATUS      current
        DESCRIPTION
            "(U//FOUO) The value of sysUpTime the last time any entry
            in the hLocalCompromisedKeyTable was modified, created,
            or deleted by either SNMP or other management method
            (e.g. via an HMI).

            (U//FOUO) Managers can use this object to ensure that no
            changes to configuration of this table have happened
            since the last time it examined the table.

            (U//FOUO) A value of 0 indicates that no entry has been
            changed since the agent initialized."
        ::= { hFFLocalCKLInformation 2 }


hLocalCompromisedKeyTable OBJECT-TYPE
        SYNTAX      SEQUENCE OF HLocalCompromisedKeyEntry
        MAX-ACCESS  not-accessible
        STATUS      current
        DESCRIPTION
            "(U//FOUO) DEPRECATION WARNING: It is recommended that
            implementations use the hLocalCompromisedKeyListTable to
            handle local compromised key lists instead of this table.

            (U//FOUO) A table for maintaining a local compromised
            key list, for devices that support the concept of user
            imputable bad-keys.  It is expected that administrators
            local to the network will add or remove entries in this
            table to supplement the Compromised Key List (CKL)
            distributed by the Central Facility (CF).

            (U//FOUO) If any KMID conflicts exist (non-unique KMID
            values in separate keys) when an implementation uses this
            table, all keys with matching KMID values MUST be
            considered compromised.  Usage of the
            hLocalCompromisedKeyListTable instead of this table fixes
            this issue."
        ::= { hFFLocalCKLInformation 3 }

hLocalCompromisedKeyEntry OBJECT-TYPE
        SYNTAX      HLocalCompromisedKeyEntry
        MAX-ACCESS  not-accessible
        STATUS      current
        DESCRIPTION
            "(U//FOUO) A row describing a compromised key."
        INDEX   { hLocalCKLIDBegin, hLocalCKLIDEnd }
        ::= { hLocalCompromisedKeyTable 1 }

HLocalCompromisedKeyEntry ::= SEQUENCE
    {
	hLocalCKLIDBegin                 KMID,
	hLocalCKLIDEnd                   KMID,
	hLocalCKLDate                    DateAndTime,
	hLocalCKLReason                  SnmpAdminString,
	hLocalCKLRowStatus               RowStatus
    }

hLocalCKLIDBegin        OBJECT-TYPE
        SYNTAX          KMID
        MAX-ACCESS      read-create
        STATUS          current
        DESCRIPTION
            "(U//FOUO) The starting KMID for a range of keys which
            have been compromised."
        ::= { hLocalCompromisedKeyEntry 1 }

hLocalCKLIDEnd          OBJECT-TYPE
        SYNTAX          KMID
        MAX-ACCESS      read-create
        STATUS          current
        DESCRIPTION
            "(U//FOUO) The ending KMID for a range of keys which
            have been compromised."
        ::= { hLocalCompromisedKeyEntry 2 }

hLocalCKLDate           OBJECT-TYPE
        SYNTAX          DateAndTime
        MAX-ACCESS      read-only
        STATUS          current
        DESCRIPTION
            "(U//FOUO) The date and time at which the key was added
            to the compromised key list."
        ::= { hLocalCompromisedKeyEntry 3 }

hLocalCKLReason         OBJECT-TYPE
        SYNTAX          SnmpAdminString
        MAX-ACCESS      read-create
        STATUS          current
        DESCRIPTION
            "(U//FOUO) The human-consumable reason the entry was
            added to the table."
        ::= { hLocalCompromisedKeyEntry 4 }

hLocalCKLRowStatus  OBJECT-TYPE
        SYNTAX      RowStatus
        MAX-ACCESS  read-create
        STATUS      current
        DESCRIPTION
            "(U//FOUO) The status of this row, by which new entries
            may be created, or old entries deleted from this table.

            (U//FOUO) A new row may be created by
            setting this object to createAndGo. If this object is
            set to createAndGo and any columns included in the
            request contain inconsistent values an inconsistentName
            error will be returned for this object.

            (U//FOUO) If any column is set to an invalid or
            unsupported value (during row creation or any other
            time), a wrongValue error will be returned for that
            object."
        ::= { hLocalCompromisedKeyEntry 5 }


--
-- hLocalkCompromisedKeyListTable
-- local Compromised Key List information
-- updated table of the hLocalCompromisedKeyTable
--
-- Use of hLocaklCompromisedKeyListTable instead of
-- hLocalCompromisedKeyTable is recommended.
--

hLocalCompromisedKeyListTableCount OBJECT-TYPE
    SYNTAX      Unsigned32
    MAX-ACCESS  read-only
    STATUS      current
    DESCRIPTION
        "(U//FOUO) The number of rows in the
        hLocalCompromisedKeyListTable."
    ::= { hFFLocalCKLInformation 4 }

hLocalCompromisedKeyListTableLastChanged OBJECT-TYPE
    SYNTAX      TimeStamp
    MAX-ACCESS  read-only
    STATUS      current
    DESCRIPTION
        "(U//FOUO) The value of sysUpTime the last time any entry in
        the hLocalCompromisedKeyListTable was modified, created, or
        deleted by either SNMP or other management method (e.g. via
        an HMI).

        (U//FOUO) Managers can use this object to ensure that no
        changes to configuration of this table have happened since
        the last time it examined the table.

        (U//FOUO) A value of 0 indicates that no entry has been
        changed since the agent initialized."
    ::= { hFFLocalCKLInformation 5 }


hLocalCompromisedKeyListTable OBJECT-TYPE
    SYNTAX      SEQUENCE OF HLocalCompromisedKeyListEntry
    MAX-ACCESS  not-accessible
    STATUS      current
    DESCRIPTION
        "(U//FOUO) The table for maintaining a local compromised key
        list, for devices that support the concept of user imputable
        bad-keys.  It is expected that administrators local to the
        network will add or remove entries in this table to
        supplement the Compromised Key List (CKL) distributed by the
        Central Facility (CF).

        (U//FOUO) Keys are considered compromised if they have a
        Universal ID and Universal Edition that match a row in this
        table and they also have a KMID value that falls within the
        KMID start and end ranges of that row.

        (U//FOUO) This table is an updated version of the
        hLocalCompromisedKeyTable and it is recommended that
        implementations use this table instead."
    ::= { hFFLocalCKLInformation 6 }

hLocalCompromisedKeyListEntry OBJECT-TYPE
    SYNTAX      HLocalCompromisedKeyListEntry
    MAX-ACCESS  not-accessible
    STATUS      current
    DESCRIPTION
        "(U//FOUO) A row describing one or more compromised keys."
    INDEX   { hLocalCKListUniversal, hLocalCKListUniversalEdition,
              hLocalCKListKMIDBegin, hLocalCKListKMIDEnd }
    ::= { hLocalCompromisedKeyListTable 1 }

HLocalCompromisedKeyListEntry ::= SEQUENCE
    {
	hLocalCKListUniversal            FFUniversalID,
	hLocalCKListUniversalEdition     OCTET STRING,
	hLocalCKListKMIDBegin            KMID,
	hLocalCKListKMIDEnd              KMID,
	hLocalCKListDate                 DateAndTime,
	hLocalCKListReason               SnmpAdminString,
	hLocalCKListRowStatus            RowStatus
    }

hLocalCKListUniversal      OBJECT-TYPE
    SYNTAX        FFUniversalID
    MAX-ACCESS    read-only
    STATUS		 current
    DESCRIPTION
    "(U//FOUO) The Universal ID of the compromised key(s)."
    ::= { hLocalCompromisedKeyListEntry 1 }

hLocalCKListUniversalEdition  OBJECT-TYPE
    SYNTAX        OCTET STRING (SIZE(2))
    MAX-ACCESS    read-only
    STATUS		 current
    DESCRIPTION
    "(U//FOUO) The Universal Edition of the compromised key."
    ::= { hLocalCompromisedKeyListEntry 2 }

hLocalCKListKMIDBegin      OBJECT-TYPE
    SYNTAX        KMID
    MAX-ACCESS    read-only
    STATUS        current
    DESCRIPTION
        "(U//FOUO) The start KMID value of a range of compromised
        keys. (inclusive)"
    ::= { hLocalCompromisedKeyListEntry 3 }

hLocalCKListKMIDEnd      OBJECT-TYPE
    SYNTAX        KMID
    MAX-ACCESS    read-only
    STATUS        current
    DESCRIPTION
        "(U//FOUO) The end KMID value of a range of compromised keys
        (inclusive)."
    ::= { hLocalCompromisedKeyListEntry 4 }

hLocalCKListDate           OBJECT-TYPE
    SYNTAX        DateAndTime
    MAX-ACCESS    read-only
    STATUS        current
    DESCRIPTION
        "(U//FOUO) The date and time at which the key was added to
        the compromised key list."
    ::= { hLocalCompromisedKeyListEntry 5 }

hLocalCKListReason         OBJECT-TYPE
    SYNTAX        SnmpAdminString
    MAX-ACCESS    read-create
    STATUS        current
    DESCRIPTION
        "(U//FOUO) The human-consumable reason the entry was added
        to the table."
    ::= { hLocalCompromisedKeyListEntry 6 }

hLocalCKListRowStatus  OBJECT-TYPE
    SYNTAX        RowStatus
    MAX-ACCESS    read-create
    STATUS        current
    DESCRIPTION
        "(U//FOUO) The status of this row, by which new entries may
        be created, or old entries deleted from this table.

        (U//FOUO) A new row may be created by setting this object to
        createAndGo. If this object is set to createAndGo and any
        columns included in the request contain inconsistent values
        an inconsistentName error will be returned for this object.

        (U//FOUO) If any column is set to an invalid or unsupported
        value (during row creation or any other time), a wrongValue
        error will be returned for that object."
    ::= { hLocalCompromisedKeyListEntry 7 }


--
-- PPK group information
-- The PPK group has a table with information on each PPK, and a
-- table of PPK chains.
--

hPreplacedKeyTableCount OBJECT-TYPE
        SYNTAX          Unsigned32
        MAX-ACCESS      read-only
        STATUS          current
        DESCRIPTION
            "(U//FOUO) The number of rows in the hPreplacedKeyTable."
        ::= { hPPKKeyInformation 1 }

hPreplacedKeyTableCapacity OBJECT-TYPE
        SYNTAX          Unsigned32
        MAX-ACCESS      read-only
        STATUS          current
        DESCRIPTION
            "(U//FOUO) The total number of pre-placed keys (PPK's)
            this HAIPE can hold."
        ::= { hPPKKeyInformation 2 }

hPreplacedKeyTableLastChanged OBJECT-TYPE
        SYNTAX      TimeStamp
        MAX-ACCESS  read-only
        STATUS      current
        DESCRIPTION
            "(U//FOUO) The value of sysUpTime the last time any entry
            in the hPreplacedKeyTable was modified, created, or
            deleted by either SNMP or other management method
            (e.g. via an HMI).

            (U//FOUO) Managers can use this object to ensure that no
            changes to configuration of this table have happened
            since the last time it examined the table.

            (U//FOUO) A value of 0 indicates that no entry has been
            changed since the agent initialized."
        ::= { hPPKKeyInformation 3 }

hPreplacedKeyTable      OBJECT-TYPE
        SYNTAX          SEQUENCE OF HPreplacedKeyEntry
        MAX-ACCESS      not-accessible
        STATUS          current
        DESCRIPTION
            "(U//FOUO) The table containing information about the
            loaded pre-placed keys (PPK's)."
        ::= { hPPKKeyInformation 4 }

hPreplacedKeyEntry      OBJECT-TYPE
        SYNTAX          HPreplacedKeyEntry
        MAX-ACCESS      not-accessible
        STATUS          current
        DESCRIPTION
            "(U//FOUO) A row describing the information about a
            particular pre-placed key (PPK)."
        INDEX  { hPPKShortTitleName, hPPKEdition, hPPKSegment }
        ::= { hPreplacedKeyTable 1 }

HPreplacedKeyEntry ::= SEQUENCE
    {
	hPPKShortTitleName               PPKShortTitle,
	hPPKEdition                      PPKEdition,
	hPPKSegment                      HaipeSegment,
	hPPKUsageType                    INTEGER,
	hPPKEffectiveDate                DateAndTime,
	hPPKSecurityLevel                HaipeSecurityLevel,
	hPPKZeroizeKey                   TruthValue,
	hPPKRegister                     OCTET STRING,
	hPPKAuthority                    HaipeSecurityAuthority,
	hPPKLastChanged                  TimeStamp
    }

hPPKShortTitleName      OBJECT-TYPE
        SYNTAX          PPKShortTitle
        MAX-ACCESS      read-only
        STATUS          current
        DESCRIPTION
            "(U//FOUO) The short title of the pre-placed key (PPK)."
        ::= { hPreplacedKeyEntry 1 }

hPPKEdition             OBJECT-TYPE
        SYNTAX          PPKEdition
        MAX-ACCESS      read-only
        STATUS          current
        DESCRIPTION
            "(U//FOUO) The edition of this pre-placed key (PPK)."
        ::= { hPreplacedKeyEntry 2 }

hPPKSegment             OBJECT-TYPE
        SYNTAX          HaipeSegment
        MAX-ACCESS      read-only
        STATUS          current
        DESCRIPTION
            "(U//FOUO) The segment number of this pre-placed key (PPK)."
        ::= { hPreplacedKeyEntry 3 }

hPPKUsageType           OBJECT-TYPE
        SYNTAX          INTEGER { unassigned(1),
                                  trafficKey(2),
                                  exclusionKey(3) }
        MAX-ACCESS      read-write
        STATUS          current
        DESCRIPTION
            "(U//FOUO) Indicates how this key can be used.  Once set
            to a value other than unassigned, it can not be changed again
            and will return wrongValue if another attempt to change it
            is made. "
        ::= { hPreplacedKeyEntry 4 }

hPPKEffectiveDate       OBJECT-TYPE
        SYNTAX          DateAndTime
        MAX-ACCESS      read-only
        STATUS          current
        DESCRIPTION
            "(U//FOUO) The effective start date and time of this
            pre-placed key (PPK).  This object will be automatically
            set from the chain information once the spot in the chain
            is reached where this key becomes actively used."
        ::= { hPreplacedKeyEntry 5 }

hPPKSecurityLevel       OBJECT-TYPE
        SYNTAX          HaipeSecurityLevel
        MAX-ACCESS      read-write
        STATUS          current
        DESCRIPTION
            "(U//FOUO) The security level usable with this
            pre-placed key (PPK)."
        ::= { hPreplacedKeyEntry 6 }

hPPKZeroizeKey          OBJECT-TYPE
        SYNTAX          TruthValue
        MAX-ACCESS      read-write
        STATUS		 current
        DESCRIPTION
            "(U//FOUO) Setting this object to 'true' will zeroize
            this key. Any active SAs using this key should be torn
            down.  It must not modify any other information in the
            device including the audit log.  When read this object
            should return true if the key has been zeroized, or
            false otherwise.  If this object is set to the same
            value as the current value, the device must not perform
            any operation but should accept this as a valid SET
            operation. Once the value is set to true, attempts to
            set it back to false will return an an inconsistentValue
            error.

            (U//FOUO) It is beyond the scope of the MIB model to
            indicate whether zeroized keys are reported in this table
            or not.  This text allows for either the keys to continue
            to be reported or the row may be removed when a key is
            zeroized.  Which mode a device supports is implementation
            dependent."
        ::= { hPreplacedKeyEntry 7 }

hPPKRegister            OBJECT-TYPE
        SYNTAX          OCTET STRING (SIZE(5))
        MAX-ACCESS      read-only
        STATUS          current
        DESCRIPTION
            "(U//FOUO) The register number of this PPK.  The right
            most 36 bits are used to signify the register number.  The
            left most 4 bits must be set to zero in responses from the
            SNMP agent."
        ::= { hPreplacedKeyEntry 8 }

hPPKAuthority OBJECT-TYPE
        SYNTAX       HaipeSecurityAuthority
        MAX-ACCESS	 read-only
        STATUS       deprecated
        DESCRIPTION
            "(U//FOUO) This object is deprecated and should not be
            implemented."
        ::= { hPreplacedKeyEntry 9 }

hPPKLastChanged         OBJECT-TYPE
        SYNTAX          TimeStamp
        MAX-ACCESS      read-only
        STATUS          current
        DESCRIPTION
            "(U//FOUO) The value of sysUpTime the last time any value
            in this row was modified, created, or deleted by either
            SNMP or other management method (e.g. via an HMI).

            (U//FOUO) Managers can use this object to ensure that no
            changes to configuration of this row have happened since
            the last time it examined the row.

            (U//FOUO) A value of 0 indicates that no value has been
            changed since the agent initialized."
        ::= { hPreplacedKeyEntry 10 }

--
-- PPK Traffic Key Information
--

hPPKTrafficTableCount    OBJECT-TYPE
        SYNTAX          Unsigned32
        MAX-ACCESS      read-only
        STATUS          current
        DESCRIPTION
            "(U//FOUO) The number of rows in the hPPKTrafficTable."
        ::= { hPPKTrafficInformation 1 }

hPPKTrafficTableMaxCount        OBJECT-TYPE
        SYNTAX          Unsigned32
        MAX-ACCESS      read-only
        STATUS          current
        DESCRIPTION
            "(U//FOUO) The maximum number of traffic PPKs the HAIPE
            can handle."
        ::= { hPPKTrafficInformation 2 }

hPPKTrafficTableLastChanged OBJECT-TYPE
        SYNTAX      TimeStamp
        MAX-ACCESS  read-only
        STATUS      current
        DESCRIPTION
            "(U//FOUO) The value of sysUpTime the last time any entry in
            the hPPKTrafficTable was modified.

            (U//FOUO) Managers can use this object to ensure that no
            changes to this table has happened since the last time it
            examined the table.

            (U//FOUO) A value of 0 indicates that no entry has been
            changed since the agent initialized."
        ::= { hPPKTrafficInformation 3 }

hPPKTrafficTable OBJECT-TYPE
        SYNTAX      SEQUENCE OF HPPKTrafficEntry
        MAX-ACCESS  not-accessible
        STATUS      current
        DESCRIPTION
            "(U//FOUO) A list of PPKs being used for traffic known to
            the HAIPE.  This table should be considered an extension
            of the hPreplacedKeyTable and should list all keys whose
            hPPKUsageType is set to trafficKey."
        ::= { hPPKTrafficInformation 4 }

hPPKTrafficEntry OBJECT-TYPE
        SYNTAX      HPPKTrafficEntry
        MAX-ACCESS  not-accessible
        STATUS      current
        DESCRIPTION
            "(U//FOUO) A row describing a particular traffic PPK."
        INDEX   { hPPKShortTitleName, hPPKEdition, hPPKSegment }
        ::= { hPPKTrafficTable 1 }

HPPKTrafficEntry ::= SEQUENCE
    {
	hPPKTrafficIntegrityAlgorithm    HaipeIntegrityAlgorithm,
	hPPKTrafficEncryptAlgorithm      HaipeEncryptionAlgorithm
    }

hPPKTrafficIntegrityAlgorithm OBJECT-TYPE
        SYNTAX      HaipeIntegrityAlgorithm
        MAX-ACCESS  read-only
        STATUS      current
        DESCRIPTION
            "(U//FOUO) The integrity algorithm type of this pre-placed
            key (PPK).  Its initial value will be unassigned.  Once
            this key has been used to protect traffic, this column
            will indicate the type of algorithm that was used to
            protect the traffic unless it is in use by multiple
            algorithms, in which case it will indicate multiple(7)."
        ::= { hPPKTrafficEntry 1 }

hPPKTrafficEncryptAlgorithm    OBJECT-TYPE
        SYNTAX          HaipeEncryptionAlgorithm
        MAX-ACCESS      read-only
        STATUS          current
        DESCRIPTION
            "(U//FOUO) The encryption algorithm type of this pre-placed
            key (PPK).  Its initial value will be unassigned.  Once
            this key has been used to protect traffic, this column
            will indicate the type of algorithm that was used to
            protect the traffic.  The value will come from the
            hPPKChainTable settings."
        ::= { hPPKTrafficEntry 2 }

--
-- EK Information
--

hPPKEKTableCount    OBJECT-TYPE
        SYNTAX          Unsigned32
        MAX-ACCESS      read-only
        STATUS          current
        DESCRIPTION
            "(U//FOUO) The number of rows in the hPPKEKTable."
        ::= { hPPKEKInformation 1 }

hPPKEKTableMaxCount        OBJECT-TYPE
        SYNTAX          Unsigned32
        MAX-ACCESS      read-only
        STATUS          current
        DESCRIPTION
            "(U//FOUO) The maximum number of EKs the HAIPE can handle."
        ::= { hPPKEKInformation 2 }

hPPKEKTableLastChanged OBJECT-TYPE
        SYNTAX      TimeStamp
        MAX-ACCESS  read-only
        STATUS      current
        DESCRIPTION
            "(U//FOUO) The value of sysUpTime the last time any entry in
            the hPPKEKTable was modified.

            (U//FOUO) Managers can use this object to ensure that no
            changes to this table has happened since the last time it
            examined the table.

            (U//FOUO) A value of 0 indicates that no entry has been
            changed since the agent initialized."
        ::= { hPPKEKInformation 3 }

hPPKEKTable OBJECT-TYPE
        SYNTAX      SEQUENCE OF HPPKEKEntry
        MAX-ACCESS  not-accessible
        STATUS      current
        DESCRIPTION
            "(U//FOUO) A list of exclusion keys known to the HAIPE.
            This table should be considered an extension of the
            hPreplacedKeyTable and should list all keys whose
            hPPKUsageType is set to exclusionKey."
        ::= { hPPKEKInformation 4 }

hPPKEKEntry OBJECT-TYPE
        SYNTAX      HPPKEKEntry
        MAX-ACCESS  not-accessible
        STATUS      current
        DESCRIPTION
            "(U//FOUO) A row describing a particular EK."
        INDEX   { hPPKShortTitleName, hPPKEdition, hPPKSegment }
        ::= { hPPKEKTable 1 }

HPPKEKEntry ::= SEQUENCE
    {
	hPPKEKKeyType                    INTEGER,
	hPPKEKUniversalID                FFUniversalID
    }

hPPKEKKeyType OBJECT-TYPE
    SYNTAX      INTEGER {
                        unassigned(0), global(1), local(2), 
			privacy(3), separate(4)
                }
    MAX-ACCESS  read-write
    STATUS      current
    DESCRIPTION
        "(U//FOUO) The key type of this EK."
    ::= { hPPKEKEntry 1 }

hPPKEKUniversalID OBJECT-TYPE
    SYNTAX      FFUniversalID
    MAX-ACCESS  read-write
    STATUS      current
    DESCRIPTION
        "(U//FOUO) The universal this EK is assigned to.
	
	(U//FOUO) A string of NULL characters should be used when 
	initially creating this object, if no suitable default 
	Universal ID can be automatically determined."
    ::= { hPPKEKEntry 2 }

--
-- PPK chains
--

hPPKChainTableCount OBJECT-TYPE
    SYNTAX          Unsigned32
    MAX-ACCESS      read-only
    STATUS          current
    DESCRIPTION
    "(U//FOUO) The number of rows in the hPPKChainTable."
    ::= { hPPKChainInformation 5 }

hPPKChainTableLastChanged OBJECT-TYPE
    SYNTAX      TimeStamp
    MAX-ACCESS  read-only
    STATUS      current
    DESCRIPTION
        "(U//FOUO) The value of sysUpTime the last time any entry in
        the hPPKChainTable was modified, created, or deleted by
        either SNMP or other management method (e.g. via an HMI).

        (U//FOUO) Managers can use this object to ensure that no
        changes to configuration of this table have happened since
        the last time it examined the table.

        (U//FOUO) A value of 0 indicates that no entry has been
        changed since the agent initialized."  
    ::= { hPPKChainInformation 6 }

hPPKChainTable      OBJECT-TYPE
    SYNTAX          SEQUENCE OF HPPKChainEntry
    MAX-ACCESS      not-accessible
    STATUS          current
    DESCRIPTION
        "(U//FOUO) The table containing information about pre-placed
        key (PPK) chains.  For a given Security Association (SA), a
        set or chain of pre-placed keys for that SA will be
        indicated by the hTPSAPPK in the hTPSATable which will match
        on the hPPKChainID value in this table.  The current PPK to
        use for an SA is indicated by the row having the lowest
        value of hPPKChainOrder for the set of rows with a matching
        hPPKChainID value.

        (U//FOUO) At the end of a PPK changeover, the previous low
        hPPKChainOrder row, of the a set of rows with the matching
        hPPKChainID, is deleted."
    ::= { hPPKChainInformation 7 }

hPPKChainEntry      OBJECT-TYPE
    SYNTAX          HPPKChainEntry
    MAX-ACCESS      not-accessible
    STATUS          current
    DESCRIPTION
        "(U//FOUO) A row indicating a pre-placed key (PPK) within a
        chain of PPK's and the order that the PPK indicated will be
        used by the HAIPE device as part of that chain."
    INDEX  { hPPKChainID, hPPKChainOrder }
    ::= { hPPKChainTable 1 }

HPPKChainEntry ::= SEQUENCE
    {
	hPPKChainID                      SnmpAdminString,
	hPPKChainOrder                   Unsigned32,
	hPPKChainPPK                     RowPointer,
	hPPKChainEffectiveDate           DateAndTime,
	hPPKChainIntegrityAlgorithm      HaipeIntegrityAlgorithm,
	hPPKChainEncryptionAlgorithm     HaipeEncryptionAlgorithm,
	hPPKChainRowStatus               RowStatus
    }

hPPKChainID     OBJECT-TYPE
    SYNTAX      SnmpAdminString (SIZE(1..32))
    MAX-ACCESS  read-create
    STATUS      current
    DESCRIPTION
        "(U//FOUO) An administratively assigned name to link a group
        of PPKs together.

        (U//FOUO) This object may be referenced by the hIPhRuleActionIndex
        object in the hIPhRuleTable. See the DESCRIPTION for hIPhRuleAction
        and hIPhRuleActionIndex for details."
    ::= { hPPKChainEntry 1 }

hPPKChainOrder  OBJECT-TYPE
    SYNTAX      Unsigned32 (1..65535)
    MAX-ACCESS  read-create
    STATUS      current
    DESCRIPTION
        "(U//FOUO) The order of which this key is applied.
         Lower values occur first (e.g. a hPPKChainOrder of 1 is
         used before a hPPKChainOrder of 2)."
    ::= { hPPKChainEntry 2 }

hPPKChainPPK    OBJECT-TYPE
    SYNTAX      RowPointer
    MAX-ACCESS  read-create
    STATUS      current
    DESCRIPTION
        "(U//FOUO) This object indicates the pre-placed key (PPK) in
        the hPreplacedKeyTable to use for the chain indicated by the
        column hPPKChainID in the order indicated by the column
        hPPKChainOrder.  It must point to a key with an identical
        hPPKUsageType value if other keys already exist in the chain."
    ::= { hPPKChainEntry 3 }

hPPKChainEffectiveDate OBJECT-TYPE
    SYNTAX      DateAndTime
    MAX-ACCESS  read-create
    STATUS      current
    DESCRIPTION
        "(U//FOUO) The effective date at which point this key within
        this chain will become active.  This date should be manually
        configured for the first key assigned to the chain but later
        keys added to the same chain will have this date set to the
        proper date following the previous key in the chain."
    ::= { hPPKChainEntry 4 }

hPPKChainIntegrityAlgorithm OBJECT-TYPE
    SYNTAX      HaipeIntegrityAlgorithm
    MAX-ACCESS  read-only
    STATUS      deprecated
    DESCRIPTION
        "(U//FOUO) This object is deprecated.  The algorithm must be 
        set directly by configuring the SA in the hTPSATable directly. New
        implementations should ignore values SET to this object and
        should not return instances of this object when queried."
    ::= { hPPKChainEntry 5 }

hPPKChainEncryptionAlgorithm OBJECT-TYPE
    SYNTAX      HaipeEncryptionAlgorithm
    MAX-ACCESS  read-create
    STATUS      current
    DESCRIPTION
        "(U//FOUO) The encryption algorithm to be used by this key.
        This encryption algorithm should be manually configured for
        the first key assigned to the chain but later keys added to
        the same chain will have this encryption algorithm field set
        to the same encryption algorithm from the previous key in the
        chain.  When a given key becomes active and is used to protect
        traffic, the hPPKTrafficEncryptAlgorithm column for this
        key in the chain will update to match the value in this
        column."
    ::= { hPPKChainEntry 6 }

hPPKChainRowStatus   OBJECT-TYPE
    SYNTAX          RowStatus
    MAX-ACCESS      read-create
    STATUS		 current
    DESCRIPTION
        "(U//FOUO) The status of this row, by which entries may be
        created and deleted from this table.

        (U//FOUO) Entries created with this table may not become
        active unless the hPPKChainPPK, hPPKChainEffectiveDate,
        hPPKChainIntegrityAlgorithm, and hPPKChainEncryptAlgorithm
        columns of this table have a valid value.  The values may
        have come from either OTNM or HMI configuration or through
        automatic setting.

        (U//FOUO) Entries in this table may not be set to notInService
        once they have been made active.  Once active(1), this object
        may only be changed to destroy(6).

        (U//FOUO) Entries in this table must assigned consecutively to
        a given chain.  IE, the hPPKChainOrder picked when inserting a
        new row for an existing chain must be one plus the highest
        hPPKChainOrder number already available in the row.

        (U//FOUO) Similarly, only the last key in a chain may be
        deleted from the chain.  If a key is deleted that is in use by
        an active SA, that SA will become unusable and should be torn
        down.

        (U//FOUO) If a PPK key in a chain is removed from the system,
        E.G. via zeroization, then the entire chain from that point on
        must be removed.  It should also tear down the SA and clear
        the entire contents of the chain if it was the first and
        active key in the chain."
    ::= { hPPKChainEntry 7 }

--
-- DePAC Moduli Table
--

hDePACModuliTableCount OBJECT-TYPE
    SYNTAX          Unsigned32
    MAX-ACCESS	 read-only
    STATUS		 current
    DESCRIPTION
    "(U//FOUO) The number of rows in the hDePACModuliTable."
    ::= { hDePACModuliInformation 1 }

hDePACModuliTableLastChanged OBJECT-TYPE
    SYNTAX      TimeStamp
    MAX-ACCESS	 read-only
    STATUS		 current
    DESCRIPTION
        "(U//FOUO) The value of sysUpTime the last time any entry in
        the hDePACModuliTable was modified, created, or deleted by
        either SNMP or other management method (e.g. via an HMI).

        (U//FOUO) Managers can use this object to ensure that no
        changes to configuration of this table have happened since
        the last time it examined the table.

        (U//FOUO) A value of 0 indicates that no entry has been
        changed since the agent initialized."  
    ::= { hDePACModuliInformation 2 }

hDePACModuliTable      OBJECT-TYPE
    SYNTAX          SEQUENCE OF HDePACModuliEntry
    MAX-ACCESS      not-accessible
    STATUS		 current
    DESCRIPTION
        "(U//FOUO) The table containing a list of loaded DePAC
        moduli."
    ::= { hDePACModuliInformation 3 }

hDePACModuliEntry      OBJECT-TYPE
    SYNTAX          HDePACModuliEntry
    MAX-ACCESS      not-accessible
    STATUS		 current
    DESCRIPTION
        "(U//FOUO) A row describing information about loaded DePAC
        moduli."
    INDEX  { hDModuliIndex }
    ::= { hDePACModuliTable 1 }

HDePACModuliEntry ::= SEQUENCE
    {
	hDModuliIndex                    Unsigned32,
	hDModuliBaseType                 INTEGER,
	hDModuliID                       OCTET STRING,
	hDModuliCOI                      INTEGER,
	hDModuliUserID                   OCTET STRING,
	hDModuliSourceID                 OCTET STRING,
	hDModuliNationalID               OCTET STRING,
	hDModuliShortTitleName           ShortTitle64
    }

hDModuliIndex OBJECT-TYPE
    SYNTAX      Unsigned32
    MAX-ACCESS  not-accessible
    STATUS      current
    DESCRIPTION
        "(U//FOUO) A unique numeric index per loaded DePAC 
        moduli."
    ::= { hDePACModuliEntry 1 }

hDModuliBaseType OBJECT-TYPE
    SYNTAX      INTEGER { base(1), alternate(2) }
    MAX-ACCESS	 read-only
    STATUS		 current
    DESCRIPTION
        "(U//FOUO) Identifies whether this is a Base or Alternate moduli."
    ::= { hDePACModuliEntry 2 }

hDModuliID OBJECT-TYPE
    SYNTAX      OCTET STRING (SIZE(6))
    MAX-ACCESS  read-only
    STATUS		 current
    DESCRIPTION
        "(U//FOUO) The 6 byte integer value of the Moduli ID from 
	the CPC/PPC in network byte order."
    ::= { hDePACModuliEntry 3 }

hDModuliCOI OBJECT-TYPE
    SYNTAX      INTEGER { us(1), nato(2), natoNations(3), cceb(4), coalition(5),
                          foreignSovereign(6), reserved(7) }
    MAX-ACCESS	 read-only
    STATUS		 current
    DESCRIPTION
        "(U//FOUO) The COI associated with the Moduli ID indicated
        by this row."
    ::= { hDePACModuliEntry 4 }

hDModuliUserID OBJECT-TYPE
    SYNTAX      OCTET STRING (SIZE(16))
    MAX-ACCESS	 read-only
    STATUS      current
    DESCRIPTION
        "(U//FOUO) 16 Character ASCII value from the User ID from
        the CPC."
    ::= { hDePACModuliEntry 5 }

hDModuliSourceID OBJECT-TYPE
    SYNTAX        OCTET STRING (SIZE(16))
    MAX-ACCESS	 read-only
    STATUS		 current
    DESCRIPTION
        "(U//FOUO) 16 Character ASCII value from the Source ID from
        the CPC."
    ::= { hDePACModuliEntry 6 }

hDModuliNationalID OBJECT-TYPE
    SYNTAX      OCTET STRING (SIZE(16))
    MAX-ACCESS	 read-only
    STATUS       current
    DESCRIPTION
        "(U//FOUO) 16 Character ASCII value from the National ID
        from the PPC."
    ::= { hDePACModuliEntry 7 }

hDModuliShortTitleName OBJECT-TYPE
    SYNTAX          ShortTitle64
    MAX-ACCESS      read-only 
    STATUS          current
    DESCRIPTION
        "(U//FOUO) The 64 byte ASCII short title for a DePAC moduli."
    ::= { hDePACModuliEntry 8 }

--
-- APPK Trust Anchor Table
--

hAPPKTrustAnchorTableCount OBJECT-TYPE
    SYNTAX          Unsigned32
    MAX-ACCESS	 read-only
    STATUS		 current
    DESCRIPTION
        "(U//FOUO) The number of rows in the hAPPKTrustAnchorTable."
    ::= { hAPPKTrustAnchorInformation 1 }

hAPPKTrustAnchorTableLastChanged OBJECT-TYPE
    SYNTAX      TimeStamp
    MAX-ACCESS	 read-only
    STATUS		 current
    DESCRIPTION
        "(U//FOUO) The value of sysUpTime the last time any entry in
        the hAPPKTrustAnchorTable was modified, created, or deleted
        by either SNMP or other management method (e.g. via an HMI).

        (U//FOUO) Managers can use this object to ensure that no
        changes to configuration of this table have happened since
        the last time it examined the table.

        (U//FOUO) A value of 0 indicates that no entry has been
        changed since the agent initialized."
    ::= { hAPPKTrustAnchorInformation 2 }

hAPPKTrustAnchorTable      OBJECT-TYPE
    SYNTAX          SEQUENCE OF HAPPKTrustAnchorEntry
    MAX-ACCESS      not-accessible
    STATUS		 current
    DESCRIPTION
        "(U//FOUO) The table containing a list of loaded APPK Trust
        Anchors."
    ::= { hAPPKTrustAnchorInformation 3 }

hAPPKTrustAnchorEntry      OBJECT-TYPE
    SYNTAX          HAPPKTrustAnchorEntry
    MAX-ACCESS      not-accessible
    STATUS		 current
    DESCRIPTION
        "(U//FOUO) A row describing information about loaded APPK
        Trust Anchors."
    INDEX  { hAPPKTAPartialQy }
    ::= { hAPPKTrustAnchorTable 1 }

HAPPKTrustAnchorEntry ::= SEQUENCE
    {
	hAPPKTAPartialQy                 OCTET STRING,
	hAPPKTAShortTitleName            ShortTitle64
    }

hAPPKTAPartialQy OBJECT-TYPE
    SYNTAX      OCTET STRING (SIZE(8))
    MAX-ACCESS  not-accessible
    STATUS		 current
    DESCRIPTION
        "(U//FOUO) The low order 64 bits of the ECDSA Public Key."
    ::= { hAPPKTrustAnchorEntry 1 }

hAPPKTAShortTitleName OBJECT-TYPE
    SYNTAX            ShortTitle64
    MAX-ACCESS        read-only
    STATUS            current
    DESCRIPTION
        "(U//FOUO) 64 byte ASCII short title for the APPK Trust Anchor."
    ::= { hAPPKTrustAnchorEntry 2 }

--
-- Traffic Protection Notifications
--

--
-- key notifications
--

hTPKeyNotifications         OBJECT IDENTIFIER ::= { hTPNotifications 0 }
hTPKeyNotificationObjects   OBJECT IDENTIFIER ::= { hTPNotifications 1 }

hFFKeyExpirationWarning NOTIFICATION-TYPE
        OBJECTS         { hStationID, hrSystemDate, 
                          hFFKMID,   hFFExpiration }
        STATUS          current
        DESCRIPTION
            "(U//FOUO) The notification from the HAIPE device to the
            HAIPE HMS indicating that a given Firefly key is going to
            expire within one month and does not contain a valid
            hFFNextVector.  This notification should be sent when the
            one month time is reached, and should be sent after
            startup for any key within the system which has less than
            one month left in its expiration window (and does not have
            a valid hFFNextVector assigned).

            (U//FOUO) The recommended hAuditConfigTable defaults for this
            notification are:
                ThrottlingEnabled: false
                NotifEnabled     : true"
        ::={ hTPKeyNotifications 1 }

hPPKKeyExpirationWarning NOTIFICATION-TYPE
        OBJECTS         { hStationID, hrSystemDate,
                          hPPKKeyExpirationWarningCount }
        STATUS          current
        DESCRIPTION
            "(U//FOUO) The notification from the HAIPE device to the
            HAIPE HMS indicating that PPK chains within the
            hPPKChainTable are going to expire within one month and
            the entries in the hPPKChainTable does not contain a valid
            next PPK with a higher hPPKChainOrder.  This notification
            should be sent when the one month time is reached, and
            should be sent after startup for at least one key within
            the system which has less than one month left in its
            expiration window.

            (U//FOUO) Once a HMS receives the notification, it should
            then examine the contents of the hPPKChainTable to
            deterimne which exact key chains are about to expire.

            (U//FOUO) The recommended hAuditConfigTable defaults for this
            notification are:
                ThrottlingEnabled: false
                NotifEnabled     : true"
        ::={ hTPKeyNotifications 2 }

hPPKKeyExpirationWarningCount OBJECT-TYPE
        SYNTAX      Unsigned32
        MAX-ACCESS  accessible-for-notify
        STATUS      current
        DESCRIPTION
            "(U//FOUO) The number of keys which are going to expire in
            one month."
        ::= { hTPKeyNotificationObjects 1 }


-- ********************************************************************
-- Security and traffic policy related processing
-- ********************************************************************

hOutputPacketPadding OBJECT-TYPE
        SYNTAX      INTEGER { fixedSize(1), randomSize(2), noPadding(3) }
        MAX-ACCESS  read-write
        STATUS      deprecated
        DESCRIPTION
            "(U//FOUO) The type of padding for output traffic.  It
            indicates whether the output traffic (CT) will be padded
            to a fixed packet length, a random packet length or not
            at all.
            
            (U//FOUO) Note: This object has been deprecated and
            packet padding is handled at the interface level by
            objects in the HAIPE IPv4 and IPv6 interface tables
            within the HAIPE-NETWORKING-MIB."
        DEFVAL { noPadding }
        ::= { hTPPolicyPacketProcessing 1 }

hOutputPacketFixedSize OBJECT-TYPE
        SYNTAX      Unsigned32
        MAX-ACCESS  read-write
        STATUS      deprecated
        DESCRIPTION
            "(U//FOUO) If hOutputPacketPadding is set to fixedSize,
            this object will indicate the actual fixed size of the
            packets to be sent.  Implementations will certainly not
            support the setting of all possible values to this object,
            and a wrongValue exception should be returned when an
            attempt to set this object to an unsupported value
            occurs.

            (U//FOUO) Note: This object has been deprecated and
            packet padding is handled at the interface level by
            objects in the HAIPE IPv4 and IPv6 interface tables
            within the HAIPE-NETWORKING-MIB."
        ::= { hTPPolicyPacketProcessing 2 }


-- ********************************************************************
-- Security Policy Database
-- Information on security policy.
-- ********************************************************************


HECNTreatment ::= TEXTUAL-CONVENTION 
    STATUS       current
    DESCRIPTION
        "(U//FOUO) The indication of how the Explicit Congestion
        Notification (ECN) bits are to be treated when encapsulation
        and de-encapsulation occurs.

        (U//FOUO) If set to disabled, when encapsulation takes place
        (i.e PT->CT traffic) the ECN bits must be set to (10) in the
        CT packet regardless of the values in the headers for the
        packet being encapsulated.  For CT->PT traffic, the inner
        headers are passed through unmodified.

        (U//FOUO) If set to congestionNotification, HAIPEs should
        follow the HAIPIS specification for Congestion Notification
        processing of the ECN bits in the post-decapsulation PT IP
        header.  PT->CT traffic should be treated the same as for
        disabled mode.

        (U//FOUO) If set to admissionControl, HAIPEs should follow
        the HAIPIS specification for Admission Control processing on
        PT->CT and CT->PT traffic.

        (U//FOUO) This is used for both IPv4 and IPv6 packets.  For
        IPv6 packets, the ECN bits are the 2 low/right-most bits of
        the Traffic Class (TC) header bits.  For IPv4 packets, the ECN
        bits are the low/right-most bits of two bits of the Type Of
        Service (TOS) bits."
    REFERENCE  "RFC3168 section 9.1.1"
    SYNTAX      INTEGER { disabled(1), congestionNotification(2), 
                          admissionControl(3) }


-- ********************************************************************
-- HAIPE SPD Rule Table
--

hTPiphRule  OBJECT IDENTIFIER ::= { hTPSecurityPolicyDatabase 1 }

hIPhRuleTableCount OBJECT-TYPE
    SYNTAX      Unsigned32
    MAX-ACCESS  read-only
    STATUS      current
    DESCRIPTION
        "(U//FOUO) The number of rows in the hIPhRuleTable."
     ::= { hTPiphRule 1 }


hIPhRuleTableLastChanged OBJECT-TYPE
    SYNTAX      TimeStamp
    MAX-ACCESS  read-only
    STATUS      current
    DESCRIPTION
        "(U//FOUO) The value of sysUpTime the last time any entry
         in the hIPhRuleTable was modified, created, or deleted by
         either SNMP or other management method (e.g. via an HMI).

         (U//FOUO) Managers can use this object to ensure that no
         changes to configuration of this table have happened since
         the last time it examined the table.

         (U//FOUO) A value of 0 indicates that no entry has been
         changed since the agent initialized."
     ::= { hTPiphRule 2 }

hIPhRuleTable   OBJECT-TYPE
    SYNTAX      SEQUENCE OF HIPhRuleEntry
    MAX-ACCESS  not-accessible
    STATUS      current
    DESCRIPTION
        "(U//FOUO) The table for configuring a HAIPE's
         Security Policy Database.  IP packets arriving on an
         interface should be checked against the Security Policy
         defined partly by the contents of this table to decide
         whether a Security Association should be created for this
         packet.

         (U//FOUO) In general the values for hIPhIfIndex,
         hIPhRulePacketDirection and hIPhRulePriority uniquely
         identify a rule for a given priority to be applied to packets
         traveling across a certain interface in a certain direction.

         (U//FOUO) HAIPE devices will have an SPD on each interface,
         regardless of where crypographic processing occurs within the
         device.  All cryptographic related rules (starting SAs, etc)
         will be only installed and listed on the CT interfaces of a
         device.  All PT interfaces must also contain a SPD, but the
         acceptable actions (hIPhRuleAction) for these rules will not
         include the protect actions.  Only bypass and
         discard are allowed actions for SPD rules on the PT
         interfaces.

         (U//FOUO) This description is only a configuration model,
         however, and implementations are not bound architectually to
         implement the internals of a device in exactly this manner.
         The only important result is that the resulting external
         appearance of this model represented by this MIB must conform
         to this described model."
    ::= { hTPiphRule 3 }

hIPhRuleEntry   OBJECT-TYPE
    SYNTAX      HIPhRuleEntry
    MAX-ACCESS  not-accessible
    STATUS      current
    DESCRIPTION
        "(U//FOUO) A row which describes the handling of IP
         messages arriving on a particular interface."
    INDEX { hIPhIfIndex, hIPhRulePacketDirection, hIPhRulePriority }
    ::= { hIPhRuleTable 1 }

HIPhRuleEntry ::= SEQUENCE
    {
	hIPhIfIndex                      InterfaceIndex,
	hIPhRulePacketDirection          INTEGER,
	hIPhRulePriority                 Unsigned32,
	hIPhRuleName                     SnmpAdminString,
	hIPhRuleSelectorName             SnmpAdminString,
	hIPhRuleAction                   INTEGER,
	hIPhRuleActionIndex              SnmpAdminString,
	hIPhRuleAdminStatus              TruthValue,
	hIPhRuleLastChanged              TimeStamp,
	hIPhRuleRowStatus                RowStatus
    }

hIPhIfIndex    OBJECT-TYPE
    SYNTAX     InterfaceIndex   
    MAX-ACCESS not-accessible
    STATUS     current
    DESCRIPTION
        "(U//FOUO) The index value which uniquely identifies the
         interface to which this entry is applicable.  The interface
         identified by a particular value of this index is the same
         interface as identified by the same value of the IF-MIB's
         ifIndex."
    ::= { hIPhRuleEntry 1 }

hIPhRulePacketDirection OBJECT-TYPE
    SYNTAX      INTEGER { incoming(1), outgoing(2) }
    MAX-ACCESS  not-accessible
    STATUS      current
    DESCRIPTION
        "(U//FOUO) The direction of packet traffic that this rule is
         applied to."
    ::= { hIPhRuleEntry 2 }

hIPhRulePriority OBJECT-TYPE
    SYNTAX      Unsigned32 (1..65535)
    MAX-ACCESS  not-accessible
    STATUS      current
    DESCRIPTION
        "(U//FOUO) The priority at which this rule is applied.
         Lower values have higher priority (e.g. a hIPhRulePriority
         of 1 will be processed before a hIPhRulePriority of 2)."
    ::= { hIPhRuleEntry 3 }

hIPhRuleName    OBJECT-TYPE
    SYNTAX      SnmpAdminString (SIZE(1..32))
    MAX-ACCESS  read-create
    STATUS      current
    DESCRIPTION
        "(U//FOUO) The administrative name for this rule."
    ::= { hIPhRuleEntry 4 }

hIPhRuleSelectorName OBJECT-TYPE
    SYNTAX      SnmpAdminString (SIZE(1..32))
    MAX-ACCESS  read-create
    STATUS      current
    DESCRIPTION
        "(U//FOUO) The selector name for this rule.

         (U//FOUO) This object indexes into the hIPhSelectorTable to
         indicate which selectors should be used to test against an
         incoming packet for this row (rule)."
    ::= { hIPhRuleEntry 5 }

hIPhRuleAction OBJECT-TYPE
    SYNTAX      INTEGER { unassigned(0),
                          discard(1),
                          bypass(2),
                          protectWithPPK(3),
                          protectWithFF(4),
                          deprecatedRespondWithFF(5)
                        }
    MAX-ACCESS  read-create
    STATUS      current
    DESCRIPTION
        "(U//FOUO) This indicates the action that should be taken on the packet 
         when a packet matches the set of selectors indicated by the value of
         this row's hIPhRuleSelectorName.

         (U//FOUO) Possible values include:

            (U//FOUO) discard:
                (U//FOUO) Discard the packet

            (U//FOUO) bypass:
                (U//FOUO) Bypass the packet.  An implementation may
                choose to not allow this action for a given selector.
                A wrongValue exception should be returned for this
                case either during the SET of the hIPhRuleAction
                column itself, if possible, or the instructions should
                be followed in the hIPhRuleRowStatus column instead
                about returning an inconsistentValue errors.  Bypass
                support may also require address mapping, per the
                hTPAddressMapping table.

            (U//FOUO) protectWithPPK:   
                (U//FOUO) Protect the packet within a PPK manual SA.
                The SA to use should have already been configured in
                the hTPSATable.  Which of these SAs to use should be
                based on the contents of that table and the contents
                of the HAIPE-NETWORKING-DISCOVERY-MIB::hTopologyTable
                and any other related discovery services.  EG, when a
                rule of this type is hit the discovery knowledge base
                should be consulted, which would ultimately end in a
                hTopologyTable entry which can then be used to select
                an indidual row in the hTPSATable through which the
                traffic should be sent.  New traffic triggering new
                discovery may result in the selectors for a given SA
                to be modified to incoperate the new traffic based on
                the discovery result.  The value of the
                hIPhRuleActionIndex column will indicate the PPK chain
                to use in the hPPKChainTable.  The PPK chain indicated
                will have the value of the hIPhRuleActionIndex column
                as it's hPPKChainID column.

                (U//FOUO) If the value of the hIPhRuleActionIndex
                column is a zero length string, then any PPK chain
                available and in use by an active SA may be used to
                protect the traffic to the remote destination.  This
                allows for different PPKs to be used with only a
                single rule and the discovery/topology system in
                combination with the active SAs can be used to select
                a SA (with a PPK) for use in protecting the traffic.

                (U//FOUO) This value is only legal for use on CT
                interfaces supporting cryptographic processing.
                Attempts to set this action to a rule on a PT or other
                interface type will result in a wrongValue exception
                being returned.

            (U//FOUO) protectWithFF:    
                (U//FOUO) Protect the packet within a FF SA.  The
                value of the hIPhRuleActionIndex index column will
                indicate which rows in the hIPhFFSATable to use to
                create the SA with by matching against rows with the
                hIPhRuleActionIndex value in the hIPhFFSAName.

                (U//FOUO) This value is only legal for use on CT
                interfaces supporting cryptographic processing.
                Attempts to set this action to a rule on a PT or other
                interface type will result in a wrongValue exception
                being returned.

        	(U//FOUO) For outgoing traffic on the CT interface,
        	this will likely start a new IKE negotiation (or
        	potentially continue an existing one for IKE message 3).
        	For incoming messages on the CT interface, this action
        	will trigger responding to the incoming IKE request.
          "
    DEFVAL { discard }
    ::= { hIPhRuleEntry 6 }

hIPhRuleActionIndex OBJECT-TYPE
    SYNTAX      SnmpAdminString (SIZE(0..32))
    MAX-ACCESS  read-create
    STATUS      current
    DESCRIPTION
        "(U//FOUO) This column indicates the lookup value into another
        table. This may be hIPhFFSATable or hPPKChainTable depending
        on the value of hIPhRuleAction.  See the DESCRIPTION for the
        hIPhRuleAction object for a more complete description.

        (U//FOUO) Note that this object is somewhat badly labeled by
        reusing the word 'Index'.  Please note that it is not
        referring to a SNMP Index, but rather an administrative named
        lookup value."
    ::= { hIPhRuleEntry 7 }

hIPhRuleAdminStatus OBJECT-TYPE
    SYNTAX      TruthValue
    MAX-ACCESS  read-create
    STATUS      current
    DESCRIPTION
        "(U//FOUO) The indication of whether this row should
         currently be used to associate filters on incoming IP
         packets to actions to take.  If true it should be applied
         to incoming IP packets on the associated interface.  If
         false, this row should ignored when processing the current
         packet."
    DEFVAL { true }
    ::= { hIPhRuleEntry 8 }

hIPhRuleLastChanged OBJECT-TYPE
    SYNTAX      TimeStamp
    MAX-ACCESS  read-only
    STATUS      current
    DESCRIPTION
        "(U//FOUO) The value of sysUpTime when this row was last
         modified or created either through SNMP SET's or by some
         other external means."
    ::= { hIPhRuleEntry 9 }

hIPhRuleRowStatus OBJECT-TYPE
    SYNTAX      RowStatus
    MAX-ACCESS  read-create
    STATUS      current
    DESCRIPTION
        "(U//FOUO) The status of this row, by which new entries may
        be created, or old entries deleted from this table.
        
        (U//FOUO) If an attempt to create a new row via createAndGo
        does not include a value for columns without defaults
        (hIPhRuleName and hIPhRuleSelectorName) for the new row, an
        inconsistentName error will be returned for this object.
        
        (U//FOUO) A row cannot be set to active while
        hIPhRuleSelectorName or hIPhRuleAction/hIPhRuleActionIndex do
        not point to active rows in their respective tables, or there
        are unmet requirements for the hIPhSelectorType for the
        hIPhSelectorTable row that hIPhRuleSelectorName points to (an
        inconsistentValue error will be returned for this object). In
        other words, if the associated value columns needed by a
        particular test have not been set, then attempting to change
        this row to an active state will result in an
        inconsistentValue error. See the hIPhSelectorType object
        description for further details for example.

        (U//FOUO) If a row cannot be set to active due to an
        unsupported combination of filter and/or action parameters
        restrictions due to implementation dependent restrictions
        the inconsistentValue error must be returned for this object
        when an attempt is made to set this object to active.

        (U//FOUO) If any column is set to an invalid or unsupported
        value (during row creation or any other time), a wrongValue
        error will be returned for that object.

        (U//FOUO) The value of this object has no effect on whether
        other objects in this row can be modified.

        (U//FOUO) The hIPhRuleSelectorName and
        hIPhRuleAction/hIPhRuleActionIndex objects of an active row
        may not be changed to values that are not valid, active rows
        in their respective tables (an inconsistentValue error will be
        returned the object).

        (U//FOUO) If a row is deleted or set to not-in-service then
        all associated SAs created under this rule must be deleted as
        well.  Any other value changes must also result in any created
        SAs under the previous rules being deleted."
    ::= { hIPhRuleEntry 10 }


-- ********************************************************************
-- SPD Selector Table

hTPiphSelector OBJECT IDENTIFIER ::= { hTPSecurityPolicyDatabase 2 }

hIPhSelectorTableCount OBJECT-TYPE
    SYNTAX      Unsigned32
    MAX-ACCESS  read-only
    STATUS      current
    DESCRIPTION
        "(U//FOUO) The number of rows in the hIPhSelectorTable."
     ::= { hTPiphSelector 1 }


hIPhSelectorTableLastChanged OBJECT-TYPE
    SYNTAX      TimeStamp
    MAX-ACCESS  read-only
    STATUS      current
    DESCRIPTION
        "(U//FOUO) The value of sysUpTime the last time any entry
         in the hIPhSelectorTable was modified, created, or deleted
         by either SNMP or other management method (e.g. via an HMI).

         (U//FOUO) Managers can use this object to ensure that no
         changes to configuration of this table have happened since
         the last time it examined the table.

         (U//FOUO) A value of 0 indicates that no entry has been
         changed since the agent initialized."
     ::= { hTPiphSelector 2 }

hIPhSelectorTable OBJECT-TYPE
    SYNTAX      SEQUENCE OF HIPhSelectorEntry
    MAX-ACCESS  not-accessible
    STATUS      current
    DESCRIPTION
        "(U//FOUO) The table for configuring a HAIPE's
         Security Policy Database.  IP packets arriving on an
         interface should be checked against the Security Policy
         defined partly by the contents of this table to decide
         whether a Security Association should be created for this
         packet.

         (U//FOUO) In general, a value for hIPhSelectorName is used
         to associate selectors that should be applied to a packet
         as indicated by a row in the hIPhRuleTable."
    ::= { hTPiphSelector 3 }


hIPhSelectorEntry OBJECT-TYPE
    SYNTAX      HIPhSelectorEntry
    MAX-ACCESS  not-accessible
    STATUS      current
    DESCRIPTION
        "(U//FOUO) A row which describes the handling of IP
         messages arriving on a particular interface."
    INDEX   { hIPhSelectorName }
    ::= { hIPhSelectorTable 1 }

HIPhSelectorEntry ::= SEQUENCE
    {
	hIPhSelectorName                 SnmpAdminString,
	hIPhSelectorType                 BITS,
	hIPhSelectorOpaques              BITS,
	hIPhSelectorIPVersion            InetAddressType,
	hIPhSelectorSrcAddressBegin      InetAddress,
	hIPhSelectorSrcAddressEnd        InetAddress,
	hIPhSelectorDstAddressBegin      InetAddress,
	hIPhSelectorDstAddressEnd        InetAddress,
	hIPhSelectorNextHeaderStart      Unsigned32,
	hIPhSelectorNextHeaderEnd        Unsigned32,
	hIPhSelectorNextHeaderOpt1Start  Unsigned32,
	hIPhSelectorNextHeaderOpt1End    Unsigned32,
	hIPhSelectorNextHeaderOpt2Start  Unsigned32,
	hIPhSelectorNextHeaderOpt2End    Unsigned32,
	hIPhSelectorDSCP                 OCTET STRING,
	hIPhSelectorFlowLabel            OCTET STRING,
	hIPhSelectorLastChanged          TimeStamp,
	hIPhSelectorRowStatus            RowStatus
    }

hIPhSelectorName OBJECT-TYPE
    SYNTAX      SnmpAdminString (SIZE(1..32))
    MAX-ACCESS  not-accessible
    STATUS      current
    DESCRIPTION
        "(U//FOUO) The administrative name for this filter. This
         object is the index into this table."
    ::= { hIPhSelectorEntry 1 }

hIPhSelectorType OBJECT-TYPE
    SYNTAX      BITS { sourceAddress(0), destinationAddress(1),
                       nextHeader(2), nextHeaderOpt1(3),
                       nextHeaderOpt2(4), dscp(5), flowlabel(6) }
    MAX-ACCESS  read-create
    STATUS      current
    DESCRIPTION
        "(U//FOUO) This defines the various tests that are used when
         evaluating a given filter.  

         (U//FOUO) The results of each test are ANDed together with
         each other and with the tests indicated by the
         hIPhSelectorOpaques object to produce the result of the
         entire filter.  When processing this filter, it is
         recommended for efficiency reasons that the filter halt
         processing the instant any of the specified tests fail.  

         (U//FOUO) With the exception of tests indicated by the
         hIPhSelectorOpaques column, any bit which is not set is
         equivalent to the ANY value discussed in 2401bis.

         (U//FOUO) Once a row is 'active', this object's value may
         not be changed unless all the required columns needed by
         any new selectors have been appropriately configured. The
         requirements for each selector are described below.

         (U//FOUO) A BIT value can not be set in this object if the
         corresponding BIT value in the hIPhSelectorOpaques column
         object is set.  e.g., if the nextHeader(2) bit is set in
         the hIPhSelectorOpaques column object, the corresponding
         nextHeader(2) bit can not be set in this object.  Any
         attempt to set such a value will result in an
         inconsistentValue error.

         (U//FOUO) If an attempt is made to set a value for this
         object that an agent does not understand, it should fail
         with a wrongValue error.

         (U//FOUO) The various tests definable in this table are as
         follows:

         (U//FOUO) sourceAddress:
           - (U//FOUO) Tests if the source address in the packet
             lies between the hIPhSelectorSrcAddressBegin and
             hIPhSelectorSrcAddressEnd objects.

             (U//FOUO) Note that setting these two objects to the
             same address will limit the search to the exact match
             of a single address.  The format and length of the
             address objects are defined by the
             hIPhSelectorIPVersion column.

             (U//FOUO) A notInService row in this table containing a
             hIPhSelectorType object with the sourceAddress object
             bit but without the hIPhSelectorIPVersion,
             hIPhSelectorSrcAddressBegin and
             hIPhSelectorSrcAddressEnd objects set will prevent this
             object from transitioning to the active state.

         (U//FOUO) destinationAddress:
           - (U//FOUO) Tests if the destination address in the
             packet lies between the hIPhSelectorDstAddressBegin and
             hIPhSelectorDstAddressEnd objects.  Note that setting
             these two objects to the same address will limit the
             search to the exact match of a single address.  The
             format and length of the address objects are defined by
             the hIPhSelectorIPVersion column.

             (U//FOUO) A notInService row in this table containing a
             hIPhSelectorType object with the destinationAddress
             object bit but without the hIPhSelectorIPVersion,
             hIPhSelectorDstAddressBegin and
             hIPhSelectorDstAddressEnd objects set will prevent this
             object from transitioning to the active state.

         (U//FOUO) nextHeader:
           - (U//FOUO) Tests if NextHeader/Protocol value falls in the
             range of hIPhSelectorNextHeaderStart to
             hIPhSelectorNextHeaderEnd.  Note, setting these two
             columns to the same value will limit the filter to match
             a single value of the NextHeader/Protocol field .
             Implementations may choose not to support a range, and if
             so should return a WrongValue exception during a SET to
             the headerEnd object.

             (U//FOUO) A notInService row in this table containing a
             hIPhSelectorType object with the nextHeader object bit
             set but without the hIPhSelectorHeaderStart and
             hIPhSelectorHeaderEnd objects set will prevent this
             object from transitioning to the active state.

         (U//FOUO) nextHeaderOpt1:
           - (U//FOUO) Tests if an optional value in the range
             between hIPhSelectorNextHeaderOpt1Start and
             hIPhSelectorNextHeaderOpt1End exists in an IP packet.
             This option value is based on the NextHeader/protocol
             of the packet.  Because of this, in order to be a valid
             filter, when the nextHeaderOpt1 bit is set, the
             nextHeader bit MUST also be set and the
             hIPhSelectorHeaderStart and hIPhSelectorHeaderEnd
             objects MUST be equal.  If the hIPhSelectorHeaderStart
             object is any of the values in the first column below,
             the option tested for by this filter is indicated in
             the second column:
            (U//FOUO)
                        udp: source port
                        tcp: source port
                       icmp: icmp message type
                   mobility: mobility header type
            (U//FOUO)

             (U//FOUO) In order for a row that is currently
             notInService to transition to an active state with the
             nextHeaderOpt1 set, the following requirements MUST be
             met:
             The nextHeader bit MUST be set.
             The nextHeaderStart and nextHeaderEnd objects MUST be
             set to valid values and be equal.
             The hIPhSelectorHeaderOpt1Start and
             hIPhSelectorHeaderOpt1End objects must have valid
             values.

         (U//FOUO) nextHeaderOpt2:
           - (U//FOUO) Tests if an optional value in the range
             between hIPhSelectorNextHeaderOpt2Start and
             hIPhSelectorNextHeaderOpt2End exists in an IP packet.
             This option value is based on the NextHeader/protocol
             of the packet.  Because of this, in order to be a valid
             filter, when the nextHeaderOpt2 bit is set, the
             nextHeader bit MUST also be set and the
             hIPhSelectorHeaderStart and hIPhSelectorHeaderEnd
             objects MUST be equal.  If the hIPhSelectorHeaderStart
             object is any of the values in the first column below,
             the option tested for by this filter is indicated in
             the second column:
             (U//FOUO)
                        udp: destination port
                        tcp: destination port
                       icmp: icmp message code
             (U//FOUO)
 
             (U//FOUO) In order for a row that is currently
             notInService to transition to an active state with the
             nextHeaderOpt2 set, the following requirements MUST be
             met:
             The nextHeader bit MUST be set.
             The nextHeaderStart and nextHeaderEnd objects MUST be
             set to valid values and be equal.
             The hIPhSelectorHeaderOpt2Start and
             hIPhSelectorHeaderOpt2End objects must have valid
             values.

         (U//FOUO) dscp:
           - (U//FOUO) Tests to see if the packet being processed is
             matched properly for the given dscp value.

             (U//FOUO) A notInService row in this table containing a
             hIPhSelectorType object with the dscp object bit but
             without the hIPhSelectorDSCP object set will prevent
             this object from transitioning to the active state.

         (U//FOUO) flowlabel:
           - (U//FOUO) Tests to see if the packet being processed is
             matched properly for the given IPv6 flowlabel value.

             (U//FOUO) A notInService row in this table containing a
             hIPhSelectorType object with the flowlabel object bit
             but without the hIPhSelectorFlowLabel object set will
             prevent this object from transitioning to the active
             state.

         (U//FOUO) icmp:
           - (U//FOUO) Tests to see if the packet matches particular
             ICMP message types.  To be a successful match, the
             packet must be an ICMP message (of either IPv4 or IPv6)
             and the IP version must match the hIPhSelectorIPVersion
             column and the ICMP message's type value must match the
             value of the hIPhSelectorICMPType column and the ICMP
             message's code must match the value in the
             hIPhSelectorICMPCode column.  Anything else will result
             in a negative result.

             (U//FOUO) A notInService row in this table containing a
             hIPhSelectorType object with the icmp object bit but
             without the hIPhSelectorIPVersion,
             hIPhSelectorICMPType, or hIPhSelectorICMPCode objects
             sets will prevent this object from transitioning to the
             active state.

         (U//FOUO) If any values of this object are unsupported by
         an implementation, than a wrongValue error should be
         returned upon a SET of one of these unsupported values."
    ::= { hIPhSelectorEntry 2 }

hIPhSelectorOpaques OBJECT-TYPE
    SYNTAX      BITS { deprecatedProtocol(0), nextHeader(1), nextHeaderOpt1(2),
                       nextHeaderOpt2(3) }
    MAX-ACCESS  read-create
    STATUS      current
    DESCRIPTION
        "(U//FOUO) This defines various OPAQUE tests that can be
         used to filter a packet.  An OPAQUE test is true when the
         fields selected via the set bits are not available for
         examination.  Some examples of reasons that a field may not
         be available are: the field may not exist in a fragment;
         the field may not exist for a given next layer protocol; or
         because prior application of IPsec may have encrypted the
         values.

         (U//FOUO) The results of each test are ANDed together with
         each other and with the tests indicated by the
         hIPhSelectorType object to produce the result of the
         entire filter.  When processing this filter, it is
         recommended for efficiency reasons that the filter halt
         processing the instant any of the specified tests fail.

         (U//FOUO) A BIT value can not be set in this object if the
         corresponding BIT value in the hIPhSelectorType column
         object is set.  e.g., if the nextHeader(2) bit is set in
         the hIPhSelectorType column object, the corresponding
         nextHeader(2) bit can not be set in this object.  Any
         attempt to set such a value will result in an
         inconsistentValue error.

         (U//FOUO) If an attempt is made to set a value for this
         object that an agent does not understand, it should fail
         with a wrongValue error.
  
         (U//FOUO) The various tests definable in this table are as
         follows:

         (U//FOUO) nextHeader:
           - (U//FOUO) Tests that the Next Layer Protocol value
             indicated by the 'Next Header' fields is not
             examinable.  Either the field does not exist in the
             packet or it is otherwise unavailable for examination.

             (U//FOUO) This setting is only available for IPv6
             packets.  This bit should only be set if the
             hIPhSelectorIPVersion object indicates IPv6.  If an
             attempt to set this bit is made while the
             hIPhSelectorIPVersion object does not indicate IPv6, an
             inconsistentValue error should be returned.

             (U//FOUO) Any values in the hIPhSelectorNextHeaderStart
             or hIPhSelectorNextHeaderEnd objects are ignored.

         (U//FOUO) nextHeaderOpt1:
           - (U//FOUO) Tests if a value in the packet cannot be
             examined.  Either the field does not exist in the
             packet or it is otherwise unavailable for examination.
             The value this test for is dependent on the
             hIPhSelectorNextHeader object.  When
             hIPhSelectorNameHeader is set to the value in the first
             column of the following table, the second column
             indicates that field that should be unexaminable.
             (U//FOUO)
                        udp: source port
                        tcp: source port
                       icmp: icmp message type
                   mobility: mobility header type
             (U//FOUO)

             (U//FOUO) In order for a row that is currently
             notInService to transition to an active state with the
             nextHeaderOpt1 bit set, the following requirements MUST
             be met:
             The nextHeader bit MUST NOT be set.  
             The hIPhSelectorNextHeaderStart object MUST be set to a
             valid value.
 
             (U//FOUO) Any values in the
             hIPhSelectorNextHeaderOpt1Start and
             hIPhSelectorNextHeaderOpt1End objects are ignored.

         (U//FOUO) nextHeaderOpt2:
           - (U//FOUO) Tests if a value in the packet cannot be
             examined.  Either the field does not exist in the
             packet or it is otherwise unavailable for examination.
             The value this test for is dependent on the
             hIPhSelectorNextHeader object.  When
             hIPhSelectorNextHeader is set to the value in the first
             column of the following table, the second column
             indicates that field that should be unexaminable.
             (U//FOUO)
                        udp: destination port
                        tcp: destination port
                       icmp: icmp message code
             (U//FOUO)
 
             (U//FOUO) In order for a row that is currently
             notInService to transition to an active state with the
             nextHeaderOpt2 bit set, the following requirements MUST
             be met: 
             The nextHeader bit MUST NOT be set.  
             The hIPhSelectorNextHeaderStart object MUST be set to a
             valid value.
 
             (U//FOUO) Any values in the
             hIPhSelectorNextHeaderOpt2Start and
             hIPhSelectorNextHeaderOpt2End objects are ignored.

         (U//FOUO) deprecatedProtocol:
           - (U//FOUO) This field value is a duplicate of the
             nextHeader field and should be considered deprecated from
             use.  Implementations should use the nextHeader value
             instead.

         (U//FOUO) If any values of this object are unsupported by
         an implementation, than a wrongValue error should be
         returned upon a SET of one of these unsupported values."
    ::= { hIPhSelectorEntry 3 }

hIPhSelectorIPVersion OBJECT-TYPE
    SYNTAX      InetAddressType
    MAX-ACCESS  read-create
    STATUS      current
    DESCRIPTION
        "(U//FOUO) The Internet Protocol version the addresses are
         to match against.  The value of this property determines
         the size and format of the hIPhSelectorSrcAddressBegin,
         hIPhSelectorSrcAddressEnd, hIPhSelectorDstAddressBegin, and
         hIPhSelectorDstAddressEnd objects.

         (U//FOUO) Values of unknown, ipv4z, ipv6z and dns are not
         legal values for this object."
    DEFVAL  { ipv6 }             -- XXX is this a correct default?
    ::= { hIPhSelectorEntry 4 }

hIPhSelectorSrcAddressBegin OBJECT-TYPE
    SYNTAX      InetAddress
    MAX-ACCESS  read-create
    STATUS      current
    DESCRIPTION
        "(U//FOUO) The starting address of a source address range
         that the packet must match against for this filter to be
         considered TRUE.

         (U//FOUO) This object is used only if sourceAddress is set
         in hIPhSelectorType."
    ::= { hIPhSelectorEntry 5 }

hIPhSelectorSrcAddressEnd OBJECT-TYPE
    SYNTAX      InetAddress
    MAX-ACCESS  read-create
    STATUS      current
    DESCRIPTION
        "(U//FOUO) The ending address of a source address range to
         check a packet against, where the starting is specified by
         the hIPhSelectorSrcAddressBegin object.  Set this column to
         the same value as the hIPhSelectorSrcAddressBegin column to
         get an exact single address match.  That is, the address
         range is inclusive.

         (U//FOUO) This object is used only if sourceAddress is set
         in hIPhSelectorType."
    ::= { hIPhSelectorEntry 6 }

hIPhSelectorDstAddressBegin OBJECT-TYPE
    SYNTAX      InetAddress
    MAX-ACCESS  read-create
    STATUS      current
    DESCRIPTION
        "(U//FOUO) The starting address of a destination address
         range that the packet must match against for this filter to
         be considered TRUE.

         (U//FOUO) This object is used only if destinationAddress is
         set in hIPhSelectorType."
    ::= { hIPhSelectorEntry 7 }

hIPhSelectorDstAddressEnd OBJECT-TYPE
    SYNTAX      InetAddress
    MAX-ACCESS  read-create
    STATUS      current
    DESCRIPTION
        "(U//FOUO) The ending address of a destination address range
         to check a packet against, where the first is specified by
         the hIPhSelectorDstAddressBegin object.  Set this column to
         the same value as the hIPhSelectorDstAddressBegin column to
         get an exact single address match.  That is, the address
         range is inclusive.

         (U//FOUO) This object is used only if destinationAddress is
         set in hIPhSelectorType."
    ::= { hIPhSelectorEntry 8 }

hIPhSelectorNextHeaderStart OBJECT-TYPE
        SYNTAX      Unsigned32 (0..255)
        MAX-ACCESS	 read-create
        STATUS		 current
        DESCRIPTION
            "(U//FOUO) The starting NextHeader/Protocol selector value
            for this filter. Implementations may choose not to support
            a range, and if so should return a WrongValue exception
            during a SET to the headerEnd object."
        DEFVAL { 0 }
        ::= { hIPhSelectorEntry 9 }

hIPhSelectorNextHeaderEnd OBJECT-TYPE
        SYNTAX      Unsigned32 (0..255)
        MAX-ACCESS	 read-create
        STATUS		 current
        DESCRIPTION
            "(U//FOUO) The ending NextHeader/Protocol selector value
            for this Filter. Implementations may choose not to support
            a range, and if so should return a WrongValue exception
            during a SET to the headerEnd object."
        DEFVAL { 255 }
        ::= { hIPhSelectorEntry 10 }

hIPhSelectorNextHeaderOpt1Start OBJECT-TYPE
        SYNTAX      Unsigned32
        MAX-ACCESS	 read-create
        STATUS		 current
        DESCRIPTION
            "(U//FOUO) The starting option value for selector range.
            This option value is based on the NextHeader/protocol of
            the packet.  If the NextHeader/protocol is any of the
            following, this column and the
            hIPhSelectorNextHeaderOpt1End indicates:

            (U//FOUO)
                        udp: source port
                        tcp: source port
                       icmp: icmp message type
                   mobility: mobility header type
            (U//FOUO)"
        ::= { hIPhSelectorEntry 11 }

hIPhSelectorNextHeaderOpt1End OBJECT-TYPE
        SYNTAX      Unsigned32
        MAX-ACCESS	 read-create
        STATUS		 current
        DESCRIPTION
            "(U//FOUO) The ending option value for the selector range."
        ::= { hIPhSelectorEntry 12 }

hIPhSelectorNextHeaderOpt2Start OBJECT-TYPE
        SYNTAX      Unsigned32
        MAX-ACCESS	 read-create
        STATUS		 current
        DESCRIPTION
            "(U//FOUO) The starting option value for selector range.
            This option value is based on the NextHeader/protocol of
            the packet.  If the NextHeader/protocol is any of the
            following, this column and the
            hIPhSelectorNextHeaderOpt2End indicates:

            (U//FOUO)
                        udp: destination port
                        tcp: destination port
                       icmp: icmp message code
            (U//FOUO)"
        ::= { hIPhSelectorEntry 13 }

hIPhSelectorNextHeaderOpt2End OBJECT-TYPE
        SYNTAX      Unsigned32
        MAX-ACCESS	 read-create
        STATUS		 current
        DESCRIPTION
            "(U//FOUO) The ending option value for the selector range."
        ::= { hIPhSelectorEntry 14 }

hIPhSelectorDSCP OBJECT-TYPE
    SYNTAX      OCTET STRING (SIZE(1))
    MAX-ACCESS  read-create
    STATUS      current
    DESCRIPTION
        "(U//FOUO) The DSCP value a packet must match against for
        this filter to be evaluated as true.  If support for this
        type of selector is not implemented, then a wrongValue error
        should be returned upon a SET to this object.

        (U//FOUO) The DSCP value used is garnered from the
        lower/right-most 6 bits of this octet.  Allowable values for
        this object should be in the range 0x00 - 0x3f.  Any attempt
        to set this object to a value outside of this range should
        fail with a wrong value error.

        (U//FOUO) This column is used for both IPv4 and IPv6
        packets.  For IPv6 packets, the DSCP bits are the
        high/left-most bits of the Traffic Class (TC) header bits.
        For IPv4, the DSCP bits are the high/left-most bits of Type
        Of Service (TOS) header bits.

        (U//FOUO) This object is used only if dscp is set in
        hIPhSelectorType."
    ::= { hIPhSelectorEntry 15 }

hIPhSelectorFlowLabel OBJECT-TYPE
    SYNTAX      OCTET STRING (SIZE(3))
    MAX-ACCESS  read-create
    STATUS      current
    DESCRIPTION
        "(U//FOUO) The FlowLabel value the packet must match against
        for this filter to be evaluated as true.  If support for this
        type of selector is not implemented, then a wrongValue error
        should be returned upon a SET to this object.

        (U//FOUO) Only the high/left-most 20 bits of this column are
        used.  Therefore, when setting this column, the last four
        bits in the last octet MUST be set to zero.  Any attempt to
        set the last four bits of this value to anything other than
        zero should result in a wrong value error.

        (U//FOUO) This object is used only if flowlabel is set in
        hIPhSelectorType."
    ::= { hIPhSelectorEntry 16 }

hIPhSelectorLastChanged OBJECT-TYPE
    SYNTAX      TimeStamp
    MAX-ACCESS  read-only
    STATUS      current
    DESCRIPTION
        "(U//FOUO) The value of sysUpTime when this row was last
         modified or created either through SNMP SET's or by some
         other external means."
    ::= { hIPhSelectorEntry 17 }

hIPhSelectorRowStatus OBJECT-TYPE
    SYNTAX      RowStatus
    MAX-ACCESS  read-create
    STATUS      current
    DESCRIPTION
        "(U//FOUO) The conceptual status of this row.

         (U//FOUO) A row may not be deleted while it is referenced
         by any active row in the hIPhRuleTable (an
         inconsistentValue error will be returned for this object).

         (U//FOUO) This object may not be created via createAndGo or
         set to active if the requirements of the hIPhSelectorType
         object are not met.  In other words, if the associated
         value columns needed by a particular test have not been
         set, then attempting to change this row to active or
         createAndGo will result in an inconsistentValue or
         inconsistentName error, respectively.  See the
         hIPhSelectorType object description for further details.

         (U//FOUO) If any column is set to an invalid or unsupported
         value (during row creation or any other time), a wrongValue
         error will be returned for that object.

         (U//FOUO) The value of this object has no effect on whether
         other objects in this row can be modified.

         (U//FOUO) Once a row is active, this object's value may not
         be changed unless all the appropriate columns needed by the
         new value to be imposed on this object have been
         appropriately configured (an inconsistentValue error will
         be returned for the object). See the hIPhSelectorType
         object description for further details."
    ::= { hIPhSelectorEntry 18 }


-- ********************************************************************
-- Security Policy Database
-- Information on SPD Action  policy.
-- ********************************************************************

hTPiphActions         OBJECT IDENTIFIER ::= { hTPSecurityPolicyDatabase 3 }

-- ********************************************************************
-- SPD Security Association Transform Actions

hTPiphSATransforms OBJECT IDENTIFIER ::= { hTPiphActions 2 }

-- ********************************************************************
-- FF Security Association Configuration
-- hTPiphFFSA
-- 

hTPiphFFSA             OBJECT IDENTIFIER ::= { hTPiphSATransforms 2 }
hTPiphFFSAKey          OBJECT IDENTIFIER ::= { hTPiphFFSA 1 }

-- ********************************************************************
-- hIPhFFSATable
-- holds the information for FF/EFF keys and points to the transform
-- values to use to create an SA.

hIPhFFSATableCount OBJECT-TYPE
    SYNTAX      Unsigned32
    MAX-ACCESS  read-only
    STATUS      current
    DESCRIPTION
        "(U//FOUO) The number of rows in the hIPhFFSATable."
     ::= { hTPiphFFSAKey 1 }

hIPhFFSATableLastChanged OBJECT-TYPE
    SYNTAX      TimeStamp
    MAX-ACCESS  read-only
    STATUS      current
    DESCRIPTION
        "(U//FOUO) The value of sysUpTime the last time any entry
         in the hIPhFFSATable was modified, created, or deleted by
         either SNMP or other management method (.eg., via an HMI).

         (U//FOUO) Managers can use this object to ensure that no
         changes to configuration of this table have happened since
         the last time it examined the table.

         (U//FOUO) A value of 0 indicates that no entry has been
         changed since the agent initialized."
     ::= { hTPiphFFSAKey 2 }

hIPhFFSATable OBJECT-TYPE
    SYNTAX      SEQUENCE OF HIPhFFSAEntry
    MAX-ACCESS  not-accessible
    STATUS      current
    DESCRIPTION
        "(U//FOUO) The table for configuring a HAIPE's
         Security Policy Database.  When a Security Association (SA)
         is indicated by the hIPhSelectorTable, the hIPhRuleTable
         table indicates the rows of this table that provide Firefly
         information used to negotiate that SA."
    ::= { hTPiphFFSAKey 3 }

hIPhFFSAEntry OBJECT-TYPE
    SYNTAX      HIPhFFSAEntry
    MAX-ACCESS  not-accessible
    STATUS      current
    DESCRIPTION
        "(U//FOUO) A row which describes the Firefly information
         needed to setup a Security Association with a remote HAIPE."
    INDEX   { hIPhFFSAName, hIPhFFSAPriority }
    ::= { hIPhFFSATable 1 }

HIPhFFSAEntry ::= SEQUENCE
    {
	hIPhFFSAName                     SnmpAdminString,
	hIPhFFSAPriority                 Unsigned32,
	hIPhFFSAFF                       KMID,
	hIPhFFSATransformsName           SnmpAdminString,
	hIPhFFSADSCP                     INTEGER,
	hIPhFFSADSCPValue                OCTET STRING,
	hIPhFFSAECN                      HECNTreatment,
	hIPhFFSAFlowLabel                INTEGER,
	hIPhFFSAFlowLabelValue           OCTET STRING,
	hIPhFFSADecrementTTL             TruthValue,
	hIPhFFSADIndexType               INTEGER,
	hIPhFFSALastChanged              TimeStamp,
	hIPhFFSARowStatus                RowStatus,
	hIPhFFSAPDUNEnabled              TruthValue,
	hIPhFFSAPHRDRate                 Unsigned32,
	hIPhFFSADFBit                    INTEGER,
	hIPhFFSAProcessFlowlabel         TruthValue,
	hIPhFFSARetryICMPCount           Unsigned32,
	hIPhFFSAConnectionType           INTEGER,
	hIPhFFSACTOutAddressType         InetAddressType,
	hIPhFFSACTOutAddress             InetAddress,
	hIPhFFSAPopulateFromPacket       BITS,
	hIPhFFSATransmissionType         INTEGER,
	hIPhFFSATransmissionRate         Unsigned32,
	hIPhFFSATransmissionSize         Unsigned32,
	hIPhFFSAFFUniversal              FFUniversalID,
	hIPhFFSAFFUniversalEdition       OCTET STRING,
	hIPhFFSATFCConfig                SnmpAdminString
    }


hIPhFFSAName    OBJECT-TYPE
    SYNTAX      SnmpAdminString (SIZE(1..32))
    MAX-ACCESS  not-accessible
    STATUS      current
    DESCRIPTION
        "(U//FOUO) The administrative name for this row.  This
         object along with hIPhFFSAPriority indexes this table.  When
         the hIPhRuleAction object in the hIPhRuleTable table is
         'protectWithFF' then the hIPhRuleActionIndex column in the
         hIPhRuleTable will point to values in this column to indicate
         a set of one or more key vectors and their associated
         transforms to negotiate an SA."
    ::= { hIPhFFSAEntry 1 }

hIPhFFSAPriority OBJECT-TYPE
    SYNTAX      Unsigned32 (1..4294967295)
    MAX-ACCESS  not-accessible
    STATUS      current
    DESCRIPTION
        "(U//FOUO) The priority at which this set of SA negotiation
        parameters is used to create an SA.

        (U//FOUO) This object is an index into this table.  Lower
        values have higher priority (e.g. 1 is the highest
        priority.)"
    ::= { hIPhFFSAEntry 2 }

hIPhFFSAFF      OBJECT-TYPE
    SYNTAX      KMID
    MAX-ACCESS	 read-create
    STATUS		 current
    DESCRIPTION
        "(U//FOUO) The key to use with this SA.  This column,
        hIPhFFSAFFUniversal, and hIPhFFSAFFUniversalEdition are used
        to indicate a row in the hFireflyTable.  The hFireflyTable
        row indicated can be used to look up more key information.

        (U//FOUO) Some implementations may only support using this
        column to locate additional key information in the
        hFireflyTable.  If this is the only column being used to
        indicate key information in the hFireflyTable and a KMID
        conflict occurs (i.e. matching KMID values in separate
        vectors within the hFireflyTable), the action associated
        with this row MUST fail."
    ::= { hIPhFFSAEntry 3 }

hIPhFFSATransformsName OBJECT-TYPE
    SYNTAX      SnmpAdminString (SIZE(1..32))
    MAX-ACCESS	 read-create
    STATUS		 current
    DESCRIPTION
        "(U//FOUO) The Transforms Name for this SA.  This object
         indexes into the hIPhFFSATransformsTable to indicate the
         set of transforms to use with the key indicated by this
         row to create an SA."
    ::= { hIPhFFSAEntry 4 }

hIPhFFSADSCP    OBJECT-TYPE
    SYNTAX      INTEGER { set(1), deprecatedandmask(2), acceptlist(3) }
    MAX-ACCESS	 read-create
    STATUS		 current
    DESCRIPTION
        "(U//FOUO) The indication of how the Differentiated
        Service Code Points (DSCP) bits in a packet's header should
        be treated.

        (U//FOUO) If this column is set to set(1), the column
        hIPhFFSADSCPValue should only be 1 octet in length and the
        DSCP value garnered from this octet is placed within the
        outgoing packet's DSCP header value.

        (U//FOUO) If this column is set to acceptlist(3), the column
        hIPhFFSADSCPValue should be 8 octets in length and it will
        provide a list of acceptable DSCP values represented as a 64
        bit vector.  Each bit of hIPhFFSADSCPValue will represent one
        acceptable DSCP value. If the incoming packet's DSCP value
        matches, that value is placed in the outgoing packet.  If
        none of the values in the list match an incoming packet's
        DSCP value, the outgoing packet's DSCP value is set to all
        0's.

        (U//FOUO) This column is used for both IPv4 and IPv6
        packets.  For IPv6 packets, the DSCP bits are the
        high/left-most bits of the Traffic Class (TC) header bits.
        For IPv4, the DSCP bits are the high/left-most bits of Type
        Of Service (TOS) header bits.

        (U//FOUO) Note: This column is only pertinent for traffic
        being encrypted (i.e. PT->CT traffic).

        (U//FOUO) DEPRECATED: If this column is set to
        deprecatedandmask(2), the column hIPhFFSADSCPValue should only
        be 1 octet in length and the DSCP value garnered from this
        octet is bitwise ANDed with the incoming packet's DSCP header
        value and the result set within the outgoing packet's DSCP
        header.  This enum is deprecated and not required for HAIPE
        3.0+ support."
    DEFVAL { set }
    ::= { hIPhFFSAEntry 5 }

hIPhFFSADSCPValue  OBJECT-TYPE
    SYNTAX      OCTET STRING (SIZE (1|8))
    MAX-ACCESS	 read-create
    STATUS		 current
    DESCRIPTION
        "(U//FOUO) The Differentiated Service Code Points (DSCP)
        value for this Firefly key SA.

        (U//FOUO) The use of this value is dependent on the value
        of the hIPhFFSADSCP column in this row.  

       (U//FOUO) If the hIFhFFSADSCP column is set to set(1), this
        value should be one octet in length in the range 0x00 -
        0x3f.  The DSCP value garnered from the lower/right-most 6
        bits of this octet is placed within the outgoing packet's
        Differentiated Service Code Points (DSCP) header value.

        (U//FOUO) When column hIFhFFSADSCP is set to set(1) or
        deprecatedandmask(2), this column is only allowed to be a single octet
        length value in the range 0x00 - 0x3f inclusive.  Any
        attempt to set this column to value outside of this range
        should, in this case, fail with an invalid value error.

        (U//FOUO) If the hIFhFFSADSCP column is set to
        acceptlist(3), this value should be 8 octets in length and
        will provide a list of acceptable DSCP values represented as
        a 64-bit vector.  Each bit of this value represents one
        acceptable DSCP value and matches when the bit is set, i.e.
        '1'.  If the incoming packet's DSCP value matches a value
        represented in the vector, that value is placed in the
        outgoing packet.  If none of the values in the vector match
        an incoming packet's DSCP value, the outgoing packet's DSCP
        value is set to all 0's.

        (U//FOUO)64 bit vector representation:
        Bit set         matches DSCP value
        0                       000000
        1                       000001
        2                       000010
        .                       .
        .                       .
        .                       .
        62                      111110
        63                      111111

        (U//FOUO) This column is used for both IPv4 and IPv6
        packets.  For IPv6 packets, the DSCP bits are the
        high/left-most bits of the Traffic Class (TC) header bits.
        For IPv4, the DSCP bits are the high/left most bits of Type
        Of Service (TOS) header.

        (U//FOUO) Note: This column is only pertinent for traffic
        being encrypted (i.e. PT->CT traffic).

        (U//FOUO) DEPRECATED: If the hIFhFFSADSCP column is set to
        deprecatedandmask(2), this value should be one octet in length
        in the range 0x00 - 0x3f.  The DSCP value garnered from the
        lower/right-most 6 bits of this octet is bitwise ANDed with
        the incoming packet's DSCP header value and the result set
        within the outgoing packet's DSCP header."
    DEFVAL { '00'h }
    ::= { hIPhFFSAEntry 6 }

hIPhFFSAECN     OBJECT-TYPE
    SYNTAX      HECNTreatment
    MAX-ACCESS	 read-create
    STATUS		 current
    DESCRIPTION
        "(U//FOUO) The indication of how the Explicit Congestion
        Notification (ECN) bits should be treated within this SA."
    DEFVAL { disabled }
    ::= { hIPhFFSAEntry 7 }

hIPhFFSAFlowLabel OBJECT-TYPE
    SYNTAX      INTEGER { set(1), deprecatedandmask(2), bypass(3) }
    MAX-ACCESS	 read-create
    STATUS		 current
    DESCRIPTION
        "(U//FOUO) The indication of how the twenty Flow Label bits in
        a IPv6 packet should be treated.  If this column is set to
        set(1), the hIPhFFSAFlowLabelValue column will be placed
        within the outgoing packet's Flow Label header value.  If this
        column is set to bypass(3) then the flowlabel is bypassed from
        PT->CT.

        (U//FOUO) Note: This column is only pertinent for IPv6
        traffic that is being encrypted (i.e. PT->CT traffic).

        (U//FOUO) DEPRECATED: If this column is set to
        deprecatedandmask(2), the hIPhFFSAFlowLabelValue column will
        be bitwise ANDed with the incoming packet's Flow Label header
        value and the result set within the outgoing packet's Flow
        Label header."
    DEFVAL { set }
    ::= { hIPhFFSAEntry 8 }

hIPhFFSAFlowLabelValue OBJECT-TYPE
    SYNTAX      OCTET STRING (SIZE (0..768))
    MAX-ACCESS	 read-create
    STATUS		 current
    DESCRIPTION
        "(U//FOUO) The flow label value for this Firefly Key SA.
        
        (U//FOUO) The use of this value is dependent on the value
        of the hIPhFFSAFlowLabel column in this row.

        
        (U//FOUO) when set(1):

          (U//FOUO) If the hIPhFFSAFlowLabel column is set to set(1),
          this value will be placed within the outgoing packet's Flow
          Label header value.

          (U//FOUO) Only the high/left-most 20 bits of this column are
          used.  Therefore, when setting this column, the last four
          bits in the last octet MUST be set to zero.  Any attempt to
          set the last four bits of this value to anything other than
          zero should result in a wrong value exception.

        (U//FOUO) when bypass(3):

          (U//FOUO) If the hIPhFFSAFlowLabel column is set to
          bypass(3), this value will be a list of acceptable values to
          bypass.  The encoding is a sequence of 3-octet values where
          each 3-octet component is a flow label value to pass Only
          the high/left-most 20 bits of each 3-octet value is used and
          the left four bits MUST be set to zero).  A 0-length will
          indicate that all flow-label values should be bypassed.

          (U//FOUO) Any attempt to set this value to an illegal
          encoding sent should return a wrong value exception.  An
          inconsistent value exception should be returned on an
          unsupported value.

        (U//FOUO) Note: This column is only pertinent for IPv6
        traffic that is being encrypted (i.e. PT->CT traffic).

        (U//FOUO) DEPRECATED: If the hIPhFFSAFlowLabel column is set
        to andmask(2), this value will be bitwise ANDed with the
        incoming packet's Flow Label header value and the result set
        within the outgoing packet's Flow Label header."
    DEFVAL { '000000'h }
    ::= { hIPhFFSAEntry 9 }

hIPhFFSADecrementTTL OBJECT-TYPE
    SYNTAX          TruthValue
    MAX-ACCESS	 read-create
    STATUS		 current
    DESCRIPTION
        "(U//FOUO) The indication of whether the time-to-live
        value is decremented as traffic passes through the SA."
    ::= { hIPhFFSAEntry 10 }

hIPhFFSADIndexType OBJECT-TYPE
    SYNTAX      INTEGER { reserved(1), spiDest(2), spiDestSrc(3),
                          reservedDontUse(4) }
    MAX-ACCESS	 read-create
    STATUS		 current
    DESCRIPTION
        "(U//FOUO) The Index type of the SAD entry.

        (U//FOUO) This object indicates whether an SAD entry
        created from this row requires an SA lookup to match
        the SPI and destination address; or the SPI, destination and
        source addresses.

        (U//FOUO) Note that the SAD entry with the longest matching
        SA identifier will be selected. That is, a matching SAD
        entry with an index type of spiDestSrc will be selected
        before an entry with an index type of spiDest."
    REFERENCE "2401bis section 4.1"
    DEFVAL { spiDest }
    ::= { hIPhFFSAEntry 11 }

hIPhFFSALastChanged OBJECT-TYPE
    SYNTAX      TimeStamp
    MAX-ACCESS  read-only
    STATUS		 current
    DESCRIPTION
        "(U//FOUO) The value of sysUpTime when this row was last
         modified or created either through SNMP SET's or by some
         other external means."
    ::= { hIPhFFSAEntry 12 }

hIPhFFSARowStatus OBJECT-TYPE
    SYNTAX      RowStatus
    MAX-ACCESS	 read-create
    STATUS		 current
    DESCRIPTION
        "(U//FOUO) The status of the row, by which new entries may
        be created, or old entries deleted from this table.

        (U//FOUO) If an attempt to create a new row via createAndGo
        does not include values for columns without defaults,
        (e.g. hIPhFFSAFF), an inconsistentName error will be returned
        for this object.

        (U//FOUO) A row cannot be set to active while the
        appropriate key, hIPhFFSAFF, does not contain a valid value
        of an active row in the corresponding table (an
        inconsistentValue error will be returned for this object).

        (U//FOUO) If any column is set to an invalid or unsupported
        value (during row creation or any other time), a wrongValue
        error will be returned for that object.

        (U//FOUO) The value of this object has no effect on whether
        other objects in this row can be modified.

        (U//FOUO) An active row cannot be changed to an inconsistent
        state (an inconsistentValue error will be returned for the
        object).

        (U//FOUO) An active row may not be deleted while it is
        referenced by any active row in the hTPiphRuleTable (an
        inconsistentValue error will be returned for this object)."
    ::= { hIPhFFSAEntry 13 }

hIPhFFSAPDUNEnabled OBJECT-TYPE
    SYNTAX      TruthValue
    MAX-ACCESS	 read-create
    STATUS		 current
    DESCRIPTION
        "(U//FOUO) The indication of whether Peer Destination Unreachable
        Notification messages should be transmitted for this SA."
    ::= { hIPhFFSAEntry 14 }

hIPhFFSAPHRDRate OBJECT-TYPE
    SYNTAX      Unsigned32
    UNITS       "Seconds"
    MAX-ACCESS	 read-create
    STATUS		 current
    DESCRIPTION
        "(U//FOUO) The rate at which Peer HAIPE Reachability Detection
        messages should be transmitted for this SA (defined by the
        number of seconds between sent messages).  A value of zero
        indicates that the messages should never be sent (i.e. they
        are disabled)."
    DEFVAL { 0 }
    ::= { hIPhFFSAEntry 15 }

hIPhFFSADFBit  OBJECT-TYPE
    SYNTAX      INTEGER { set(1), clear(2), copy(3) }
    MAX-ACCESS  read-create
    STATUS      current
    DESCRIPTION
        "(U//FOUO) The indication of how to handle the DF bit
        created in the CT packet: set it; clear it, or copy the DF
        bit from the PT packet.
        
        (U//FOUO) Note: This column is only pertinent traffic that
        is being encrypted (i.e. PT->CT traffic)."
    DEFVAL { clear }
    ::= { hIPhFFSAEntry 16 }

hIPhFFSAProcessFlowlabel  OBJECT-TYPE
    SYNTAX      TruthValue
    MAX-ACCESS  read-create
    STATUS      deprecated
    DESCRIPTION
        "(U//FOUO) The indication of whether an SA should process IPv6
        Flow Labels."
    ::= { hIPhFFSAEntry 17 }

hIPhFFSARetryICMPCount  OBJECT-TYPE
    SYNTAX      Unsigned32
    MAX-ACCESS  read-create
    STATUS      current
    DESCRIPTION
        "(U//FOUO) The number of successive missed PT ICMP Echo Requests
        that will cause the HAIPE to mark this SA endpoint as unreachable."
    ::= { hIPhFFSAEntry 18 }

hIPhFFSAConnectionType OBJECT-TYPE
    SYNTAX      INTEGER { transportct(1), tunnel(2),
                          transportsa(3) }
    MAX-ACCESS  read-create
    STATUS      current
    DESCRIPTION
        "(U//FOUO) The connection type of this Security Association
        (SA).

        (U//FOUO) A type of tunnel(2) indicates a tunnel type
        connection.

        (U//FOUO) A type of transportsa(3) indicates a transport
        type connection that is differentiated by the SA the packet
        travels through.  The hTPTransportMapTable is used to map
        the SA of an arriving packet on the Cipher Text (CT)
        interface to the Plain Text (PT) source and destination
        addresses that are placed in the packet header.

        (U//FOUO) A type of transportct(1) indicates a transport
        type connection that is differentiated by the Cipher Text
        (CT) destination address.  The hTPAddressMapTable is used to
        map the source and destination CT addresses of a packet
        arriving on the CT interface to the PT addresses placed in
        the packet header."
    DEFVAL { tunnel }
    ::= { hIPhFFSAEntry 19 }

hIPhFFSACTOutAddressType OBJECT-TYPE
    SYNTAX      InetAddressType
    MAX-ACCESS  read-create
    STATUS      current
    DESCRIPTION
        "(U//FOUO) This sets the address type of the address to use
        for the outgoing CT address for this SA.  If left unset by the
        manager it will default to an appropriate address from the
        HAIPE's addresses assigned to the CT interface."
    ::= { hIPhFFSAEntry 20 }

hIPhFFSACTOutAddress OBJECT-TYPE
    SYNTAX      InetAddress
    MAX-ACCESS  read-create
    STATUS      current
    DESCRIPTION
        "(U//FOUO) This sets the address to use for the outgoing CT
        address for this SA.  If left unset by the manager it will
        default to an appropriate address from the HAIPE's addresses
        assigned to the CT interface. "
    ::= { hIPhFFSAEntry 21 }

hIPhFFSAPopulateFromPacket OBJECT-TYPE
    SYNTAX      BITS { srcAddress(0), dstAddress(1), 
                       nextHeader(2), protoOpt1(3), protoOpt2(4),
                       dscp(5), flowLabel(6) } 
    MAX-ACCESS  read-create
    STATUS      current
    DESCRIPTION
        "(U//FOUO) This field indicates whether the new SA is created
        with selectors based on the packet that triggered the SA
        creation, or whether the selector values from the SPD rule
        should be used.

            (U//FOUO)
               srcAdrdess: the source address of the triggering packet
               dstAddress: the destination address of the triggering packet
               nextHeader: the nextHeader/protocol field
               protoOpt1:  Based on the nextHeader/protocol field:
                        udp: source port
                        tcp: source port
                       icmp: icmp message type
                   mobility: mobility header type
               protoOpt2:  Based on the nextHeader/protocol field:
                        udp: destination port
                        tcp: destination port
                       icmp: icmp message code
               dscp: the dscp value of the triggering packet.
               flowLabel: the flow label value of the triggering packet.
            (U//FOUO)

        (U//FOUO) If a bit is set to 1, then a unique value for
        that selector attribute should be placed into the SA selector
        set.

        (U//FOUO) If a bit is not set, then the values to build the SA
        selectors from must be taken from the SPD selector set
        instead.

        (U//FOUO) Thus if the SPD specifies a selector range of
        nextHeader values 1-10, and a TCP packet (nextHeader = 6)
        triggers the SA creation then if the PFP bit will dictate
        whether the range (1-10) is used for the SA selection if the
        nextHeader bit is 0, or 6-6 is used if the nextHeader bit is
        set.

        (U//FOUO) HAIPE Discovery adds another complication to this
        process, as the SPD may have a selector set which is different
        than discovery may return results for.  In this case, the
        intersection of the discovery results and the SPD selectors
        should be used.  EG, If the srcAddress bit is 0 the SPD
        selectors specify a source range of 10.0.1.0-10.0.2.255 but
        discovery returns only 10.0.1.0 - 10.0.1.255 is behind the
        remote gateway, then only the discovery results should be used
        in the built SA selectors.  However, if discovery returned
        10.0.0.0-10.255.255.255 was the behind the remote gateway,
        then the SPD selectors would have to be used, being the
        smaller of the two.  Overlaps would have to be the subset of
        both of them."
    REFERENCE "2401bis Section 4.4.1"
    ::= { hIPhFFSAEntry 22 }

hIPhFFSATransmissionType OBJECT-TYPE
    SYNTAX      INTEGER { regular(1), required(2), random(3) }
    MAX-ACCESS  read-create
    STATUS      deprecated
    DESCRIPTION
        "(U//FOUO) This object is deprecated. 
        New implementations should use the hTPTFCConfigTable with 
        hIPhFFSATFCConfig and hTPSATFCConfig to configure TFC.

        (U//FOUO) The type of transmission mechansim SAs created from
        this action will use."
    DEFVAL { regular }
    ::= { hIPhFFSAEntry 23 }

hIPhFFSATransmissionRate OBJECT-TYPE
    SYNTAX      Unsigned32
    UNITS       "packets/second"
    MAX-ACCESS  read-create
    STATUS      deprecated
    DESCRIPTION
        "(U//FOUO) This object is deprecated. 
        New implementations should use the hTPTFCConfigTable with 
        hIPhFFSATFCConfig and hTPSATFCConfig to configure TFC.

        (U//FOUO) The rate of transmission for created SAs when
        hIPhFFSATransmissionType is set to required ."
    ::= { hIPhFFSAEntry 24 }

hIPhFFSATransmissionSize OBJECT-TYPE
    SYNTAX      Unsigned32
    UNITS       "octets"
    MAX-ACCESS  read-create
    STATUS      deprecated
    DESCRIPTION
        "(U//FOUO) This object is deprecated. 
        New implementations should use the hTPTFCConfigTable with 
        hIPhFFSATFCConfig and hTPSATFCConfig to configure TFC.

        (U//FOUO) The size of transmission for created SAs when
        hIPhFFSATransmissionType is set to required.  This setting
        will force the SA to use this value instead of the global
        hOutputPacketFixedSize object setting if
        hIPhFFSATransmissionType is set to required."
    ::= { hIPhFFSAEntry 25 }

hIPhFFSAFFUniversal      OBJECT-TYPE
    SYNTAX      FFUniversalID
    MAX-ACCESS	 read-create
    STATUS		 current
    DESCRIPTION
        "(U//FOUO) The key to use with this SA.  This column,
        hIPhFFSAFF, and hIPhFFSAFFUniversalEdition are used to
        indicate a row in the hFireflyTable.  The hFireflyTable row
        indicated can be used to look up more key information."
    ::= { hIPhFFSAEntry 26 }

hIPhFFSAFFUniversalEdition  OBJECT-TYPE
    SYNTAX      OCTET STRING (SIZE(2))
    MAX-ACCESS	 read-create
    STATUS		 current
    DESCRIPTION
        "(U//FOUO) The key to use with this SA.  This column,
        hIPhFFSAFF, and hIPhFFSAFFUniversal are used to indicate a
        row in the hFireflyTable.  The hFireflyTable row indicated
        can be used to look up more key information."
    ::= { hIPhFFSAEntry 27 }

hIPhFFSATFCConfig  OBJECT-TYPE
    SYNTAX       SnmpAdminString (SIZE(0..32))
    MAX-ACCESS	 read-create
    STATUS		 current
    DESCRIPTION
        "(U//FOUO) The TFC configuration to be used by SAs created
        from this entry.  

        (U//FOUO) If populated, the value of this object 
        indicates which row in the hTPTFCConfigTable is to be used.
        This value must match the hTPTFCConfigName index value of the
        desired configuration.

        (U//FOUO) If this object is not populated, set to a zero
        length empty string, or set to a value which does not exist
        in the hTPTFCConfigTable, then no TFC mechanisms will be used 
        by SAs created from this entry."

    ::= { hIPhFFSAEntry 28 }


-- ********************************************************************
-- hIPhFFSATransformsTable
-- holds the information for the individual transforms.

hTPiphFFSATransforms   OBJECT IDENTIFIER ::= { hTPiphFFSA 2 }

hIPhFFSATransformsTableCount OBJECT-TYPE
    SYNTAX      Unsigned32
    MAX-ACCESS  read-only
    STATUS      current
    DESCRIPTION
        "(U//FOUO) The number of rows in the hIPhFFSATransformsTable."
     ::= { hTPiphFFSATransforms 1 }

hIPhFFSATransformsTableLastChanged OBJECT-TYPE
    SYNTAX      TimeStamp
    MAX-ACCESS  read-only
    STATUS      current
    DESCRIPTION
        "(U//FOUO) The value of sysUpTime the last time any entry
         in the hIPhFFSATransformsTable was modified, created, or
         deleted by either SNMP or other management method (e.g.,
         via an HMI).

         (U//FOUO) Managers can use this object to ensure that no
         changes to configuration of this table have happened since
         the last time it examined the table.

         (U//FOUO) A value of 0 indicates that no entry has been
         changed since the agent initialized."
     ::= { hTPiphFFSATransforms 2 }

hIPhFFSATransformsTable OBJECT-TYPE
    SYNTAX      SEQUENCE OF HIPhFFSATransformsEntry
    MAX-ACCESS  not-accessible
    STATUS      current
    DESCRIPTION
        "(U//FOUO) The table for configuring a HAIPE's
         Security Policy Database.  When a Security Association
         (SA) is indicated by the hIPhSelectorTable, this table
         indicates the transforms to use to set up a Firefly SA."
    ::= { hTPiphFFSATransforms 3 }

hIPhFFSATransformsEntry OBJECT-TYPE
    SYNTAX      HIPhFFSATransformsEntry
    MAX-ACCESS  not-accessible
    STATUS      current
    DESCRIPTION
        "(U//FOUO) A row which describes the properties of a
         transform to use to setup a Security Association with a
         remote HAIPE."
    INDEX   { hIPhFFSATransformName, hIPhFFSATransformPriority }
    ::= { hIPhFFSATransformsTable 1 }

HIPhFFSATransformsEntry ::= SEQUENCE
    {
	hIPhFFSATransformName            SnmpAdminString,
	hIPhFFSATransformPriority        Unsigned32,
	hIPhFFSATransformEncryptAlgorithm HaipeEncryptionAlgorithm,
	hIPhFFSATransformKeyUpdateMethod INTEGER,
	hIPhFFSATransformKeyUpdateFrequency Unsigned32,
	hIPhFFSATransformCryptoBlockSize Unsigned32,
	hIPhFFSATransformLastChanged     TimeStamp,
	hIPhFFSATransformRowStatus       RowStatus,
	hIPhFFSATransformESN             TruthValue,
	hIPhFFSATransformIntegrityAlgorithm HaipeIntegrityAlgorithm,
	hIPhFFSATransformHashAlgorithm   HaipeHashAlgorithm,
	hIPhFFSATransformAuthenticationAlgorithm HaipeAuthenticationAlgorithm,
	hIPhFFSATransformICV             Unsigned32
    }

hIPhFFSATransformName OBJECT-TYPE
    SYNTAX      SnmpAdminString (SIZE(1..32))
    MAX-ACCESS  not-accessible
    STATUS      current
    DESCRIPTION
        "(U//FOUO) The administrative name for this row.  This
         object indexes into the hIPhFFSATransformsTable and
         indicates a set of 1+ transforms to use to create an SA."
    ::= { hIPhFFSATransformsEntry 1 }

hIPhFFSATransformPriority OBJECT-TYPE
    SYNTAX      Unsigned32 (1..65535)
    MAX-ACCESS  not-accessible
    STATUS      current
    DESCRIPTION
        "(U//FOUO) The priority at which this transform is applied within
        a set of transforms. This object is an index into this table.
        Lower values have higher priority (e.g. 1 is the highest priority.)"
    ::= { hIPhFFSATransformsEntry 2 }

hIPhFFSATransformEncryptAlgorithm OBJECT-TYPE
    SYNTAX      HaipeEncryptionAlgorithm
    MAX-ACCESS  read-create
    STATUS      current
    DESCRIPTION
        "(U//FOUO) The encryption type to use with this transform."
    DEFVAL  { medley }
    ::= { hIPhFFSATransformsEntry 3 }

hIPhFFSATransformKeyUpdateMethod OBJECT-TYPE
    SYNTAX      INTEGER { deprecatedmtekUpdate(1), mtekMtek(2) }
    MAX-ACCESS  read-create
    STATUS      current
    DESCRIPTION
        "(U//FOUO) The key update method to use to update the TEK
        for SA's created by this row.

        (U//FOUO) The mtekUpdated method is now deprecated.  The
        hIPhFFSATransformKeyUpdateMethod object is not deprecated,
        however, to provide for legacy support as well as to leave
        room for future expansion if needed.  Implementation of just
        the mtekMtek value should be trivial."
    DEFVAL { mtekMtek }
    ::= { hIPhFFSATransformsEntry 4 }

hIPhFFSATransformKeyUpdateFrequency OBJECT-TYPE
    SYNTAX      Unsigned32 (240..1440)
    MAX-ACCESS  read-create
    STATUS      current
    DESCRIPTION
        "(U//FOUO) The frequency at which TEK's should be updated in
         minutes.  The default and maximum value is 24 hours and the
         minimum is 4 hours.  For HAIPE's that do not allow configuration
         of this object, when an attempt is made to set this value, a
         notWritable error should be returned."
    DEFVAL { 1440 }
    ::= { hIPhFFSATransformsEntry 5 }

hIPhFFSATransformCryptoBlockSize OBJECT-TYPE
    SYNTAX      Unsigned32
    MAX-ACCESS  read-create
    STATUS      current
    DESCRIPTION
        "(U//FOUO) The Crypto Block Size in bytes for this transform.
        The current valid values for this object are: 4,8, and 48."
    DEFVAL { 4 }
    ::= { hIPhFFSATransformsEntry 6 }

hIPhFFSATransformLastChanged OBJECT-TYPE
    SYNTAX      TimeStamp
    MAX-ACCESS  read-only
    STATUS      current
    DESCRIPTION
        "(U//FOUO) The value of sysUpTime when this row was last
         modified or created either through SNMP SET's or by some
         other external means."
    ::= { hIPhFFSATransformsEntry 7 }

hIPhFFSATransformRowStatus OBJECT-TYPE
    SYNTAX      RowStatus
    MAX-ACCESS  read-create
    STATUS      current
    DESCRIPTION
        "(U//FOUO) The status of the row, by which new entries may
        be created, or old entries deleted from this table.

        (U//FOUO) Since all writable columns in this table have
        default values, a new row may be created by simply setting
        this object to createAndGo. If this object is set to
        createAndGo and any columns included in the request contain
        inconsistent values an inconsistentName error will be
        returned for this object.

        (U//FOUO) The value of this object has no effect on whether
        other objects in this row can be modified.

        (U//FOUO) If any column is set to an invalid or unsupported
        value (during row creation or any other time), a wrongValue
        error will be returned for that object.

        (U//FOUO) An active row cannot be changed to an inconsistent
        state (an inconsistentValue error will be returned for the
        object).

        (U//FOUO) An active row may not be deleted while it is
        referenced by any active row in the hIPhFFSATable (an
        inconsistentValue error will be returned for this object)."
    ::= { hIPhFFSATransformsEntry 8 }

hIPhFFSATransformESN OBJECT-TYPE
    SYNTAX      TruthValue
    MAX-ACCESS  read-create
    STATUS      deprecated
    DESCRIPTION
        "(U//FOUO) Object DEPRECATED: HAIPEs will never use 32bit
        sequence numbers from ESPv1.
        
        (U//FOUO) Whether or not the SA should use Extended
        Sequence Numbers (i.e. 64 bit).  A value of 'true' indicates
        that 64 bit sequence numbers should be used.  A value of
        'false' indicates that 32 bit sequence numbers should be
        used instead."
    DEFVAL { true }
    ::= { hIPhFFSATransformsEntry 9 }

hIPhFFSATransformIntegrityAlgorithm OBJECT-TYPE
    SYNTAX      HaipeIntegrityAlgorithm
    MAX-ACCESS  read-create
    STATUS      current
    DESCRIPTION
        "(U//FOUO) The integrity algorithm type to use with this
        transform.  The value of multiple(7) is not a legal value here."
    DEFVAL  { gcm96 }
    ::= { hIPhFFSATransformsEntry 10 }

hIPhFFSATransformHashAlgorithm OBJECT-TYPE
    SYNTAX      HaipeHashAlgorithm
    MAX-ACCESS  read-create
    STATUS      current
    DESCRIPTION
        "(U//FOUO) The hash algorithm type to use with this transform."
    DEFVAL  { sha384 }
    ::= { hIPhFFSATransformsEntry 11 }

hIPhFFSATransformAuthenticationAlgorithm OBJECT-TYPE
    SYNTAX      HaipeAuthenticationAlgorithm
    MAX-ACCESS  read-create
    STATUS      current
    DESCRIPTION
        "(U//FOUO) The authentication algorithm type to use with this transform."
    DEFVAL  { eff }
    ::= { hIPhFFSATransformsEntry 12 }

hIPhFFSATransformICV OBJECT-TYPE
    SYNTAX      Unsigned32
    MAX-ACCESS  read-create
    STATUS      deprecated
    DESCRIPTION
        "(U//FOUO) DEPRECATED: this object duplicates values already
        known by looking at the integrity algorithm filed.

        (U//FOUO) The size of the Integrity Check Value (ICV) for
        this transform."
    DEFVAL { 96 }
    ::= { hIPhFFSATransformsEntry 13 }


-- **********************************************************************
-- Security Association Database Objects   SAD
--

hTPSAManagement       OBJECT IDENTIFIER ::= { hTPSecurityAssocDatabase 1 }

--
-- Table of SA Management
--


hTPSATableCount         OBJECT-TYPE
        SYNTAX          Unsigned32
        MAX-ACCESS      read-only
        STATUS		 current
        DESCRIPTION
            "(U//FOUO) The number of rows in the in the hTPSATable."
        ::= { hTPSAManagement 1 }

hTPSATableLastChanged         OBJECT-TYPE
        SYNTAX          TimeStamp
        MAX-ACCESS      read-only
        STATUS		 current
        DESCRIPTION
            "(U//FOUO) The value of sysUpTime the last time any entry in
        the hTPSATable was modified, created, or deleted by either
        SNMP or other management method (e.g. via an HMI).

        (U//FOUO) Managers can use this object to ensure that no
        changes to configuration of this table have happened since
        the last time it examined the table.

        (U//FOUO) A value of 0 indicates that no entry has been
        changed since the agent initialized."
        ::= { hTPSAManagement 2 }

hTPSATable              OBJECT-TYPE
        SYNTAX          SEQUENCE OF HTPSAEntry
        MAX-ACCESS      not-accessible
        STATUS		 current
        DESCRIPTION
            "(U//FOUO) The table containing a list of the known
            Security Associations (SA's) on this machine.  This table
            lists SAs created by any method, regardless of whether
            they were manually entered or created via an IKE
            negotiation.  This table only defines pairings between two
            HAIPEs and does not offer selector information about which
            remote networks/hosts are being protected by the remote
            and local HAIPEs.  This information is available in the
            HAIPE-NETWORKING-DISCOVERY-MIB::hDiscoveryTable.

            (U//FOUO) The index object for this table does not
            indicate the only requirement for uniqueness.  It is a
            simple integer to ease the lexographical processing burden
            of the agent.  Other IS requirements, such as the
            requirement to not accept configuration of two identical
            SPI values for multiple SAs operating simultaniously, will
            affect acceptable configuration that can be sent to this
            table.

            (U//FOUO) Note that it is possible to list both future and
            past SAs within this table and the status of a given SA
            must be checked before asusming that any entry in this
            table is currently active."
        ::= { hTPSAManagement 3 }

hTPSAEntry              OBJECT-TYPE
        SYNTAX          HTPSAEntry
        MAX-ACCESS      not-accessible
        STATUS		 current
        DESCRIPTION
            "(U//FOUO) A row describing the information about
            current Security Associations (SA's)."
        INDEX   { hTPSAIndex }
        ::= { hTPSATable 1 }

HTPSAEntry ::= SEQUENCE
    {
	hTPSAIndex                       Unsigned32,
	hTPSAspi                         Unsigned32,
	hTPSASelectorType                BITS,
	hTPSASelectorOpaques             BITS,
	hTPSAAddressType                 InetAddressType,
	hTPSALocalCTAddress              InetAddress,
	hTPSARemoteCTAddress             InetAddress,
	hTPSAPTAddressType               InetAddressType,
	hTPSALocalPTAddress              InetAddress,
	hTPSARemotePTAddress             InetAddress,
	hTPSADirection                   INTEGER,
	hTPSASelectorNextHeaderStart     Unsigned32,
	hTPSASelectorNextHeaderEnd       Unsigned32,
	hTPSASelectorNextHeaderOpt1Start Unsigned32,
	hTPSASelectorNextHeaderOpt1End   Unsigned32,
	hTPSASelectorNextHeaderOpt2Start Unsigned32,
	hTPSASelectorNextHeaderOpt2End   Unsigned32,
	hTPSAConnectionType              INTEGER,
	hTPSASecurityPayloadType         INTEGER,
	hTPSAStartTime                   DateAndTime,
	hTPSAEndTime                     DateAndTime,
	hTPSAPPK                         SnmpAdminString,
	hTPSACreationReason              INTEGER,
	hTPSAEncryptAlgorithm            HaipeEncryptionAlgorithm,
	hTPSAIntegrityAlgorithm          HaipeIntegrityAlgorithm,
	hTPSAICV                         Unsigned32,
	hTPSACryptoBlockSize             Unsigned32,
	hTPSASelectorDSCP                OCTET STRING,
	hTPSASelectorFlowLabel           OCTET STRING,
	hTPSADSCP                        INTEGER,
	hTPSADSCPValue                   OCTET STRING,
	hTPSAPMTU                        Unsigned32,
	hTPSAECN                         HECNTreatment,
	hTPSAFlowLabel                   INTEGER,
	hTPSAFlowLabelValue              OCTET STRING,
	hTPSADecrementTTL                TruthValue,
	hTPSADIndexType                  INTEGER,
	hTPSAPDUNEnabled                 TruthValue,
	hTPSAPHRDRate                    Unsigned32,
	hTPSADFBit                       INTEGER,
	hTPSAProcessFlowlabel            TruthValue,
	hTPSARetryICMPCount              Unsigned32,
	hTPSAesn                         TruthValue,
	hTPSATransmissionType            INTEGER,
	hTPSATransmissionRate            Unsigned32,
	hTPSATransmissionSize            Unsigned32,
	hTPSAHCOctets                    Counter64,
	hTPSAHCUcastPkts                 Counter64,
	hTPSAHCMcastPkts                 Counter64,
	hTPSAHCBrdcastPkts               Counter64,
	hTPSARowStatus                   RowStatus,
	hTPSALocalCredentialID           OCTET STRING,
	hTPSALocalCredentialType         HaipeCredentialType,
	hTPSALocalCAName                 OCTET STRING,
	hTPSARemoteCredentialID          OCTET STRING,
	hTPSARemoteCredentialType        HaipeCredentialType,
	hTPSARemoteCAName                OCTET STRING,
	hTPSANATAddress                  InetAddress,
	hTPSANATPort                     Unsigned32,
	hTPSAReuseSpi                    INTEGER,
	hTPSAReachable                   TruthValue,
	hTPSATFCConfig                   SnmpAdminString,
	hTPSATRPMDControlPlaneSignaling  TruthValue
    }

hTPSAIndex OBJECT-TYPE
    SYNTAX      Unsigned32
    MAX-ACCESS  not-accessible
    STATUS      current
    DESCRIPTION
        "(U//FOUO) A unique numeric index per SA.  The significance
        and ordering of this number will not reflect on the processing
        order of lookups within the SAD at all and is merely for
        management purposes."
    ::= { hTPSAEntry 1 }

hTPSAspi OBJECT-TYPE
    SYNTAX      Unsigned32
    MAX-ACCESS	 read-create
    STATUS		 current
    DESCRIPTION
        "(U//FOUO) The Security Parameters Index (SPI) value for
        this Security Association (SA).  This SPI will either be the
        local SPI when hTPSADirection is incoming, or the remote SPI
        when hTPSADirection is outgoing.

        (U//FOUO) Note that certain SPI values maybe restricted from
        use either for manually created SAs, automaticly created SAs
        or both.  There are no restrictions imposed by this MIB.

        (U//FOUO) Known existing restrictions from the HAIPE
        Interoperability Specifications include: 

           (U//FOUO)
           TP.ESP.ESPV3.1

        (U//FOUO) This list is included for convenience but is not
        intended to be a definitive source of information.  Please
        consult the real specifications for exact SPI value
        requirements."
    ::= { hTPSAEntry 2 }

hTPSASelectorType OBJECT-TYPE
    SYNTAX      BITS { sourceAddress(0), destinationAddress(1),
                       nextHeader(2), nextHeaderOpt1(3),
                       nextHeaderOpt2(4), dscp(5), flowlabel(6) }
    MAX-ACCESS	 read-create
    STATUS      current
    DESCRIPTION
        "(U//FOUO) This defines the various filters that are
        enforced on this SA.

        (U//FOUO) The results of each test are ANDed together with
        each other and with the tests indicated by the
        hTPSASelectorOpaques object to produce the result of the
        entire filter.  Any packet that doesn't match all the
        indicated filters MUST be dropped.  When processing this
        filter, it is recommended for efficiency reasons that the
        filter halt processing the instant any of the specified
        tests fail.

        (U//FOUO) With the exception of tests indicated by the
        hTPSASelectorOpaques column, any bit which is not set is
        equivalent to the ANY value discussed in 2401bis.

        (U//FOUO) Once a row is 'active', this object's value may
        not be changed unless all the required columns needed by any
        new selectors have been appropriately configured. The
        requirements for each selector are described below.

        (U//FOUO) A BIT value can not be set in this object if the
        corresponding BIT value in the hTPSASelectorOpaques column
        object is set.  e.g., if the nextHeader(2) bit is set in the
        hTPSASelectorOpaques column object, the corresponding
        nextHeader(2) bit can not be set in this object.  Any
        attempt to set such a value will result in an
        inconsistentValue error.

        (U//FOUO) If an attempt is made to set a value for this
        object that an agent does not understand, it should fail
        with a wrongValue error.

        (U//FOUO) The various tests definable in this table are as
        follows:

        (U//FOUO) sourceAddress:
           - (U//FOUO) Tests if the source address in the packet
             lies between the hTPSAAddressBegin and hTPSAAddressEnd
             objects in the rows of the hTPSAAddressSelectorTable
             which have a matching hTPSAIndex values to this row and
             where the hTPSAAddressSrcOrDest object is set to
             source(1).

             (U//FOUO) Note that setting the two objects above to
             the same address will limit the match to a single
             address.  The format and length of the address objects
             are defined by the hTPSAPTAddressType column.

             (U//FOUO) A notInService row in this table containing a
             hTPSASelectorType object with the sourceAddress bit set
             but without the hTPSAPTAddressType object set and at
             least one valid row in the hTPSAAddressSelectorTable
             with a matching hTPSAIndex and a hTPSAAddressSrcOrDest
             of source(1) will prevent this object from
             transitioning to the active state.

        (U//FOUO) destinationAddress:
           - (U//FOUO) Tests if the destination address in the
             packet lies between the hTPSAAddressBegin and hTPSAAddressEnd
             objects in the rows of the hTPSAAddressSelectorTable
             which have a matching hTPSAIndex values to this row and
             where the hTPSAAddressSrcOrDest object is set to
             destination(2).

             (U//FOUO) Note that setting the two objects above to
             the same address will limit the match to a single
             address.  The format and length of the address objects
             are defined by the hTPSAPTAddressType column.

             (U//FOUO) A notInService row in this table containing a
             hTPSASelectorType object with the destinationAddress
             bit set but without the hTPSAPTAddressType object set
             and at least one valid row in the
             hTPSAAddressSelectorTable with a matching hTPSAIndex
             and a hTPSAAddressSrcOrDest of destination(2) will
             prevent this object from transitioning to the active
             state.

         (U//FOUO) nextHeader:
           - (U//FOUO) Tests if NextHeader/Protocol value falls in the
             range of hTPSASelectorNextHeaderStart to
             hTPSASelectorNextHeaderEnd.  Note, setting these two
             columns to the same value will limit the match a single
             value of the NextHeader/Protocol field.  Implementations
             may choose not to support a range, and if so should
             return a WrongValue exception during a SET to the
             headerEnd object.

             (U//FOUO) A notInService row in this table containing a
             hTPSASelectorType object with the nextHeader object bit
             set but without the hTPSASelectorHeaderStart and
             hTPSASelectorHeaderEnd objects set will prevent this
             object from transitioning to the active state.

         (U//FOUO) nextHeaderOpt1:
           - (U//FOUO) Tests if an optional value in the range
             between hTPSASelectorNextHeaderOpt1Start and
             hTPSASelectorNextHeaderOpt1End exists in an IP packet.
             This option value is based on the NextHeader/protocol
             of the packet.  Because of this, in order to be a valid
             filter, when the nextHeaderOpt1 bit is set, the
             nextHeader bit MUST also be set and the
             hTPSASelectorHeaderStart and hTPSASelectorHeaderEnd
             objects MUST be equal.  If the hTPSASelectorHeaderStart
             object is any of the values in the first column below,
             the option tested for by this filter is indicated in
             the second column:
            (U//FOUO)
                        udp: source port
                        tcp: source port
                       icmp: icmp message type
                   mobility: mobility header type
            (U//FOUO)

             (U//FOUO) In order for a row that is currently
             notInService to transition to an active state with the
             nextHeaderOpt1 set, the following requirements MUST be
             met:
             The nextHeader bit MUST be set.
             The nextHeaderStart and nextHeaderEnd objects MUST be
             set to valid values and be equal.
             The hTPSASelectorHeaderOpt1Start and
             hTPSASelectorHeaderOpt1End objects must have valid
             values.

         (U//FOUO) nextHeaderOpt2:
           - (U//FOUO) Tests if an optional value in the range
             between hTPSASelectorNextHeaderOpt2Start and
             hTPSASelectorNextHeaderOpt2End exists in an IP packet.
             This option value is based on the NextHeader/protocol
             of the packet.  Because of this, in order to be a valid
             filter, when the nextHeaderOpt2 bit is set, the
             nextHeader bit MUST also be set and the
             hTPSASelectorHeaderStart and hTPSASelectorHeaderEnd
             objects MUST be equal.  If the hTPSASelectorHeaderStart
             object is any of the values in the first column below,
             the option tested for by this filter is indicated in
             the second column:
            (U//FOUO)
                        udp: destination port
                        tcp: destination port
                       icmp: icmp message code
            (U//FOUO)
 
             (U//FOUO) In order for a row that is currently
             notInService to transition to an active state with the
             nextHeaderOpt2 set, the following requirements MUST be
             met:
             The nextHeader bit MUST be set.
             The nextHeaderStart and nextHeaderEnd objects MUST be
             set to valid values and be equal.
             The hTPSASelectorHeaderOpt2Start and
             hTPSASelectorHeaderOpt2End objects must have valid
             values.

        (U//FOUO) dscp:
           - (U//FOUO) Tests to see if the packet being processed is
             matched properly for the dscp value given by the
             hTPSASelectorDSCP object.

             (U//FOUO) A notInService row in this table containing a
             hTPSASelectorType object with the dscp object bit but
             without the hTPSASelectorDSCP object set will prevent
             this object from transitioning to the active state.

        (U//FOUO) flowlabel:
           - (U//FOUO) Tests to see if the packet being processed is
             matched properly for the IPv6 flowlabel value given in
             the hTPSASelectorFlowLabel object.

             (U//FOUO) A notInService row in this table containing a
             hTPSASelectorType object with the flowlabel object bit
             but without the hTPSASelectorFlowLabel object set will
             prevent this object from transitioning to the active
             state.

        (U//FOUO) If any values of this object are unsupported by an
        implementation, than a wrongValue error should be returned
        upon a SET of one of these unsupported values."
    ::= { hTPSAEntry 3 }

hTPSASelectorOpaques OBJECT-TYPE
    SYNTAX      BITS { reserved(0), nextHeader(1), nextHeaderOpt1(2),
                       nextHeaderOpt2(3) }
    MAX-ACCESS  read-create
    STATUS      current
    DESCRIPTION
        "(U//FOUO) This defines various OPAQUE tests that can be
         used to filter a packet.  An OPAQUE test is true when the
         fields selected via the set bits are not available for
         examination.  Some examples of reasons that a field may not
         be available are: the field may not exist in a fragment;
         the field may not exist for a given next layer protocol; or
         because prior application of IPsec may have encrypted the
         values.

         (U//FOUO) The results of each test are ANDed together with
         each other and with the tests indicated by the
         hTPSASelectorType object to produce the result of the
         entire filter.  When processing this filter, it is
         recommended for efficiency reasons that the filter halt
         processing the instant any of the specified tests fail.

         (U//FOUO) A BIT value can not be set in this object if the
         corresponding BIT value in the hTPSASelectorType column
         object is set.  e.g., if the nextHeader(2) bit is set in
         the hTPSASelectorType column object, the corresponding
         nextHeader(2) bit can not be set in this object.  Any
         attempt to set such a value will result in an
         inconsistentValue error.

         (U//FOUO) If an attempt is made to set a value for this
         object that an agent does not understand, it should fail
         with a wrongValue error.
  
         (U//FOUO) The various tests definable in this table are as
         follows:

         (U//FOUO) nextHeader:
           - (U//FOUO) Tests that the Next Layer Protocol value
             indicated by the 'Next Header' fields is not
             examinable.  Either the field does not exist in the
             packet or it is otherwise unavailable for examination.

             (U//FOUO) This setting is only available for IPv6
             packets.  This bit should only be set if the
             hTPSAPTAddressType object indicates IPv6.  If an
             attempt to set this bit is made while the
             hTPSAPTAddressType object does not indicate IPv6,
             an inconsistentValue error should be returned.

             (U//FOUO) Any values in the
             hTPSASelectorNextHeaderStart and
             hTPSASelectorNextHeaderEnd objects are ignored.

         (U//FOUO) nextHeaderOpt1:
           - (U//FOUO) Tests if a value in the packet cannot be
             examined.  Either the field does not exist in the
             packet or it is otherwise unavailable for examination.
             The value this test for is dependent on the
             hTPSASelectorNextHeaderStart object.  When
             hTPSASelectorNextHeaderStart is set to the value in the
             first column of the following table, the second column
             indicates that field that should be unexaminable.
             (U//FOUO)
                        udp: source port
                        tcp: source port
                       icmp: icmp message type
                   mobility: mobility header type
             (U//FOUO)

             (U//FOUO) In order for a row that is currently
             notInService to transition to an active state with the
             nextHeaderOpt1 bit set, the following requirements MUST
             be met:
             The nextHeader bit MUST NOT be set.  
             The hTPSASelectorNextHeaderStart object MUST be set to
             a valid value.
 
             (U//FOUO) Any values in the
             hTPSASelectorNextHeaderOpt1Start and
             hTPSASelectorNextHeaderOpt1End objects are ignored.

         (U//FOUO) nextHeaderOpt2:
           - (U//FOUO) Tests if a value in the packet cannot be
             examined.  Either the field does not exist in the
             packet or it is otherwise unavailable for examination.
             The value this test for is dependent on the
             hTPSASelectorNextHeaderStart object.  When
             hTPSASelectorNextHeaderStart is set to the value in the
             first column of the following table, the second column
             indicates that field that should be unexaminable.
             (U//FOUO)
                        udp: destination port
                        tcp: destination port
                       icmp: icmp message code
             (U//FOUO)
 
             (U//FOUO) In order for a row that is currently
             notInService to transition to an active state with the
             nextHeaderOpt2 bit set, the following requirements MUST
             be met: 
             The nextHeader bit MUST NOT be set.  
             The hTPSASelectorNextHeaderStart object MUST be set to
             a valid value.
 
             (U//FOUO) Any values in the
             hTPSASelectorNextHeaderOpt2Start and
             hTPSASelectorNextHeaderOpt2End objects are ignored.

         (U//FOUO) If any values of this object are unsupported by
         an implementation, than a wrongValue error should be
         returned upon a SET of one of these unsupported values."
    ::= { hTPSAEntry 4 }

hTPSAAddressType OBJECT-TYPE
        SYNTAX      InetAddressType
        MAX-ACCESS	 read-create
        STATUS		 current
        DESCRIPTION
            "(U//FOUO) The address type for the source and destination
            CT addresses for this row.  If left unset by the manager
            during the creation of a manual SA it will default to an
            appropriate address from the HAIPE's addresses assigned to
            the CT interface."
        ::= { hTPSAEntry 5 }

hTPSALocalCTAddress OBJECT-TYPE
        SYNTAX      InetAddress
        MAX-ACCESS	 read-create
        STATUS		 current
        DESCRIPTION
            "(U//FOUO) The local CT IP address for the SA.  If left
            unset by the manager during the creation of a manual SA it
            will default to an appropriate address from the HAIPE's
            addresses assigned to the CT interface."
        ::= { hTPSAEntry 6 }

hTPSARemoteCTAddress OBJECT-TYPE
        SYNTAX      InetAddress
        MAX-ACCESS	 read-create
        STATUS		 current
        DESCRIPTION
            "(U//FOUO) The remote CT IP address for the SA."
        ::= { hTPSAEntry 7 }

hTPSAPTAddressType OBJECT-TYPE
        SYNTAX      InetAddressType
        MAX-ACCESS	 read-create
        STATUS		 current
        DESCRIPTION
            "(U//FOUO) The IP address type for the HAIPEs' PT addresses."
        ::= { hTPSAEntry 8 }

hTPSALocalPTAddress OBJECT-TYPE
        SYNTAX      InetAddress
        MAX-ACCESS	 read-create
        STATUS		 current
        DESCRIPTION
            "(U//FOUO) The local PT IP address for the SA."
        ::= { hTPSAEntry 9 }

hTPSARemotePTAddress OBJECT-TYPE
        SYNTAX      InetAddress
        MAX-ACCESS	 read-create
        STATUS		 current
        DESCRIPTION
            "(U//FOUO) The remote PT IP address for the SA.  If this
            SA's hTPSARemoteCTAddress is a multicast address then this
            column need not be set as there is no remote PT multicast
            address appropriate for this column.  An implementation
            should return a 'wrongValue' exception if this field is
            set for a multicast SA."
        ::= { hTPSAEntry 10 }

hTPSADirection OBJECT-TYPE
        SYNTAX      INTEGER { incoming(1), outgoing(2) }
        MAX-ACCESS	 read-create
        STATUS		 current
        DESCRIPTION
            "(U//FOUO) The direction that packet traffic is flowing
            for this SA."
        ::= { hTPSAEntry 11 }

hTPSASelectorNextHeaderStart OBJECT-TYPE
        SYNTAX      Unsigned32 (0..255)
        MAX-ACCESS	 read-create
        STATUS		 current
        DESCRIPTION
            "(U//FOUO) The starting NextHeader/Protocol selector value
            for this SA.  Implementations may choose not to support a
            range, and if so should return a WrongValue exception
            during a SET to the headerEnd object."
        DEFVAL { 0 }
        ::= { hTPSAEntry 12 }

hTPSASelectorNextHeaderEnd OBJECT-TYPE
        SYNTAX      Unsigned32 (0..255)
        MAX-ACCESS	 read-create
        STATUS		 current
        DESCRIPTION
            "(U//FOUO) The ending NextHeader/Protocol selector value
            for this SA. Implementations may choose not to support a
            range, and if so should return a WrongValue exception
            during a SET to the headerEnd object."
        DEFVAL { 255 }
        ::= { hTPSAEntry 13 }

hTPSASelectorNextHeaderOpt1Start OBJECT-TYPE
        SYNTAX      Unsigned32
        MAX-ACCESS	 read-create
        STATUS		 current
        DESCRIPTION
            "(U//FOUO) The starting option value for selector range.
            This option value is based on the NextHeader/protocol of
            the packet.  If the NextHeader/protocol is any of the
            following, this column and the
            hTPSASelectorNextHeaderOpt1End indicates:

            (U//FOUO)
                        udp: source port
                        tcp: source port
                       icmp: icmp message type
                   mobility: mobility header type
            (U//FOUO)"
        ::= { hTPSAEntry 14 }

hTPSASelectorNextHeaderOpt1End OBJECT-TYPE
        SYNTAX      Unsigned32
        MAX-ACCESS	 read-create
        STATUS		 current
        DESCRIPTION
            "(U//FOUO) The ending option value for the selector range."
        ::= { hTPSAEntry 15 }

hTPSASelectorNextHeaderOpt2Start OBJECT-TYPE
        SYNTAX      Unsigned32
        MAX-ACCESS	 read-create
        STATUS		 current
        DESCRIPTION
            "(U//FOUO) The starting option value for selector range.
            This option value is based on the NextHeader/protocol of
            the packet.  If the NextHeader/protocol is any of the
            following, this column and the
            hTPSASelectorNextHeaderOpt2End indicates:

            (U//FOUO)
                        udp: destination port
                        tcp: destination port
                       icmp: icmp message code
            (U//FOUO)"
        ::= { hTPSAEntry 16 }

hTPSASelectorNextHeaderOpt2End OBJECT-TYPE
        SYNTAX      Unsigned32
        MAX-ACCESS	 read-create
        STATUS		 current
        DESCRIPTION
            "(U//FOUO) The ending option value for the selector range."
        ::= { hTPSAEntry 17 }

hTPSAConnectionType OBJECT-TYPE
        SYNTAX      INTEGER { transportct(1), tunnel(2),
                              transportsa(3) }
        MAX-ACCESS	 read-create
        STATUS		 current
        DESCRIPTION
            "(U//FOUO) The connection type of this Security
            Association (SA).

            (U//FOUO) A type of tunnel(2) indicates a tunnel type
            connection.

            (U//FOUO) A type of transportsa(3) indicates a transport
            type connection that is differentiated by the SA the
            packet travels through.  The hTPTransportMapTable is
            used to map the SA of an arriving packet on the Cipher
            Text (CT) interface to the Plain Text (PT) source and
            destination addresses that are placed in the packet
            header.

            (U//FOUO) A type of transportct(1) indicates a transport
            type connection that is differentiated by the Cipher
            Text (CT) destination address.  The hTPAddressMapTable
            is used to map the source and destination CT addresses
            of a packet arriving on the CT interface to the PT
            addresses placed in the packet header."
        DEFVAL { tunnel }
        ::= { hTPSAEntry 18 }
 
hTPSASecurityPayloadType OBJECT-TYPE
        SYNTAX      INTEGER { deprecatedah(1), espv3(2), haipeespv1(3) }
        MAX-ACCESS  read-only
        STATUS		 current
        DESCRIPTION
            "(U//FOUO) The protection mechanism used to protect this SA."
        ::= { hTPSAEntry 19 }

hTPSAStartTime OBJECT-TYPE
        SYNTAX      DateAndTime
        MAX-ACCESS	 read-create
        STATUS		 current
        DESCRIPTION
            "(U//FOUO) The date and time the connection was or will
            be established."
        ::= { hTPSAEntry 20 }

hTPSAEndTime OBJECT-TYPE
        SYNTAX      DateAndTime
        MAX-ACCESS	 read-create
        STATUS		 current
        DESCRIPTION
            "(U//FOUO) The local entities notion of the end time for
            this connection.  If no definitive end-date/time is known
            than this value should be not-accessible."
        ::= { hTPSAEntry 21 }

hTPSAPPK OBJECT-TYPE
        SYNTAX      SnmpAdminString (SIZE(0..32))
        MAX-ACCESS	 read-create
        STATUS		 current
        DESCRIPTION
            "(U//FOUO) This object is only used for manually creating
            new SAs with a PPK between two HAIPEs.  It should indicate
            a set of rows in the hPPKChainTable with a matching
            hPPKChainID.  This set of rows is used to indicate a chain
            of PPK's to use for this SA.  SAs created which are not
            PPK based must return the value '' when this column is
            accessed."
        ::= { hTPSAEntry 22 }

hTPSACreationReason OBJECT-TYPE
        SYNTAX      INTEGER { other(1), manual(2), traffic(3), replacement(4) }
        MAX-ACCESS  read-only
        STATUS		 current
        DESCRIPTION
            "(U//FOUO) The reason a new SA was created.  If a SA was
            created by direct intervention of a management system,
            either HMI, SNMP or any other mechanism, the value of
            manual(2) should be used.  If a SA was created because of
            traffic (EG, an SPD rule was triggred), the value of
            traffic(3) should be used.  If an SA was created to
            replace another SA which was expiring for some reason, the
            value of replacement(4) should be used.  Otherwise, the
            value of other(1) should be used."
        DEFVAL { manual }
        ::= { hTPSAEntry 23 }

hTPSAEncryptAlgorithm OBJECT-TYPE
    SYNTAX      HaipeEncryptionAlgorithm
    MAX-ACCESS  read-only
    STATUS      current
    DESCRIPTION
        "(U//FOUO) This is the algorithm used for encrypting this SA.
        This value will usually be set from
        hPPKTrafficEncryptAlgorithm in the hPPKTrafficTable for PPK
        SA's or from the hIPhFFSATransformEncryptAlgorithm in the
        hIPhFFSATransformsTable for FF SA's."
    ::= { hTPSAEntry 24 }

hTPSAIntegrityAlgorithm OBJECT-TYPE
    SYNTAX      HaipeIntegrityAlgorithm
    MAX-ACCESS  read-create
    STATUS      current
    DESCRIPTION
        "(U//FOUO) This is the integrity algorithm uses with this
        transform SA.  This value will normally be set from the
        hIPhFFSATransformIntegrityAlgorithm column of the
        hIPhFFSATransformsTable for FF SA's.  For PPK based SAs it
        must be manually assigned when the SA is created and may not
        be changed while the SA is actively protecting traffic.  The
        value of multiple(7) is not a legal value here."
    ::= { hTPSAEntry 25 }

hTPSAICV OBJECT-TYPE
    SYNTAX      Unsigned32
    MAX-ACCESS  read-create
    STATUS      deprecated
    DESCRIPTION
        "(U//FOUO) DEPRECATED: this object duplicates values already
        known by looking at the integrity algorithm filed.

        (U//FOUO) The size of the Integrity Check Value (ICV) for
        this SA."
    ::= { hTPSAEntry 26 }

hTPSACryptoBlockSize OBJECT-TYPE
    SYNTAX      Unsigned32
    MAX-ACCESS	 read-create
    STATUS		 current
    DESCRIPTION
        "(U//FOUO) The Crypto Block Size in bytes for this SA.  The
        current valid values for this object are: 4 for SuiteA and
        SuiteB, and 8 and 48 are for older Legacy transforms."
    DEFVAL { 4 }
    ::= { hTPSAEntry 27 }

hTPSASelectorDSCP OBJECT-TYPE
    SYNTAX      OCTET STRING (SIZE(1))
    MAX-ACCESS  read-create
    STATUS      current
    DESCRIPTION
        "(U//FOUO) The DSCP value of incoming packets for this SA.
   
        (U//FOUO) The DSCP value used is garnered from the
        lower/right-most 6 bits of this octet.  Allowable values for
        this object should be in the range 0x00 - 0x3f.  Any attempt
        to set this object to a value outside of this range should
        fail with a wrong value error.

        (U//FOUO) This column is used for both IPv4 and IPv6
        packets.  For IPv6 packets, the DSCP bits are the
        high/left-most bits of the Traffic Class (TC) header bits.
        For IPv4, the DSCP bits are the high/left-most bits of Type
        Of Service (TOS) header bits."
    ::= { hTPSAEntry 28 }

hTPSASelectorFlowLabel OBJECT-TYPE
    SYNTAX      OCTET STRING (SIZE(3))
    MAX-ACCESS  read-create
    STATUS      current
    DESCRIPTION
        "(U//FOUO) The Flow Label value of incoming packets for this
        SA.

        (U//FOUO) Only the high/left-most 20 bits of this column are
        used.  Therefore, when setting this column, the last four
        bits in the last octet MUST be set to zero.  Any attempt to
        set the last four bits of this value to anything other than
        zero should result in a wrong value error."
    ::= { hTPSAEntry 29 }


hTPSADSCP   OBJECT-TYPE
    SYNTAX      INTEGER { set(1), deprecatedandmask(2), acceptlist(3) }
    MAX-ACCESS	 read-create
    STATUS		 current
    DESCRIPTION
        "(U//FOUO) The indication of how the Differentiated
        Service Code Points (DSCP) bits in a packet's header should
        be treated.

        (U//FOUO) If this column is set to set(1), the column
        hTPSADSCPValue should only be 1 octet in length and the
        DSCP value garnered from this octet is placed within the
        outgoing packet's DSCP header value.

        (U//FOUO) If this column is set to acceptlist(3), the column
        hTPSADSCPValue should be 8 octets in length and it will
        provide a list of acceptable DSCP values represented as a 64
        bit vector.  Each bit of hTPSADSCPValue will represent one
        acceptable DSCP value. If the incoming packet's DSCP value
        matches, that value is placed in the outgoing packet.  If
        none of the values in the list match an incoming packet's
        DSCP value, the outgoing packet's DSCP value is set to all
        0's.

        (U//FOUO) This column is used for both IPv4 and IPv6
        packets.  For IPv6 packets, the DSCP bits are the
        high/left-most bits of the Traffic Class (TC) header bits.
        For IPv4, the DSCP bits are the high/left-most bits of Type
        Of Service (TOS) header bits.

        (U//FOUO) Note: This column is only pertinent for traffic
        being encrypted (i.e. PT->CT traffic).

        (U//FOUO) DEPRECATED: If this column is set to andmask(2), the column
        hTPSADSCPValue should only be 1 octet in length and the DSCP
        value garnered from this octet is bitwise ANDed with the
        incoming packet's DSCP header value and the result set
        within the outgoing packet's DSCP header."
    DEFVAL { set }
    ::= { hTPSAEntry 30 }

hTPSADSCPValue  OBJECT-TYPE
    SYNTAX      OCTET STRING (SIZE (1|8))
    MAX-ACCESS	 read-create
    STATUS		 current
    DESCRIPTION
        "(U//FOUO) The Differentiated Service Code Points (DSCP)
        value for this SA.

        (U//FOUO) The use of this value is dependent on the value
        of the hTPSADSCP column in this row.  

        (U//FOUO) If the hTPSADSCP column is set to set(1), this
        value should be one octet in length in the range 0x00 -
        0x3f.  The DSCP value garnered from the lower/right-most 6
        bits of this octet is placed within the outgoing packet's
        Differentiated Service Code Points (DSCP) header value.

        (U//FOUO) When column hTPSADSCP is set to set(1) or
        deprecatedandmask(2), this column is only allowed to be a
        single octet length value in the range 0x00 - 0x3f inclusive.
        Any attempt to set this column to value outside of this range
        should, in this case, fail with an invalid value error.

        (U//FOUO) If the hTPSADSCP column is set to acceptlist(3),
        this value should be 8 octets in length and will provide a
        list of acceptable DSCP values represented as a 64-bit
        vector.  Each bit of this value represents one acceptable
        DSCP value and matches when the bit is set, i.e. '1'.  If
        the incoming packet's DSCP value matches a value represented
        in the vector, that value is placed in the outgoing packet.
        If none of the values in the vector match an incoming
        packet's DSCP value, the outgoing packet's DSCP value is set
        to all 0's.

        (U//FOUO)64 bit vector representation:
        Bit set         matches DSCP value
        0                       000000
        1                       000001
        2                       000010
        .                       .
        .                       .
        .                       .
        62                      111110
        63                      111111

        (U//FOUO) This column is used for both IPv4 and IPv6
        packets.  For IPv6 packets, the DSCP bits are the
        high/left-most bits of the Traffic Class (TC) header bits.
        For IPv4, the DSCP bits are the high/left most bits of Type
        Of Service (TOS) header.

        (U//FOUO) Note: This column is only pertinent for traffic
        being encrypted (i.e. PT->CT traffic).

        (U//FOUO) DEPRECATED: If the hTPSADSCP column is set to
        andmask(2), this value should be one octet in length in the
        range 0x00 - 0x3f.  The DSCP value garnered from the
        lower/right-most 6 bits of this octet is bitwise ANDed with
        the incoming packet's DSCP header value and the result set
        within the outgoing packet's DSCP header."
    DEFVAL { '00'h }
    ::= { hTPSAEntry 31 }

hTPSAPMTU    OBJECT-TYPE
    SYNTAX      Unsigned32
    MAX-ACCESS  read-only
    STATUS		 current
    DESCRIPTION
        "(U//FOUO) The PMTU value for this SA."
    ::= { hTPSAEntry 32 }

hTPSAECN    OBJECT-TYPE
    SYNTAX      HECNTreatment
    MAX-ACCESS	 read-create
    STATUS		 current
    DESCRIPTION
        "(U//FOUO) The indication of how the Explicit Congestion
        Notification (ECN) bits should be treated within this SA."
    DEFVAL { disabled }
    ::= { hTPSAEntry 33 }

hTPSAFlowLabel OBJECT-TYPE
    SYNTAX      INTEGER { set(1), deprecatedandmask(2), bypass(3) }
    MAX-ACCESS	 read-create
    STATUS		 current
    DESCRIPTION
        "(U//FOUO) The indication of how the twenty Flow Label bits in
        a IPv6 packet should be treated.  If this column is set to
        set(1), the hTPSAFlowLabelValue column will be placed within
        the outgoing packet's Flow Label header value.  If this column
        is set to bypass(3) then the flowlabel is bypassed from
        PT->CT.
        
        (U//FOUO) Note: This column is only pertinent for IPv6
        traffic that is being encrypted (i.e. PT->CT traffic).

        (U//FOUO) DEPRECATED: If this column is set to
        deprecatedandmask(2), the hTPSAFlowLabelValue column will be
        bitwise ANDed with the incoming packet's Flow Label header
        value and the result set within the outgoing packet's Flow
        Label header."
    DEFVAL { set }
    ::= { hTPSAEntry 34 }

hTPSAFlowLabelValue OBJECT-TYPE
    SYNTAX      OCTET STRING (SIZE (0..768))
    MAX-ACCESS	 read-create
    STATUS		 current
    DESCRIPTION
        "(U//FOUO) The flow label value for this PPK SA.

        (U//FOUO) The use of this value is dependent on the value
        of the hTPSAFlowLabel column in this row.
        
        (U//FOUO) when set(1):

          (U//FOUO) If the hTPSAFlowLabel column is set to set(1),
          this value will be placed within the outgoing packet's Flow
          Label header value.

          (U//FOUO) Only the high/left-most 20 bits of this column are
          used.  Therefore, when setting this column, the last four
          bits in the last octet MUST be set to zero.  Any attempt to
          set the last four bits of this value to anything other than
          zero should result in a wrong value exception.

        (U//FOUO) when bypass(3):

          (U//FOUO) If the hTPSAFlowLabel column is set to
          bypass(3), this value will be a list of acceptable values to
          bypass.  The encoding is a sequence of 3-octet values where
          each 3-octet component is a flow label value to pass Only
          the high/left-most 20 bits of each 3-octet value is used and
          the left four bits MUST be set to zero).  A 0-length will
          indicate that all flow-label values should be bypassed.

          (U//FOUO) Any attempt to set this value to an illegal
          encoding sent should return a wrong value exception.  An
          inconsistent value exception should be returned on an
          unsupported value.

        (U//FOUO) Note: This column is only pertinent for IPv6
        traffic that is being encrypted (i.e. PT->CT traffic).

        (U//FOUO) DEPRECATED: If the hTPSAFlowLabel column is set to
        andmask(2), this value will be bitwise ANDed with the
        incoming packet's Flow Label header value and the result set
        within the outgoing packet's Flow Label header."
    DEFVAL { '000000'h }
    ::= { hTPSAEntry 35 }

hTPSADecrementTTL OBJECT-TYPE
    SYNTAX          TruthValue
    MAX-ACCESS	 read-create
    STATUS		 current
    DESCRIPTION
        "(U//FOUO) The indication of whether the time-to-live (TTL)
        value is decremented as traffic passes through the SA."
    ::= { hTPSAEntry 36 }

hTPSADIndexType OBJECT-TYPE
    SYNTAX      INTEGER { reserved(1), spiDest(2), spiDestSrc(3), spi(4) }
    MAX-ACCESS	 read-create
    STATUS		 current
    DESCRIPTION
        "(U//FOUO) The Index type of the SAD entry.

        (U//FOUO) This object indicates whether an SAD entry
        created from this row requires an SA lookup to match
        the SPI and destination address; or the SPI, destination and
        source addresses.

        (U//FOUO) Note that the SAD entry with the longest matching
        SA identifier will be selected. That is, a matching SAD
        entry with an index type of spiDestSrc will be selected
        before an entry with an index type of spiDest.

        (U//FOUO) The spi(4) value should only be supported for legacy
        use reasons.  SAs only selecting on the spi value could have
        conflicts with dynamically configure SPIs being automatically
        generated prior to a manually assigned SPIs for use in shared
        multicast SAs."
    REFERENCE "2401bis section 4.1; 4301 section 4.1"
    DEFVAL { spiDest }
    ::= { hTPSAEntry 37 }

hTPSAPDUNEnabled OBJECT-TYPE
    SYNTAX      TruthValue
    MAX-ACCESS	 read-create
    STATUS		 current
    DESCRIPTION
        "(U//FOUO) The indication of whether the Peer Destination Unreachable
        Notification messages should be transmitted for this SA."
    ::= { hTPSAEntry 38 }

hTPSAPHRDRate OBJECT-TYPE
    SYNTAX      Unsigned32
    UNITS       "Seconds"
    MAX-ACCESS	 read-create
    STATUS		 current
    DESCRIPTION
        "(U//FOUO) The rate at which Peer HAIPE Reachability Detection
        messages should be transmitted for this SA (defined by the
        number of seconds between sent messages).  A value of zero
        indicates that the messages should never be sent (i.e. they
        are disabled)."
    DEFVAL { 0 }
    ::= { hTPSAEntry 39 }

hTPSADFBit  OBJECT-TYPE
    SYNTAX      INTEGER { set(1), clear(2), copy(3) }
    MAX-ACCESS	 read-create
    STATUS      current
    DESCRIPTION
        "(U//FOUO) The indication of how to handle the DF bit
        created in the CT packet: set it; clear it, or copy the DF
        bit from the PT packet.
        
        (U//FOUO) Note: This column is only pertinent traffic that
        is being encrypted (i.e. PT->CT traffic)."
    DEFVAL { clear }
    ::= { hTPSAEntry 40 }

hTPSAProcessFlowlabel  OBJECT-TYPE
    SYNTAX      TruthValue
    MAX-ACCESS	 read-create
    STATUS      deprecated
    DESCRIPTION
        "(U//FOUO) The indication of whether an SA should process IPv6
        Flow Labels."
    ::= { hTPSAEntry 41 }

hTPSARetryICMPCount  OBJECT-TYPE
    SYNTAX      Unsigned32
    MAX-ACCESS	 read-create
    STATUS      current
    DESCRIPTION
        "(U//FOUO) The number of successive missed PT ICMP Echo
        Requests that will cause the HAIPE to mark this SA endpoint
        as unreachable."
    ::= { hTPSAEntry 42 }

hTPSAesn OBJECT-TYPE
    SYNTAX      TruthValue
    MAX-ACCESS	 read-create
    STATUS      deprecated
    DESCRIPTION
        "(U//FOUO) Object DEPRECATED: HAIPEs will never use 32bit
        sequence numbers from ESPv1.
        
        (U//FOUO) Whether or not the SA should use Extended
        Sequence Numbers (i.e. 64 bit).  A value of 'true' indicates
        that 64 bit sequence numbers should be used.  A value of
        'false' indicates that 32 bit sequence numbers should be
        used instead."
    DEFVAL { true }
    ::= { hTPSAEntry 43 }

hTPSATransmissionType OBJECT-TYPE
    SYNTAX      INTEGER { regular(1), required(2), random(3) }
    MAX-ACCESS	 read-create
    STATUS      deprecated
    DESCRIPTION
        "(U//FOUO) This object is deprecated. 
        New implementations should use the hTPTFCConfigTable with 
        hIPhFFSATFCConfig and hTPSATFCConfig to configure TFC.

        (U//FOUO) The type of transmission mechansim this SA uses."
    DEFVAL { regular }
    ::= { hTPSAEntry 44 }

hTPSATransmissionRate OBJECT-TYPE
    SYNTAX      Unsigned32
    UNITS       "packets/second"
    MAX-ACCESS	 read-create
    STATUS      deprecated
    DESCRIPTION
        "(U//FOUO) This object is deprecated. 
        New implementations should use the hTPTFCConfigTable with 
        hIPhFFSATFCConfig and hTPSATFCConfig to configure TFC.

        (U//FOUO) The rate of transmission when hTPSATransmissionType
        is set to required ."
    ::= { hTPSAEntry 45 }

hTPSATransmissionSize OBJECT-TYPE
    SYNTAX      Unsigned32
    UNITS       "octets"
    MAX-ACCESS	 read-create
    STATUS      deprecated
    DESCRIPTION
        "(U//FOUO) This object is deprecated. 
        New implementations should use the hTPTFCConfigTable with 
        hIPhFFSATFCConfig and hTPSATFCConfig to configure TFC.

        (U//FOUO) The size of transmission when hTPSATransmissionType
        is set to required."
    ::= { hTPSAEntry 46 }

hTPSAHCOctets OBJECT-TYPE
    SYNTAX      Counter64
    MAX-ACCESS  read-only
    STATUS      current
    DESCRIPTION
        "(U//FOUO) A counter representing the number of octets
        traversing the SA."
    ::= { hTPSAEntry 47 }

hTPSAHCUcastPkts OBJECT-TYPE
    SYNTAX      Counter64
    MAX-ACCESS  read-only
    STATUS      current
    DESCRIPTION
        "(U//FOUO) A counter representing the number of unicast
        packets traversing the SA."
    ::= { hTPSAEntry 48 }

hTPSAHCMcastPkts OBJECT-TYPE
    SYNTAX      Counter64
    MAX-ACCESS  read-only
    STATUS      current
    DESCRIPTION
        "(U//FOUO) A counter representing the number of multicast
        packets traversing the SA."
    ::= { hTPSAEntry 49 }

hTPSAHCBrdcastPkts OBJECT-TYPE
    SYNTAX      Counter64
    MAX-ACCESS  read-only
    STATUS      current
    DESCRIPTION
        "(U//FOUO) A counter representing the number of broadcast
        packets traversing the SA."
    ::= { hTPSAEntry 50 }

hTPSARowStatus   OBJECT-TYPE
    SYNTAX          RowStatus
    MAX-ACCESS	 read-create
    STATUS		 current
    DESCRIPTION
        "(U//FOUO) The status of this row, by which entries may be
        created and deleted from this table.

        (U//FOUO) Entries created with this table may not become
        active unless all writable columns of this table have values
        (except potentially the hTPSAEndTime column). Manually created
        rows can not be made active while the hTPSAPPK object does not
        indicate a chain of PPK's with a current PPK that has assigned
        encryption and integrity algorithms.  Entries may be active,
        however, even though they are currently not used to protect
        traffic.  For example, SA entries defined for future use would
        have an effective start date beyond the current time.  Do not
        confuse the notion of the RowStatus value of active(1), which
        merely means the configuration is active, with the notion of
        whether or not the SA is currently being used to protect
        traffic.

        (U//FOUO) For hTPSADSCP column values of set(1) or
        deprecatedandmask(2), manually created rows can only become
        active if the column hTPSADSCPValue is one octet long.  For
        hTPSADSCP column values of acceptlist(3), manually created
        rows can only become active if the column hTPSADSCPValue is
        eight octets long.

        (U//FOUO) Entries which were created by any method other
        than manual(2) may not be modified except for setting this
        column to destroy(6), which will delete the SA.  Once a row
        has been made active it may not be modified except for
        setting this column to destroy(6) which will delete the SA."
        ::= { hTPSAEntry 51 }


hTPSALocalCredentialID  OBJECT-TYPE
    SYNTAX      OCTET STRING (SIZE(0..4096))
    MAX-ACCESS  read-only
    STATUS      current
    DESCRIPTION
        "(U//FOUO) For negotiated SAs requiring a public-key
        authentication system, this field will return the Certificate
        ID that was used to authenticate the local side of the SA.
        For manually created SAs instances of this object should not
        exist.

        (U//FOUO) When hTPSALocalCredentialType is set to ekms322(2) this
        field should be formmated as specified by the KMIDOrBlank
        TEXTUAL-CONVENTION."
    ::= { hTPSAEntry 52}

hTPSALocalCredentialType  OBJECT-TYPE
    SYNTAX      HaipeCredentialType
    MAX-ACCESS  read-only
    STATUS      current
    DESCRIPTION
        "(U//FOUO) For negotiated SAs requiring a public-key
        authentication system, this field should will return the
        certificate type that was used to authenticate the local side
        of the SA.  For manually created SAs instances of this object
        should not exist."
    ::= { hTPSAEntry 53}

hTPSALocalCAName  OBJECT-TYPE
    SYNTAX      OCTET STRING (SIZE(0..4096))
    MAX-ACCESS  read-only
    STATUS      current
    DESCRIPTION
        "(U//FOUO) The Name of the local certificate authority (CA)
        issuing the certificate referenced by the
        hTPSALocalCredentialID field.  For manually created SAs
        instances of this object should not exist.

        (U//FOUO) For hTPSALocalCredentialTypes of ekms322(2), this field
        should return 'EKMS FireFly'."
    ::= { hTPSAEntry 54}

hTPSARemoteCredentialID  OBJECT-TYPE
    SYNTAX      OCTET STRING (SIZE(0..4096))
    MAX-ACCESS  read-only
    STATUS      current
    DESCRIPTION
        "(U//FOUO) For negotiated SAs requiring a public-key
        authentication system, this field will return the Certificate
        ID that was used to authenticate the remote side of the SA.
        For manually created SAs instances of this object should not
        exist.

        (U//FOUO) When hTPSARemoteCredentialType is set to ekms322(2) this
        field should be formmated as specified by the KMIDOrBlank
        TEXTUAL-CONVENTION."
    ::= { hTPSAEntry 55}

hTPSARemoteCredentialType  OBJECT-TYPE
    SYNTAX      HaipeCredentialType
    MAX-ACCESS  read-only
    STATUS      current
    DESCRIPTION
        "(U//FOUO) For negotiated SAs requiring a public-key
        authentication system, this field should will return the
        certificate type that was used to authenticate the remote side
        of the SA.  For manually created SAs instances of this object
        should not exist."
    ::= { hTPSAEntry 56}

hTPSARemoteCAName  OBJECT-TYPE
    SYNTAX      OCTET STRING (SIZE(0..4096))
    MAX-ACCESS  read-only
    STATUS      current
    DESCRIPTION
        "(U//FOUO) The Name of the remote certificate authority (CA)
        issuing the certificate referenced by the
        hTPSARemoteCredentialID field.  For manually created SAs
        instances of this object should not exist.

        (U//FOUO) For hTPSARemoteCredentialTypes of ekms322(2), this field
        should return 'EKMS FireFly'."
    ::= { hTPSAEntry 57}

hTPSANATAddress OBJECT-TYPE
    SYNTAX      InetAddress
    MAX-ACCESS  read-create
    STATUS      current
    DESCRIPTION
        "(U//FOUO) The address of the NAT used on this SA
        connection.  It will be of the type indicated by the
        hTPSAAddressType column.  If this column is populated, this
        SA passes through a NAT of the given address.  If this
        column is empty, then no NAT exists on this connection.

        (U//FOUO) This column is the remote NAT address for both
        incoming and outgoing SAs."
    ::= { hTPSAEntry 58 }

hTPSANATPort OBJECT-TYPE
    SYNTAX      Unsigned32
    MAX-ACCESS  read-create
    STATUS      current
    DESCRIPTION
        "(U//FOUO) The port value of the NAT used on this SA
        connection.  This value is 0 for SAs that do not pass
        through a NAT.

        (U//FOUO) This column is the remote NAT port for both
        incoming and outgoing SAs."
    DEFVAL { 0 }
    ::= { hTPSAEntry 59 }

hTPSAReuseSpi OBJECT-TYPE
    SYNTAX      INTEGER { rotate(1), regular(2) }
    MAX-ACCESS	read-create
    STATUS      current
    DESCRIPTION
        "(U//FOUO) This element, once set to 'rotate', will rotate
        'Current' and 'Next' SPIs of a manual security association in
        the hTPSATable at the end of the 'Current' cryptoperiod.  This
        will result in hTPSATable being automatically populated
        indefinately with new manual security associations reusing the
        same set of SPIs every other day.  This element must be set
        for incoming (current and next) and outgoing (current and
        next) rows of a security association.  The default value for
        this element is 'regular'.

        (U//FOUO) This is implemented by having a future row with
        identical settings to this row be automatically added to the
        hTPSATable.  This future row should be created at the time the
        current SA's hTPSAEndTime has been reached.  Note that the
        date ranges specified in the hTPSAStartTime and the
        hTPSAEndTime objects of the future SA will need to indicate
        the appropriate time period of the replacement SA as indicated
        by policy of when changes must occur (EG, on a daily
        replacement schedule the future SA would be created with a
        hTPSAStartTime equal to the current hTPSAStartTime plus 2
        days, and similarily for the hTPSAEndTime).

        (U//FOUO) If another SA already exists that will conflict with
        the automatic replacement, then the pre-existant SA must take
        precidece and an automatically created SA must not be
        created.  This object is NOT applicable to Legacy ESP manual
        security association."
    DEFVAL { regular }
    ::= { hTPSAEntry 60 }

hTPSAReachable OBJECT-TYPE
    SYNTAX      TruthValue
    MAX-ACCESS  read-only
    STATUS      current
    DESCRIPTION
        "(U//FOUO) This element indicates whether or not the current
        SA is reachable based on values in the hTPSAPHRDRate and
        hTPSARetryICMPCount columns and the HAIPE reachability
        algorithm.  This value is true when the SA is currently
        considered reachable."
    ::= { hTPSAEntry 61 }

hTPSATFCConfig  OBJECT-TYPE
    SYNTAX       SnmpAdminString (SIZE(0..32))
    MAX-ACCESS	 read-create
    STATUS		 current
    DESCRIPTION
        "(U//FOUO) The TFC configuration to be used by this 
        SA.

        (U//FOUO) If populated, the value of this object 
        indicates which row in the hTPTFCConfigTable is to be used.
        This value must match the hTPTFCConfigName index value of the
        desired configuration.

        (U//FOUO) If this object is not populated, set to a zero
        length empty string, or set to a value which does not exist
        in the hTPTFCConfigTable, then no TFC mechanisms will be used 
        by this SA."

    ::= { hTPSAEntry 62 }

hTPSATRPMDControlPlaneSignaling OBJECT-TYPE
    SYNTAX      TruthValue
    MAX-ACCESS  read-create
    STATUS      current
    DESCRIPTION
        "(U//FOUO) This element indicates whether or not Control 
	Plane Signaling bits will be set for outgoing traffic.
	
	(U//FOUO) This object only applies to manually created 
	outgoing Transport Mode SAs.
	"
    ::= { hTPSAEntry 63 }


-- ********************************************************************

--
-- The address selectors for the SAs defined in the last table
--
hTPSAAddressSelectorTableCount         OBJECT-TYPE
        SYNTAX          Unsigned32
        MAX-ACCESS      read-only
        STATUS		 current
        DESCRIPTION
            "(U//FOUO) The number of rows in the in the
            hTPSAAddressSelectorTable."
        ::= { hTPSAManagement 4 }

hTPSAAddressSelectorTableLastChanged   OBJECT-TYPE
    SYNTAX          TimeStamp
    MAX-ACCESS      read-only
    STATUS		 current
    DESCRIPTION
        "(U//FOUO) The value of sysUpTime the last time any entry in
        the hTPSAAddressSelectorTable was modified, created, or
        deleted by either SNMP or other management method (e.g. via
        an HMI).

        (U//FOUO) Managers can use this object to ensure that no
        changes to configuration of this table have happened since
        the last time it examined the table.

        (U//FOUO) A value of 0 indicates that no entry has been
        changed since the agent initialized."
        ::= { hTPSAManagement 5 }

hTPSAAddressSelectorTable OBJECT-TYPE
    SYNTAX      SEQUENCE OF HTPSAAddressSelectorEntry
    MAX-ACCESS  not-accessible
    STATUS      current
    DESCRIPTION
        "(U//FOUO) The hTPSAAddressSelectorTable extends the
        hTPSATable to define a list of address-range selectors, both
        source and destination, for the SA.  This table independently
        separates the source and destination selector addresses and
        thus if there are M source adddress ranges, and N destination
        address ranges the selector will match if the packet is coming
        from any of the M source address-ranges to any of the N
        destination addresses-ranges (IE, a combination of M*N
        complete selector matching ranges)."
    ::= { hTPSAManagement 6 }

hTPSAAddressSelectorEntry OBJECT-TYPE
    SYNTAX      HTPSAAddressSelectorEntry
    MAX-ACCESS  not-accessible
    STATUS      current
    DESCRIPTION
        "A row describing an individual selector address range."
        INDEX   { hTPSAIndex, hTPSAAddressIndex }
    ::= { hTPSAAddressSelectorTable 1 }

HTPSAAddressSelectorEntry ::= SEQUENCE
    {
	hTPSAAddressIndex                Unsigned32,
	hTPSAAddressSrcOrDest            INTEGER,
	hTPSAAddressStart                InetAddress,
	hTPSAAddressEnd                  InetAddress,
	hTPSAAddressRowStatus            RowStatus
    }

hTPSAAddressIndex OBJECT-TYPE
    SYNTAX      Unsigned32
    MAX-ACCESS  not-accessible
    STATUS      current
    DESCRIPTION
        "(U//FOUO) A unique numeric index per SA - address range
        pair.  The significance and ordering of this number will not
        reflect on the processing order of lookups within the SAD at
        all and is merely for management purposes."
    ::= { hTPSAAddressSelectorEntry 1 }

hTPSAAddressSrcOrDest OBJECT-TYPE
    SYNTAX      INTEGER { source(1), destination(2) }
    MAX-ACCESS	 read-create
    STATUS		 current
    DESCRIPTION
        "(U//FOUO) Defines whether this row indicates a source address
        selector or a destination address selector."
    ::= { hTPSAAddressSelectorEntry 2 }


hTPSAAddressStart OBJECT-TYPE
        SYNTAX  InetAddress
        MAX-ACCESS	 read-create
        STATUS		 current
        DESCRIPTION
            "(U//FOUO) The starting address of the SA selector range.
            The address type is dictated by the hTPSAPTAddressType
            column in the parent table."
    ::= { hTPSAAddressSelectorEntry 3 }

hTPSAAddressEnd OBJECT-TYPE
        SYNTAX  InetAddress
        MAX-ACCESS	 read-create
        STATUS		 current
        DESCRIPTION
            "(U//FOUO) The ending address of the SA selector range.
            The address type is dictated by the hTPSAPTAddressType
            column in the parent table."
    ::= { hTPSAAddressSelectorEntry 4 }

hTPSAAddressRowStatus OBJECT-TYPE
        SYNTAX  RowStatus
        MAX-ACCESS	 read-create
        STATUS		 current
        DESCRIPTION
        "(U//FOUO) The status of this row, by which entries may be
        created and deleted from this table.

        (U//FOUO) Entries created with this table may not become
        active unless all writable columns of this table have
        values.

        (U//FOUO) Once a row has been made active it may not be
        modified except for setting this column to destroy(6) which
        will delete the Address Selection.

        (U//FOUO) When a parent row in the hTPSATable is destroyed,
        all corresponding rows in this table are to be automatically
        removed by the agent.  (Note that in SNMP it is legal for a
        manager to send a destroy(6) operation to a non-existent row,
        such as one that had been deleted in a case like this, and the
        destroy(6) operation on an empty row should not return an
        error condition to the manager.)"
    ::= { hTPSAAddressSelectorEntry 5 }

-- **********************************************************************
-- Traffic Protection address mapping
--

-- 
-- address mapping table
--

hTPAddressMapping       OBJECT IDENTIFIER ::= { hTPMapping 1 }


hTPAddressMapTableCount OBJECT-TYPE
    SYNTAX          Unsigned32
    MAX-ACCESS      read-only
    STATUS		 current
    DESCRIPTION
        "(U//FOUO) The number of rows in the in the
        hTPAddressMapTable."
    ::= { hTPAddressMapping 1 }

hTPAddressMapTableLastChanged    OBJECT-TYPE
    SYNTAX          TimeStamp
    MAX-ACCESS      read-only
    STATUS		 current
    DESCRIPTION
        "(U//FOUO) The value of sysUpTime the last time any entry in
        the hTPAddressMapTable was modified, created, or deleted by
        either SNMP or other management method (e.g. via an HMI).

        (U//FOUO) Managers can use this object to ensure that no
        changes to configuration of this table have happened since
        the last time it examined the table.

        (U//FOUO) A value of 0 indicates that no entry has been
        changed since the agent initialized."  
   ::= { hTPAddressMapping 2 }

hTPAddressMapTable      OBJECT-TYPE
    SYNTAX          SEQUENCE OF HTPAddressMapEntry
    MAX-ACCESS      not-accessible
    STATUS		 current
    DESCRIPTION
        "(U//FOUO) The table containing the current list of the
        address mappings between the Plain Text (PT) and Cipher Text
        (CT) sides of this device.

        (U//FOUO) The hTPAddMapPTAddress object indicates the PT
        address that is mapped and the hTPAddMapCTAddress object
        indicates the CT address that is mapped.  This table may be
        used to map PT->CT or CT->PT addresses.

        (U//FOUO) Note: The hTPAddMapPTAddress values are unique in
        the table while there is no such restriction on the
        hTPAddMapCTAddress object.  This allows an N to 1 mapping
        between PT and CT addresses respectively.

        (U//FOUO) This table can be used for any general PT<->CT
        mappings where the mapping information can not be extracted
        from other sources (such as the SPD rules, Topology
        information, etc).  For those implementations that support
        them, this table will normally be used for at least IGMP
        bypass."
    ::= { hTPAddressMapping 3 }

hTPAddressMapEntry              OBJECT-TYPE
    SYNTAX          HTPAddressMapEntry
    MAX-ACCESS      not-accessible
    STATUS		 current
    DESCRIPTION
        "(U//FOUO) A row describing the information about current
        address mapping across the PT-CT boundary."
    INDEX   { hTPAddMapAddressType, hTPAddMapPTAddress }
    ::= { hTPAddressMapTable 1 }

HTPAddressMapEntry ::= SEQUENCE
    {
	hTPAddMapAddressType             InetAddressType,
	hTPAddMapPTAddress               InetAddress,
	hTPAddMapCTAddress               InetAddress,
	hTPAddMapLastChanged             TimeStamp,
	hTPAddMapRowStatus               RowStatus
    }

hTPAddMapAddressType OBJECT-TYPE
    SYNTAX      InetAddressType
    MAX-ACCESS  not-accessible
    STATUS		 current
    DESCRIPTION
        "(U//FOUO) The address type for the hTPAddMapPTAddress and
        hTPAddMapCTAddress columns in this row."
    ::= { hTPAddressMapEntry 1 }

hTPAddMapPTAddress OBJECT-TYPE
    SYNTAX      InetAddress
    MAX-ACCESS  not-accessible
    STATUS		 current
    DESCRIPTION
        "(U//FOUO) This object is the Plain Text (PT) address that
        is mapped to/from the corresponding Cipher Text (CT) address
        in the hTPAddMapCTAddress object of this row."
    ::= { hTPAddressMapEntry 2 }

hTPAddMapCTAddress OBJECT-TYPE
    SYNTAX      InetAddress
    MAX-ACCESS	 read-create
    STATUS		 current
    DESCRIPTION
        "(U//FOUO) This object is the Cipher Text (CT) address that
        is mapped to/from the corresponding Plain Text (PT) address
        in the hTPAddMapPTAddress object of this row."
    ::= { hTPAddressMapEntry 3 }


hTPAddMapLastChanged OBJECT-TYPE
    SYNTAX      TimeStamp
    MAX-ACCESS  read-only
    STATUS      current
    DESCRIPTION
        "(U//FOUO) The value of sysUpTime when this row was last
         modified or created either through SNMP SET's or by some
         other external means."
    ::= { hTPAddressMapEntry 4 }

hTPAddMapRowStatus OBJECT-TYPE
    SYNTAX      RowStatus
    MAX-ACCESS  read-create
    STATUS      current
    DESCRIPTION
        "(U//FOUO) The status of the row, by which new entries may
        be created, or old entries deleted from this table.

        (U//FOUO) The value of this object has no effect on whether
        other objects in this row can be modified.

        (U//FOUO) If any column is set to an invalid or unsupported
        value (during row creation or any other time), a wrongValue
        error will be returned for that object.

        (U//FOUO) An active row cannot be changed to an inconsistent
        state (an inconsistentValue error will be returned for the
        object)."
    ::= { hTPAddressMapEntry 5 }

-- 
-- transport mapping table
--

hTPTransportMapping       OBJECT IDENTIFIER ::= { hTPMapping 2 }


hTPTransportMapTableCount OBJECT-TYPE
    SYNTAX          Unsigned32
    MAX-ACCESS      read-only
    STATUS		 current
    DESCRIPTION
        "(U//FOUO) The number of rows in the in the
        hTPTransportMapTable."
    ::= { hTPTransportMapping 1 }

hTPTransportMapTableLastChanged    OBJECT-TYPE
    SYNTAX          TimeStamp
    MAX-ACCESS      read-only
    STATUS		 current
    DESCRIPTION
        "(U//FOUO) The value of sysUpTime the last time any entry in
        the hTPTransportMapTable was modified, created, or deleted by
        either SNMP or other management method (e.g. via an HMI).

        (U//FOUO) Managers can use this object to ensure that no
        changes to configuration of this table have happened since
        the last time it examined the table.

        (U//FOUO) A value of 0 indicates that no entry has been
        changed since the agent initialized."  
   ::= { hTPTransportMapping 2 }

hTPTransportMapTable      OBJECT-TYPE
    SYNTAX          SEQUENCE OF HTPTransportMapEntry
    MAX-ACCESS      not-accessible
    STATUS		 current
    DESCRIPTION
        "(U//FOUO) The table containing the current list of the
        transportsa type SA connections.  It is used to map the
        Plain Text (PT) addresses for the transport connection."
    ::= { hTPTransportMapping 3 }

hTPTransportMapEntry              OBJECT-TYPE
    SYNTAX          HTPTransportMapEntry
    MAX-ACCESS      not-accessible
    STATUS		 current
    DESCRIPTION
        "(U//FOUO) A row describing the information about current SA
        transport address mapping across the PT-CT boundary for a
        given SA."
    INDEX   { hTPSAIndex }
    ::= { hTPTransportMapTable 1 }

HTPTransportMapEntry ::= SEQUENCE
    {
	hTPTransMapDestPTAddress         InetAddress,
	hTPTransMapSourcePTAddress       InetAddress,
	hTPTransMapLastChanged           TimeStamp,
	hTPTransMapRowStatus             RowStatus
    }

hTPTransMapDestPTAddress OBJECT-TYPE
    SYNTAX      InetAddress
    MAX-ACCESS  read-create
    STATUS		 current
    DESCRIPTION
        "(U//FOUO) For incoming Cipher Text (CT) packets using a
        transportsa type SA connection, this object indicates the
        destination address that should be set in the packet before
        sending it out on the Plain Text (PT) side.  The address type
        for this column must be the same as the hTPSAPTAddressType
        column from the hTPSATable that this row corresponds to."
    ::= { hTPTransportMapEntry 1 }

hTPTransMapSourcePTAddress OBJECT-TYPE
    SYNTAX      InetAddress
    MAX-ACCESS  read-create
    STATUS		 current
    DESCRIPTION
        "(U//FOUO) For incoming Cipher Text (CT) packets using a
        transportsa type SA connection, this object indicates the
        source address that should be set in the packet before
        sending it out on the Plain Text (PT) side.  The address type
        for this column must be the same as the hTPSAPTAddressType
        column from the hTPSATable that this row corresponds to."
    ::= { hTPTransportMapEntry 2 }

hTPTransMapLastChanged OBJECT-TYPE
    SYNTAX      TimeStamp
    MAX-ACCESS  read-only
    STATUS      current
    DESCRIPTION
        "(U//FOUO) The value of sysUpTime when this row was last
         modified or created either through SNMP SET's or by some
         other external means."
    ::= { hTPTransportMapEntry 3 }

hTPTransMapRowStatus OBJECT-TYPE
    SYNTAX      RowStatus
    MAX-ACCESS  read-create
    STATUS      current
    DESCRIPTION
        "(U//FOUO) The status of the row, by which new entries may
        be created, or old entries deleted from this table.

        (U//FOUO) The value of this object has no effect on whether
        other objects in this row can be modified.

        (U//FOUO) If any column is set to an invalid or unsupported
        value (during row creation or any other time), a wrongValue
        error will be returned for that object.

        (U//FOUO) An active row cannot be changed to an inconsistent
        state (an inconsistentValue error will be returned for the
        object).

        (U//FOUO) Once a row has been made active it may not be
        modified except for setting this column to destroy(6) which
        will delete the Address Selection.

        (U//FOUO) When a parent row in the hTPSATable is destroyed,
        all corresponding rows in this table are to be automatically
        removed by the agent.  (Note that in SNMP it is legal for a
        manager to send a destroy (6) operation to a non-existent row,
        such as one that had been deleted in a case like this, and the
        destroy (6) operation on an empty row should not return an
        error condititon to the manager)."

    ::= { hTPTransportMapEntry 4 }


-- **********************************************************************
-- Traffic Protection Traffic Flow Confidentiality (TFC)
--

-- 
-- TFC Configuration Table
--

hTPTFCConfigTableCount OBJECT-TYPE
    SYNTAX          Unsigned32
    MAX-ACCESS      read-only
    STATUS          current
    DESCRIPTION
        "(U//FOUO) The number of rows in the in the
        hTPTFCConfigTable."
    ::= { hTPTFC 1 }

hTPTFCConfigTableLastChanged    OBJECT-TYPE
    SYNTAX          TimeStamp
    MAX-ACCESS      read-only
    STATUS          current
    DESCRIPTION
        "(U//FOUO) The value of sysUpTime the last time any entry in
        the hTPTFCConfigTable was modified, created, or deleted by
        either SNMP or other management method (e.g. via an HMI).

        (U//FOUO) Managers can use this object to ensure that no
        changes to configuration of this table have happened since
        the last time it examined the table.

        (U//FOUO) A value of 0 indicates that no entry has been
        changed since the agent initialized."  
   ::= { hTPTFC 2 }

hTPTFCConfigTable   OBJECT-TYPE
    SYNTAX          SEQUENCE OF HTPTFCConfigEntry
    MAX-ACCESS      not-accessible
    STATUS          current
    DESCRIPTION
        "(U//FOUO) The table containing a list of TFC configurations.
        Entries in the hIPhFFSATable and hTPSATable reference 
        entries in this table to indicate the desired TFC configuration
        for the associated Security Association(s).

        (U//FOUO) If hIPhFFSATable or hTPSATable entries attempt to 
        reference an entry in this table which does not exist, then
        no TFC processing will be performed for those SAs.

        (U//FOUO) Deleting a row in this table disables all TFC
        processing for SAs referencing the deleted row."
    ::= { hTPTFC 3 }

hTPTFCConfigEntry   OBJECT-TYPE
    SYNTAX          HTPTFCConfigEntry
    MAX-ACCESS      not-accessible
    STATUS          current
    DESCRIPTION
        "(U//FOUO) A row describing a particular TFC configuration"
    INDEX   { hTPTFCConfigName }
    ::= { hTPTFCConfigTable 1 }

HTPTFCConfigEntry ::= SEQUENCE
    {
        hTPTFCConfigName                 SnmpAdminString,
        hTPTFCConfigTransmissionType     INTEGER,
        hTPTFCConfigTransmissionRate     Unsigned32,
        hTPTFCConfigPacketSizeType       INTEGER,
        hTPTFCConfigPacketSize           Unsigned32,
        hTPTFCConfigPacketSizeList       OCTET STRING,
        hTPTFCConfigRowStatus            RowStatus
    }


hTPTFCConfigName OBJECT-TYPE
    SYNTAX       SnmpAdminString (SIZE(1..32))
    MAX-ACCESS   not-accessible
    STATUS       current
    DESCRIPTION
        "(U//FOUO) The administrative name for this TFC configuration.
         object is the index into this table."
    ::= { hTPTFCConfigEntry 1 }

hTPTFCConfigTransmissionType OBJECT-TYPE
    SYNTAX      INTEGER { regular(1), fixedRate(2), randomRate(3) }
    MAX-ACCESS  read-create
    STATUS      current
    DESCRIPTION
        "(U//FOUO) The type of transmission mechansim SAs referencing
        this entry will use.
        
        (U//FOUO) regular(1) indicates that no Mandatory Transmission
        mechanisms are used.  Value of hTPTFCConfigTransmissionRate is
        ignored.

        (U//FOUO) fixedRate(2) indicates that Fixed Rate Mandatory 
        Transmission is required.  The value of hTPTFCConfigTransmissionRate
        specifies the desired rate.

        (U//FOUO) randomRate(3) indicates Random Rate Mandatory Transmission
        is required.  Value of hTPTFCConfigTransmissionRate is ignored.

        (U//FOUO) Implementations not supporting a particular transmission
        type should return a wrongValue error if a manager attempts to 
        enable that type."
        
    DEFVAL { regular }
    ::= { hTPTFCConfigEntry 2 }

hTPTFCConfigTransmissionRate OBJECT-TYPE
    SYNTAX      Unsigned32
    UNITS       "packets/second"
    MAX-ACCESS  read-create
    STATUS      current
    DESCRIPTION
        "(U//FOUO) The fixed rate of transmission to be used when 
        hTPTFCConfigTransmissionType is set to fixedRate.  This value is 
        ignored for all other settings of hTPTFCConfigTransmissionType."
    ::= { hTPTFCConfigEntry 3 }

hTPTFCConfigPacketSizeType OBJECT-TYPE
    SYNTAX      INTEGER { noPadding(1), fixedSize(2), 
                          randomSize(3), fixedListSize(4) }
    MAX-ACCESS  read-create
    STATUS      current
    DESCRIPTION
        "(U//FOUO) The type of TFC packet length control mechanism 
        SAs referencing this entry will use.
        
        (U//FOUO) noPadding(1) indicates that no TFC packet length
        control mechanism is used.  Value of hTPTFCConfigPacketSize 
        is ignored.

        (U//FOUO) fixedSize(2) indicates that all packets encapsulated
        by SAs referencing this entry must use a fixed ESP packet size.
        hTPTFCConfigPacketSize specifies the desired size.

        (U//FOUO) randomSize(3) indicates that all packets encapsulated
        by SAs referencing this entry must use randomly variable ESP 
        packet size.  Value of hTPTFCConfigPacketSize is ignored.

        (U//FOUO) fixedListSize(4) indicates that all packets encapsulated
        by SAs referencing this entry must restrict ESP packet sizes to
        to those specified in hTPTFCConfigPacketSizeList.
        Value of hTPTFCConfigPacketSize is ignored.

        (U//FOUO) Implementations not supporting a particular packet
        length control mechanism should return a wrongValue error 
        if a manager attempts to enable that type."
        
    DEFVAL { noPadding }
    ::= { hTPTFCConfigEntry 4 }

hTPTFCConfigPacketSize OBJECT-TYPE
    SYNTAX      Unsigned32
    MAX-ACCESS  read-create
    STATUS      current
    DESCRIPTION
       "(U//FOUO) The fixed ESP packet size to be used when 
       hTPTFCConfigPacketSizeType is set to fixedSize.  This value is 
       ignored for all other settings of hTPTFCConfigPacketSizeType.

       (U//FOUO) The value specified by this object is the number
       of octets from the SPI through the authentication/integrity
       data inclusive. i.e., the specified fixed packet size applies
       only to the ESP data, and not the outer CT IP header.
       
       (U//FOUO)  Implementations will certainly not
       support the setting of all possible values to this object,
       and a wrongValue exception should be returned when an attempt
       to set this object to an unsupported value occurs."

    ::= { hTPTFCConfigEntry 5 }

hTPTFCConfigPacketSizeList OBJECT-TYPE
   SYNTAX      OCTET STRING (SIZE(0..256))
   MAX-ACCESS  read-write
   STATUS      current
   DESCRIPTION
       "(U//FOUO) If hTPTFCConfigPacketSizeType is set to
       fixedListSize, this object will indicate a ordered list of
       ESP packet sizes to use when encapsulating packets.  
          
       (U//FOUO) The OCTET STRING will be multiple 2-octet SHORTs
       in network byte order (high octet first).  The will be sorted
       by the manager uploading the list to the object and
       configurations MAY choose to reject configuration of lists
       that are not properly sorted.

       (U//FOUO) ESP packet sizes specified by this object correspond to the
       number of octets from the SPI through the authentication/integrity 
       data inclusive. i.e., the specified packet size applies only to
       the ESP data, and not the outer CT IP header.

       (U//FOUO)  Implementations will certainly not
       support the setting of all possible values to this object,
       and a wrongValue exception should be returned when an attempt
       to set this object to an unsupported value occurs."

    ::= { hTPTFCConfigEntry 6 }

hTPTFCConfigRowStatus OBJECT-TYPE
    SYNTAX      RowStatus
    MAX-ACCESS  read-create
    STATUS      current
    DESCRIPTION
       "(U//FOUO) The status of this row, by which new entries
       may be created, or old entries deleted from this table.

       (U//FOUO) Deleting a row in this table disables all TFC
       processing for SAs referencing the deleted row.

       (U//FOUO) If any column is set to an
       unsupported value (during row creation or any other
       time), a wrongValue error will be returned for that
       object."

    ::= { hTPTFCConfigEntry 7 }


-- **********************************************************************
-- Traffic Protection policy notifications
--


hTPnSADestroyed NOTIFICATION-TYPE
    OBJECTS     { hStationID, hrSystemDate, hTPiSPI,
                  hTPiDestinationAddressType, hTPiDestinationAddress,
                  hTPiSADestroyedReason }
    STATUS      current 
    DESCRIPTION
        "(U//FOUO) This notification event indicates that a
         traffic SA was taken down between the HAIPE sending the
         notification and another remote HAIPE.

         (U//FOUO) The recommended hAuditConfigTable defaults for this
         notification are:
                ThrottlingEnabled: true
                LogThrottleCfg   : Once per minute
                NotifEnabled     : true
                NotifThrottleCfg : Once per minute"
    ::= { hTPPolicyNotifs 16 }

hTPnSACreated NOTIFICATION-TYPE
    OBJECTS     { hStationID, hrSystemDate, hTPiSPI,
                  hTPiDestinationAddressType, hTPiDestinationAddress,
                  hTPSACreationReason }
    STATUS      current 
    DESCRIPTION
        "(U//FOUO) This notification event indicates that a traffic SA
         was created between the HAIPE sending the notification and
         another remote HAIPE.

         (U//FOUO) The recommended hAuditConfigTable defaults for this
         notification are:
                ThrottlingEnabled: true
                LogThrottleCfg   : Once per minute
                NotifEnabled     : true
                NotifThrottleCfg : Once per minute"
    ::= { hTPPolicyNotifs 17 }


-- policy notification-specific objects

hTPiDestinationAddressType OBJECT-TYPE
        SYNTAX          InetAddressType
        MAX-ACCESS      accessible-for-notify
        STATUS          current
        DESCRIPTION
            "(U//FOUO) The destination address type of a packet."
        ::= { hTPPolicyNotifObjects 3 }

hTPiDestinationAddress   OBJECT-TYPE
        SYNTAX          InetAddress
        MAX-ACCESS      accessible-for-notify
        STATUS          current
        DESCRIPTION
            "(U//FOUO) The destination address of a packet."
        ::= { hTPPolicyNotifObjects 4 }

hTPiSPI OBJECT-TYPE
        SYNTAX      Unsigned32
        MAX-ACCESS  accessible-for-notify
        STATUS      current
        DESCRIPTION
            "(U//FOUO) The SPI value of the SA associated with the current
            notification."
        ::= { hTPPolicyNotifObjects 8 }

hTPiSADestroyedReason OBJECT-TYPE
        SYNTAX      INTEGER { 
                              other(1),
                              managementAction(2),
                              expired(3),
                              protocolRequested(4)
                            }
        MAX-ACCESS  accessible-for-notify
        STATUS      current
        DESCRIPTION
            "(U//FOUO) This object is sent with a SA destroyed
            notification to indicate why a SA was taken down.  Note
            that managementAction may be the result of either a remote
            or local HMI user action.  A protocolRequested action
            would be a remote IPsec or IKE action that requested the
            SA be closed (eg, a DELETE request)."
        ::= { hTPPolicyNotifObjects 14 }

END
